;
;
;     Program written by Robert Livingston, 2015-11-13
;
;     QT:GetD returns the Vehicle parameters for an entered vehicle
;
;     Returns (DEye DGear DRear DHook LockAng LoadBase LoadAngle WheelFront WheelRear)
;
;     DEye (D0) = Distance from block insertion point to the eye point (the path point of the vehicle)
;     DGear (DG) = Distance from block insertion point to front wheels
;     DRear (D) = Distance from block insertion point to rear wheels
;     DHook (DH) = Distance from block insertion point to hitch (king pin)
;     LockAng (LOCKANG) = Wheel lock angle
;     LoadBase (LB) = Distance from block insertion point to load pivot/base point
;     LoadAngle (LA) = Distance from block insertion point to load angle definition point
;     WheelFront (WF) = Width between front wheels (not used at this time)
;     WheelRear (WR) = Width between rear wheels (not used at this time)
;
;
(defun QT:GETD (ENT / D D0 DG DH ENTLIST LA LB LOCKANG WF WR)
 (setq D nil
       D0 nil
       DG nil
       DH nil
       LOCKANG nil
       LA nil
       LB nil
       WF nil
       WR nil
 )
 (if (/= nil ENT)
  (progn
   (setq ENTLIST (entget ENT))
   (setq BLOCKSCALE (cdr (assoc 41 ENTLIST)))
   (if (= "INSERT" (cdr (assoc 0 ENTLIST)))
    (progn
     (setq ENT (entnext ENT))
     (setq ENTLIST (entget ENT))
     (while (= "ATTRIB" (cdr (assoc 0 ENTLIST)))
      (cond ((= "D0" (strcase (cdr (assoc 2 ENTLIST))))
             (setq D0 (* BLOCKSCALE (atof (cdr (assoc 1 ENTLIST)))))
            )
            ((= "DG" (strcase (cdr (assoc 2 ENTLIST))))
             (setq DG (* BLOCKSCALE (atof (cdr (assoc 1 ENTLIST)))))
            )
            ((= "D" (strcase (cdr (assoc 2 ENTLIST))))
             (setq D (* BLOCKSCALE (atof (cdr (assoc 1 ENTLIST)))))
            )
            ((= "DH" (strcase (cdr (assoc 2 ENTLIST))))
             (setq DH (* BLOCKSCALE (atof (cdr (assoc 1 ENTLIST)))))
            )
            ((= "L" (strcase (cdr (assoc 2 ENTLIST))))
             (if (/= "" (cdr (assoc 1 ENTLIST)))
              (setq LOCKANG (atof (cdr (assoc 1 ENTLIST))))
             )
            )
            ((= "LB" (strcase (cdr (assoc 2 ENTLIST))))
             (setq LB (* BLOCKSCALE (atof (cdr (assoc 1 ENTLIST)))))
            )
            ((= "LA" (strcase (cdr (assoc 2 ENTLIST))))
             (setq LA (* BLOCKSCALE (atof (cdr (assoc 1 ENTLIST)))))
            )
            ((= "WF" (strcase (cdr (assoc 2 ENTLIST))))
             (if (/= "" (cdr (assoc 1 ENTLIST)))
              (setq WF (* BLOCKSCALE (atof (cdr (assoc 1 ENTLIST)))))
             )
            )
            ((= "WR" (strcase (cdr (assoc 2 ENTLIST))))
             (if (/= "" (cdr (assoc 1 ENTLIST)))
              (setq WR (* BLOCKSCALE (atof (cdr (assoc 1 ENTLIST)))))
             )
            )
      )
      (setq ENT (entnext ENT))
      (setq ENTLIST (entget ENT))
     )
    )
   )
  )
 )
 (list D0 DG D DH LOCKANG LB LA WF WR)
)
;
;
;   Program written by Robert Livingston, 2016-05-16
;
;   C:QUICKTURN main routine
;
;   QTWrapperStart.lsp is the header wrapper for C:QUICKTURN
;
;
; C:QT is a shortcut for C:QUICKTURN
(defun C:QT ()
 (C:QUICKTURN)
)
(defun C:QUICKTURN (/ *error*
                      ; Variables
                      ANGBASE ANGDIR BLOCKSCALE C CMAX CMDECHO D D0 DG DH
                      ENT ENTFIRST ENTLIST FIRSTLOCKANG FLAG GETTURNANG LA LALIST LB LBLIST LOCKANG
                      QT:LOCKANGWARNING
                      NODE OSMODE P PLA PLB PLIST PLINELIST QTDLIST QTVLIST REP REP2 STA
                      STAMAX STEP TAN TMP WF WR
                      
                      ; Functions
                      QT:CIRCLE3P QT:COPY QT:DRAWENVELOPE QT:GETENVELOPE QT:GETPLIST QT:MAKETEMPBLOCK
                      QT:MOVEVEHICLE QT:NEWANG QT:NEWWHEELANG QT:PLACE QT:SETPATH QT:SETWHEELPATH QT:TPATH
                      QT:TWHEELS
                   )
 (command "._UNDO" "M")
 (command "._UCS" "W")
 (setq CMDECHO (getvar "CMDECHO"))
 (setvar "CMDECHO" 0)
 (setq OSMODE (getvar "OSMODE"))
 (setq ANGBASE (getvar "ANGBASE"))
 (setvar "ANGBASE" 0.0)
 (setq ANGDIR (getvar "ANGDIR"))
 (setvar "ANGDIR" 0)
 
 (setq QT:LOCKANGWARNING nil)

 (if (= nil QT:MSGPOPUP)
  (progn
   (setq QT:MSGPOPUP T)
   (alert (strcat "QUICKTURN - Vehicle Turn Movement Simulator\n\n"
                  "The author makes no warranty, representation or guarantee, expressed,\n"
                  "implied or statutory, as to the accuracy, reliability, suitability,\n"
                  "function, or results derived from QUICKTURN.  The author shall incur\n"
                  "no liability, loss or damage caused or alleged to be caused directly\n"
                  "or indirectly by QUICKTURN, including, but not limited to, any\n"
                  "interruption of service, loss of business or anticipated profits, lost\n"
                  "savings, or incidental, special, punitive or consequential damages\n"
                  "resulting from the use or operation of QUICKTURN even if caused by the\n"
                  "negligence of the author and even if the author had the knowledge of\n"
                  "the possibility of such liability, loss, or damage.  All computer\n"
                  "program results require professional interpretation and the author\n"
                  "makes no warranty for results obtained by using QUICKTURN.\n\n"
                   "By clicking OK below you agree to be bound by these conditions."
          )
   )
  )
 )

 (defun *error* (msg)
  (foreach NODE QTVLIST (redraw (car NODE) 1))
  (foreach NODE QTVLIST (entdel (last NODE)))
  (command "._UCS" "P")
  (setvar "CMDECHO" CMDECHO)
  (setvar "ANGBASE" ANGBASE)
  (setvar "ANGDIR" ANGDIR)
  (setvar "OSMODE" OSMODE)
  (setq *error* nil)
  (print msg)
 )

 (defun TAN (X)
  (/ (sin X) (cos X))
 )
;
;
;   Program written by Robert Livingston, 2016-05-16
;
;   QT:CIRCLE3P calculates a 3 Point Circle
;
;
(defun QT:CIRCLE3P (P1 P2 P3 / CALCC3P TOL X1 X2 X3 Y1 Y2 Y3)
 (defun CALCC3P (X1 Y1 X2 Y2 X3 Y3 / DEN M12 M23 NUM R RES XC YC)
  (setq M12 (/ (- Y2 Y1) (- X2 X1)))
  (setq M23 (/ (- Y3 Y2) (- X3 X2)))
  (setq NUM (- (+ (* M12 M23 (- Y1 Y3)) (* M23 (+ X1 X2))) (* M12 (+ X2 X3))))
  (setq DEN (* 2.0 (- M23 M12)))
  (setq XC (/ NUM DEN))
  (setq YC (- (/ (+ Y1 Y2) 2.0) (* (/ 1.0 M12) (- XC (/ (+ X1 X2) 2.0)))))
  (setq R (sqrt (+ (expt (- X1 XC) 2.0) (expt (- Y1 YC) 2.0))))
  (list (list XC YC) R)
 )
 (setq TOL 1e-10)
 (setq X1 (car P1))
 (setq Y1 (cadr P1))
 (setq X2 (car P2))
 (setq Y2 (cadr P2))
 (setq X3 (car P3))
 (setq Y3 (cadr P3))
 (setq RES (vl-catch-all-apply 'CALCC3P (list X1 Y1 X2 Y2 X3 Y3)))
 (if (vl-catch-all-error-p RES)
  (progn
   (setq RES (vl-catch-all-apply 'CALCC3P (list X2 Y2 X3 Y3 X1 Y1)))
   (if (vl-catch-all-error-p RES)
    (progn
     (setq RES (vl-catch-all-apply 'CALCC3P (list X3 Y3 X1 Y1 X2 Y2)))
     (if (vl-catch-all-error-p RES)
      nil
      RES
     )
    )
    RES
   )
  )
  RES
 )
)
;
;
;   Program written by Robert Livingston, 2016-05-16
;
;   QT:COPY copies a vehicle at posicion 'C' to a temporary block
;
;
(defun QT:COPY (/ NODE)
 (foreach NODE QTVLIST
  (progn
   (QT:MAKETEMPBLOCK (last NODE))
  )
 )
)
;
;
;     Program written by Robert Livingston, 2015-11-13
;
;     QT:DRAWENVELOPE draws the vehicle envelope
;
;
(defun QT:DRAWENVELOPE (/ ANG1 ANG2 BLOCKNAME C C2 CECOLOR COLOR ENT ENTLIST ENTLISTNEW GETBLOCKNAME
                          NODE P P1 P2 PA PB PC PD TMP VINC VLIST)

 (defun GETBLOCKNAME (/ C)
  (setq C 1)
  (while (/= nil (tblsearch "BLOCK" (strcat "QTENVELOPE" (itoa C))))
   (setq C (+ C 1))
  )
  (strcat "QTENVELOPE" (itoa C))
 )
 (setq ENTLISTNEW (list (list (cons 0 "BLOCK")
                              (cons 2 "*U")
                              (cons 8 "0")
                              (cons 70 1)
                              (list 10 0.0 0.0 0.0)
                        )
                  )
 )
    
 (setq VINC 1)
 (setq CECOLOR (getvar "CECOLOR"))
 (setvar "OSMODE" 0)
 (setq COLOR (getint "\nEnter colour for block (0-256, 0=ByBlock, 256=ByLayer) <0> : "))
 (if (= nil COLOR) (setq COLOR 0))
 (if (or (< COLOR 0) (> COLOR 256)) (setq COLOR 0))
 (setvar "CECOLOR" (itoa COLOR))
 (foreach NODE QTVLIST
  (progn
   (setq ENT (car NODE))
   (setq VLIST (QT:GETENVELOPE ENT))
   (if (/= nil VLIST)
    (progn
     (setq C 0)
     (while (< C CMAX)
      (setq ANG1 (nth C (nth 1 NODE)))
      (setq P1 (nth C (nth 2 NODE)))
      (setq ANG2 (nth (min (+ C VINC) CMAX) (nth 1 NODE)))
      (setq P2 (nth (min (+ C VINC) CMAX) (nth 2 NODE)))
      (setq C2 0)
      (while (< C2 (length VLIST))
       (setq P (nth C2 VLIST))
       (setq PA (list (+ (nth 0 P1) (* (nth 0 P) (cos ANG1)) (* -1.0 (nth 1 P) (sin ANG1)))
                      (+ (nth 1 P1) (* (nth 0 P) (sin ANG1)) (* (nth 1 P) (cos ANG1)))))
       (setq PC (list (+ (nth 0 P2) (* (nth 0 P) (cos ANG2)) (* -1.0 (nth 1 P) (sin ANG2)))
                      (+ (nth 1 P2) (* (nth 0 P) (sin ANG2)) (* (nth 1 P) (cos ANG2)))))
       (if (= C2 (- (length VLIST) 1))
        (setq P (nth 0 VLIST))
        (setq P (nth (+ C2 1) VLIST))
       )
       (setq PB (list (+ (nth 0 P1) (* (nth 0 P) (cos ANG1)) (* -1.0 (nth 1 P) (sin ANG1)))
                      (+ (nth 1 P1) (* (nth 0 P) (sin ANG1)) (* (nth 1 P) (cos ANG1)))))
       (setq PD (list (+ (nth 0 P2) (* (nth 0 P) (cos ANG2)) (* -1.0 (nth 1 P) (sin ANG2)))
                      (+ (nth 1 P2) (* (nth 0 P) (sin ANG2)) (* (nth 1 P) (cos ANG2)))))
       (setq ENTLISTNEW (append ENTLISTNEW
                               (list (list (cons 0 "SOLID")
                                           (cons 8 "0")
                                           (list 10 (car PA) (cadr PA) 0.0)
                                           (list 11 (car PB) (cadr PB) 0.0)
                                           (list 12 (car PC) (cadr PC) 0.0)
                                           (list 13 (car PD) (cadr PD) 0.0)
                                     )
                               )
                        )
       )
       (setq C2 (+ C2 1))
      )
      (setq C (+ C VINC))
     )
    )
   )
  )
 )
 (setq ENTLISTNEW (append ENTLISTNEW (list (list (cons 0 "ENDBLK")))))
 (entmake)
 (foreach NODE ENTLISTNEW
  (setq TMP (entmake NODE))
 )
 (entmake (list (cons 0 "INSERT")
                (cons 2 TMP)
                (list 10 0.0 0.0 0.0)
                (cons 41 1.0)
                (cons 42 1.0)
                (cons 43 1.0)
                (cons 50 0.0)
          )
 )
 (command "._DRAWORDER" (entlast) "" "BACK")
 (setvar "CECOLOR" CECOLOR)
 (setvar "OSMODE" OSMODE)
)
;
;
;   Program written by Robert Livingston, 2016-05-16
;
;   QT:GETENVELOPE returns the point list of the polyline/lwpolyline on layer defpoints in the entity
;
;
(defun QT:GETENVELOPE (ENT / BLOCKSCALE ENT2 ENTLIST ENTNAME NODE P VLIST)
 (setq VLIST nil)
 (setq ENTLIST (entget ENT))
 (setq BLOCKSCALE (cdr (assoc 41 ENTLIST)))
 (setq ENTNAME (cdr (assoc 2 ENTLIST)))
 (setq ENTLIST (tblsearch "BLOCK" ENTNAME))
 (setq ENT2 (cdr (assoc -2 ENTLIST)))
 (while (/= ENT2 nil)
  (setq ENTLIST (entget ENT2))
  (if (and (= (strcase (cdr (assoc 8 ENTLIST))) "DEFPOINTS")
           (or (= (cdr (assoc 0 ENTLIST)) "POLYLINE")
               (= (cdr (assoc 0 ENTLIST)) "LWPOLYLINE")))
   (progn
    (if (= (cdr (assoc 0 ENTLIST)) "LWPOLYLINE")
     (progn
      (while (/= (setq NODE (car ENTLIST)) nil)
       (setq ENTLIST (cdr ENTLIST))
       (if (= 10 (car NODE))
        (setq VLIST (append VLIST (list (mapcar '(lambda (N) (* N BLOCKSCALE)) (cdr NODE)))))
       )
      )
     )
     (progn
      (setq ENT2 (entnext ENT2))
      (setq ENTLIST (entget ENT2))
      (while (= (cdr (assoc 0 ENTLIST)) "VERTEX")
       (setq P (cdr (assoc 10 ENTLIST)))
       (setq P (list (* BLOCKSCALE (car P)) (* BLOCKSCALE (cadr P))))
       (setq VLIST (append VLIST (list P)))
       (setq ENT2 (entnext ENT2))
       (setq ENTLIST (entget ENT2))
      )
     )
    )
    (setq ENT2 nil)
   )
   (if (/= nil ENT2) (setq ENT2 (entnext ENT2)))
  )
 )
 (setq VLIST VLIST)
)
;
;
;     Program written by Robert Livingston, 2015-11-13
;
;     QTGETPLIST returns a list of points for a selected polyline such that
;                the distance between each point is equally spaced, just
;                less than the STEP and ordered closest to P
;
;
(defun QT:GETPLIST (P STEP ENT / C CMAX ENTLIST ENTOBJ L P1 PLIST)
 (vl-load-com)
 (setq PLIST nil)
 (setq ENTLIST (entget ENT))
 (if (and (/= "POLYLINE" (cdr (assoc 0 ENTLIST)))
          (/= "LWPOLYLINE" (cdr (assoc 0 ENTLIST))))
  (progn
   (alert "!!!  Not a polyline  !!!")
   nil
  )
  (progn
   (setq ENTOBJ (vlax-ename->vla-object ENT))
   (setq L (vlax-get-property ENTOBJ "LENGTH"))
   (setq CMAX (fix (/ L STEP)))
   (setq C 0)
   (while (< C CMAX)
    (setq P1 (vlax-curve-getPointAtDist ENTOBJ (/ (* C L) CMAX)))
    (if (/= nil P1)
     (progn
      (setq P1 (list (car P1) (cadr P1)))
      (setq PLIST (append PLIST (list P1)))
     )
    )
    (setq C (1+ C))
   )
   (setq P1 (vlax-curve-getEndPoint ENTOBJ))
   (setq P1 (list (car P1) (cadr P1)))
   (setq PLIST (append PLIST (list P1)))
   (if (< (distance P (car PLIST)) (distance P (last PLIST)))
    PLIST
    (reverse PLIST)
   )
  )
 )
)

;
;
;     Program written by Robert Livingston, 2015-11-13
;
;     QT:GETTURNANG Dispalys the current wheel turn angle
;
;
(defun QT:GETTURNANG (C PLIST LOCKANG / ANG DIRECTION P0 P1 P2 PC R)
 (if (= C CMAX)
  (eval "*undefined*")
  (progn
   (if (= C 0)
    (setq P0 nil P1 (nth C PLIST) P2 (nth (+ C 1) PLIST))
    (if (= C CMAX)
     (setq P0 (nth (- C 1) PLIST) P1 (nth C PLIST) P2 nil)
     (progn
      (setq P0 (nth (- C 1) PLIST) P1 (nth C PLIST) P2 (nth (+ C 1) PLIST))
      (setq PC (QT:CIRCLE3P P0 P1 P2))
      (if (= PC nil)
       (setq P0 nil)
       (progn
        (setq R (cadr PC))
        (setq PC (car PC))
        (setq ANG (angle P1 PC))
        (if (> (sin (- (angle P2 PC) (angle P1 PC))) 0.0)
         (setq ANG (- ANG (/ pi 2.0)))
         (setq ANG (+ ANG (/ pi 2.0)))
        )
        (setq P2 (list (+ (car P1) (* R (cos ANG)))
                       (+ (cadr P1) (* R (sin ANG)))))
       )
      )
     )
    )
   )	
   (setq ANG (nth C (cadr (car QTVLIST))))
   (setq ANG (- ANG (angle P2 P1)))
   (while (< ANG 0.0)
    (setq ANG (+ ANG (* 2.0 pi)))
   )
   (while (>= ANG (* 2.0 pi))
    (setq ANG (- ANG (* 2.0 pi)))
   )
   (setq DIRECTION "Right")
   (if (> ANG pi)
    (progn
     (setq DIRECTION "Left")
     (setq ANG (- (* 2.0 pi) ANG))
    )
   )
   (if (and (= QT:LOCKANGWARNING nil) (/= LOCKANG 0.0))
    (if (> ANG (* LOCKANG (/ pi 180.0)))
     (progn
      (setq QT:LOCKANGWARNING T)
      (alert "Warning - Lock angle exceeded!")
     )
    )
   )
   (if (> ANG (* LOCKANG (/ pi 180.0)))
    (foreach NODE QTVLIST (redraw (last NODE) 3))
    (foreach NODE QTVLIST (redraw (last NODE) 1))
   )
   (strcat DIRECTION " " (angtos ANG 1 2))
  )
 )
)
;
;
;     Program written by Robert Livingston, 2015
;
;     QTMAKETEMPBLOCK creates a temporary block copied from the supplied entity using only its LINES ARCS CIRCLES POLYLINES and NESTED BLOCKS
;
;
(defun QT:MAKETEMPBLOCK (ENT / BLOCKANG BLOCKLAYER BLOCKNAME BLOCKP BLOCKSCALE ENT2 ENTLIST ENTLISTNODE ENTLISTNEW ENTNEW NODE TMP)
 (setq ENTLIST (entget ENT))
 (if (/= "INSERT" (cdr (assoc 0 ENTLIST)))
  (eval nil)
  (progn
   (setq BLOCKNAME (cdr (assoc 2 ENTLIST)))
   (setq BLOCKLAYER (cdr (assoc 8 ENTLIST)))
   (setq BLOCKP (cdr (assoc 10 ENTLIST)))
   (setq BLOCKSCALE (cdr (assoc 41 ENTLIST)))
   (setq BLOCKANG (cdr (assoc 50 ENTLIST)))
   (setq ENTLIST (tblsearch "BLOCK" BLOCKNAME))
   (setq ENT2 (cdr (assoc -2 ENTLIST)))
   (setq ENTLIST (entget ENT2))
   (setq ENTLISTNEW (list (list (cons 0 "BLOCK")
                                (cons 2 "*U")
                                (assoc 8 ENTLIST)
                                (cons 70 1)
                                (list 10 0.0 0.0 0.0)
                          )
                    )
   )
   (while (/= nil ENT2)
    (setq ENTLIST (entget ENT2))
    (setq ENTLISTNODE nil)
    (if (and (/= "DEFPOINTS" (strcase (cdr (assoc 8 ENTLIST))))
             (/= "ATTDEF" (cdr (assoc 0 ENTLIST)))
        )
     (cond ((= "ARC" (cdr (assoc 0 ENTLIST)))
            (foreach NODE ENTLIST
             (if (or (= 0 (car NODE))
                     (= 6 (car NODE))
                     (= 8 (car NODE))
                     (= 10 (car NODE))
                     (= 20 (car NODE))
                     (= 30 (car NODE))
                     (= 39 (car NODE))
                     (= 40 (car NODE))
                     (= 48 (car NODE))
                     (= 50 (car NODE))
                     (= 51 (car NODE))
                     (= 62 (car NODE))
                     (= 100 (car NODE))
                     (= 210 (car NODE))
                     (= 220 (car NODE))
                     (= 230 (car NODE))
                 )
              (setq ENTLISTNODE (append ENTLISTNODE (list NODE)))
             )
            )
           )
           ((= "INSERT" (cdr (assoc 0 ENTLIST)))
            (foreach NODE ENTLIST
             (if (or (= 0 (car NODE))
                     (= 2 (car NODE))
                     (= 6 (car NODE))
                     (= 8 (car NODE))
                     (= 10 (car NODE))
                     (= 20 (car NODE))
                     (= 30 (car NODE))
                     (= 40 (car NODE))
                     (= 41 (car NODE))
                     (= 42 (car NODE))
                     (= 43 (car NODE))
                     (= 44 (car NODE))
                     (= 45 (car NODE))
                     (= 48 (car NODE))
                     (= 50 (car NODE))
                     (= 62 (car NODE))
                     (= 70 (car NODE))
                     (= 71 (car NODE))
                     (= 100 (car NODE))
                     (= 210 (car NODE))
                     (= 220 (car NODE))
                     (= 230 (car NODE))
                 )
              (setq ENTLISTNODE (append ENTLISTNODE (list NODE)))
             )
            )
           )
           ((= "CIRCLE" (cdr (assoc 0 ENTLIST)))
            (foreach NODE ENTLIST
             (if (or (= 0 (car NODE))
                     (= 6 (car NODE))
                     (= 8 (car NODE))
                     (= 10 (car NODE))
                     (= 20 (car NODE))
                     (= 30 (car NODE))
                     (= 39 (car NODE))
                     (= 40 (car NODE))
                     (= 48 (car NODE))
                     (= 62 (car NODE))
                     (= 100 (car NODE))
                     (= 210 (car NODE))
                     (= 220 (car NODE))
                     (= 230 (car NODE))
                 )
              (setq ENTLISTNODE (append ENTLISTNODE (list NODE)))
             )
            )
           )
           ((= "LINE" (cdr (assoc 0 ENTLIST)))
            (foreach NODE ENTLIST
             (if (or (= 0 (car NODE))
                     (= 6 (car NODE))
                     (= 8 (car NODE))
                     (= 10 (car NODE))
                     (= 11 (car NODE))
                     (= 20 (car NODE))
                     (= 21 (car NODE))
                     (= 30 (car NODE))
                     (= 31 (car NODE))
                     (= 48 (car NODE))
                     (= 62 (car NODE))
                     (= 100 (car NODE))
                     (= 210 (car NODE))
                     (= 220 (car NODE))
                     (= 230 (car NODE))
                 )
              (setq ENTLISTNODE (append ENTLISTNODE (list NODE)))
             )
            )
           )
           ((= "LWPOLYLINE" (cdr (assoc 0 ENTLIST)))
            (foreach NODE ENTLIST
             (if (or (= 0 (car NODE))
                     (= 6 (car NODE))
                     (= 8 (car NODE))
                     (= 10 (car NODE))
                     (= 20 (car NODE))
                     (= 38 (car NODE))
                     (= 39 (car NODE))
                     (= 40 (car NODE))
                     (= 41 (car NODE))
                     (= 42 (car NODE))
                     (= 43 (car NODE))
                     (= 48 (car NODE))
                     (= 62 (car NODE))
                     (= 70 (car NODE))
                     (= 90 (car NODE))
                     (= 100 (car NODE))
                     (= 210 (car NODE))
                     (= 220 (car NODE))
                     (= 230 (car NODE))
                 )
              (setq ENTLISTNODE (append ENTLISTNODE (list NODE)))
             )
            )
           )
           ((= "POLYLINE" (cdr (assoc 0 ENTLIST)))
            (foreach NODE ENTLIST
             (if (or (= 0 (car NODE))
                     (= 6 (car NODE))
                     (= 8 (car NODE))
                     (= 10 (car NODE))
                     (= 20 (car NODE))
                     (= 30 (car NODE))
                     (= 39 (car NODE))
                     (= 40 (car NODE))
                     (= 41 (car NODE))
                     (= 48 (car NODE))
                     (= 62 (car NODE))
                     (= 70 (car NODE))
                     (= 71 (car NODE))
                     (= 72 (car NODE))
                     (= 73 (car NODE))
                     (= 74 (car NODE))
                     (= 75 (car NODE))
                     (= 100 (car NODE))
                     (= 210 (car NODE))
                     (= 220 (car NODE))
                     (= 230 (car NODE))
                 )
              (setq ENTLISTNODE (append ENTLISTNODE (list NODE)))
             )
            )
           )
           ((= "VERTEX" (cdr (assoc 0 ENTLIST)))
            (foreach NODE ENTLIST
             (if (or (= 0 (car NODE))
                     (= 6 (car NODE))
                     (= 8 (car NODE))
                     (= 10 (car NODE))
                     (= 20 (car NODE))
                     (= 30 (car NODE))
                     (= 40 (car NODE))
                     (= 41 (car NODE))
                     (= 42 (car NODE))
                     (= 48 (car NODE))
                     (= 50 (car NODE))
                     (= 62 (car NODE))
                     (= 70 (car NODE))
                     (= 71 (car NODE))
                     (= 72 (car NODE))
                     (= 73 (car NODE))
                     (= 74 (car NODE))
                     (= 100 (car NODE))
                 )
              (setq ENTLISTNODE (append ENTLISTNODE (list NODE)))
             )
            )
           )
           ((= "SEQEND" (cdr (assoc 0 ENTLIST)))
            (foreach NODE ENTLIST
             (if (or (= 0 (car NODE))
                 )
              (setq ENTLISTNODE (append ENTLISTNODE (list NODE)))
             )
            )
           )
           ((= "POINT" (cdr (assoc 0 ENTLIST)))
            (foreach NODE ENTLIST
             (if (or (= 0 (car NODE))
                     (= 6 (car NODE))
                     (= 8 (car NODE))
                     (= 10 (car NODE))
                     (= 20 (car NODE))
                     (= 30 (car NODE))
                     (= 39 (car NODE))
                     (= 48 (car NODE))
                     (= 50 (car NODE))
                     (= 62 (car NODE))
                     (= 100 (car NODE))
                     (= 220 (car NODE))
                     (= 230 (car NODE))
                 )
              (setq ENTLISTNODE (append ENTLISTNODE (list NODE)))
             )
            )
           )
     )
    )
    (if (/= nil ENTLISTNODE) (setq ENTLISTNEW (append ENTLISTNEW (list ENTLISTNODE))))
    (setq ENT2 (entnext ENT2))
   )
   (setq ENTLISTNEW (append ENTLISTNEW (list (list (cons 0 "ENDBLK")))))
   (entmake)
   (foreach NODE ENTLISTNEW
    (setq TMP (entmake NODE))
   )
   (if (= nil TMP)
    (eval nil)
    (progn
     (entmake (list (cons 0 "INSERT")
                    (cons 2 TMP)
                    (cons 8 BLOCKLAYER)
                    (cons 10 BLOCKP)
                    (cons 41 BLOCKSCALE)
                    (cons 42 BLOCKSCALE)
                    (cons 43 BLOCKSCALE)
                    (cons 50 BLOCKANG)
              )
     )
     (entlast)
    )
   )
  )
 )
)
;
;
;   Program written by Robert Livingston, 2016-05-16
;
;   QT:MOVEVEHICLE moves a vehicle to a position defined by grread
;
;
(defun QT:MOVEVEHICLE (PLIST / D P P0 PTMP)
 (setq D nil)
 (while (= 5 (car (setq P (grread T))))
  (setq P0 (cadr P))
  (setq D (apply 'min (mapcar '(lambda (PTMP) (distance P0 PTMP)) PLIST)))
  (setq C 0)
  (while (and (/= D (distance P0 (nth C PLIST)))
              (< C (length PLIST))
         )
   (setq C (1+ C))
  )
  (if (> C CMAX) (setq C CMAX))
  (QT:PLACE C)
  (QT:SETWHEELANG C QTVLIST PLIST)
 )
)
;
;
;   Program written by Robert Livingston, 2016-05-16
;
;   QT:NEWANG Calculates the new angle after a linear movement
;
;
(defun QT:NEWANG (ANG C PLIST L / ANG2 ANG3 FT SIGN TOL)
 (defun FT (C PLIST / D2 P1 P2 P3 R)
  (setq P1 (nth C PLIST))
  (setq P2 (nth (1- C) PLIST))
;  (setq D2 (/ (distance P1 P2) 2.0))
;  (cond ((< (1+ C) (length PLIST))
;         (setq P3 (nth (1+ C) PLIST))
;        )
;        ((> C 1)
;         (setq P3 (nth (- C 2) PLIST))
;        )
;        (T
;         (setq P3 nil)
;        )
;  )
;  (if (setq R (last (QT:CIRCLE3P P1 P2 P3)))
;   (* 2.0 R (atan (/ D2 (sqrt (- (* R R) (* D2 D2))))))
   (distance P1 P2)
;  )
 )
 (setq TOL 0.0000001)
 (setq P1 (nth C PLIST))
 (setq P2 (nth (1- C) PLIST))
 (setq ANG2 (- ANG (angle P1 P2)))
 (while (< ANG2 0.0)
  (setq ANG2 (+ ANG2 (* 2.0 pi)))
 )
 (while (>= ANG2 (* 2.0 pi))
  (setq ANG2 (- ANG2 (* 2.0 pi)))
 )
 (setq SIGN 1.0)
 (if (> ANG2 pi)
  (progn
   (setq SIGN -1.0)
   (setq ANG2 (- (* 2.0 pi) ANG2))
  )
 )
 (if (< ANG2 TOL)
  (setq ANG2 0.0)
  (setq ANG2 (* 2.0
                (atan (exp (- (log (TAN (/ ANG2 2.0)))
                              (/ (FT C PLIST) L)
                           )
                      )
                )
             )
  )
 )
 (setq ANG2 (+ (angle P1 P2) (* SIGN ANG2)))
 (while (< ANG2 0.0)
  (setq ANG2 (+ ANG2 (* 2.0 pi)))
 )
 (while (>= ANG2 (* 2.0 pi))
  (setq ANG2 (- ANG2 (* 2.0 pi)))
 )
 (eval ANG2)
)
;
;
;   Program written by Robert Livingston, 2016-05-16
;
;   QT:NEWWHEELANG Updates the wheel angle for NODE
;
;
(defun QT:NEWWHEELANG (NODE ANG / A ANG2 D D0 DG DH ENT ENT2 ENT3 ENTLIST LOCKANG P SCALE TAN TMP TOL WF WR X Y)
 (setq TOL 0.000001)
 (defun TAN (ANG)
  (/ (sin ANG) (cos ANG))
 )
 (setq ENT (last NODE))
 (setq ENTLIST (entget ENT))
 (if (= "INSERT" (cdr (assoc 0 ENTLIST)))
  (progn
   (setq SCALE (cdr (assoc 41 ENTLIST)))
   (setq ENTLIST (tblsearch "BLOCK" (cdr (assoc 2 ENTLIST))))
   (setq ENT2 (cdr (assoc -2 ENTLIST)))
   (while (/= nil ENT2)
    (setq ENTLIST (entget ENT2))
    (if (= "INSERT" (cdr (assoc 0 ENTLIST)))
     (progn
      (if (< (abs ANG) TOL)
       (setq ANG2 ANG)
       (progn
        (setq P (cdr (assoc 10 ENTLIST)))
        (setq X (* (car P) SCALE))
        (setq Y (* (cadr P) SCALE))
        (setq TMP (QT:GETD (car NODE)))
        (setq D0 (nth 0 TMP)
              DG (nth 1 TMP)
              D (nth 2 TMP)
              DH (nth 3 TMP)
              LOCKANG (nth 4 TMP)
              LB (nth 5 TMP)
              LA (nth 6 TMP)
              WF (nth 7 TMP)
              WR (nth 8 TMP)
        )
        (setq A (/ (- D D0) (TAN ANG)))
        (setq ANG2 (atan (/ (- D X) (+ A Y))))
       )
      )
      (setq ENTLIST (subst (cons 50 ANG2) (assoc 50 ENTLIST) ENTLIST))
      (entmod ENTLIST)
      (entupd ENT)
     )
    )
    (setq ENT2 (entnext ENT2))
   )
  )
 )
)
;
;
;   Program written by Robert Livingston, 2016-05-16
;
;   QT:PLACE updates a vehicle at posicion 'C'
;
;
(defun QT:PLACE (C / ANG ENT ENTLIST NODE P)
 (foreach NODE QTVLIST
  (progn
   (setq ENT (last NODE))
   (setq ANG (nth C (cadr NODE)))
   (setq P (nth C (caddr NODE)))
   (setq ENTLIST (entget ENT))
   (setq ENTLIST (subst (append (list 10) P) (assoc 10 ENTLIST) ENTLIST))
   (setq ENTLIST (subst (cons 50 ANG) (assoc 50 ENTLIST) ENTLIST))
   (entmod ENTLIST)
   (entupd ENT)
  )
 )
)
;
;
;   Program written by Robert Livingston, 2016-05-16
;
;   QT:SETPATH Calculates the point list for a vehicle along a path
;
;
(defun QT:SETPATH (PLIST ENTFIRST / ANG ANGLIST C ENT ENT2 ENTLIST NODE P P0 P0LIST PD PH PHLIST TMP WF WR)
 (setq QTVLIST nil)
 (setq QTDLIST nil)
 (setq LBLIST nil)
 (setq LALIST nil)
 (setq ENT ENTFIRST)
 (while (and (/= nil PLIST) (/= nil ENT))
  (redraw ENT 2)
  (setq ENTLIST (entget ENT))
  (setq D0 nil DG nil D nil DH nil LA nil LB nil)
  (setq TMP (QT:GETD ENT))
  (setq D0 (nth 0 TMP)
        DG (nth 1 TMP)
        D (nth 2 TMP)
        DH (nth 3 TMP)
        LOCKANG (nth 4 TMP)
        LB (nth 5 TMP)
        LA (nth 6 TMP)
        WF (nth 7 TMP)
        WR (nth 8 TMP)
  )
  (if (and (/= nil D0) (/= nil DG) (/= nil D) (/= nil DH))
   (progn
    (setq ANG nil ANGLIST nil P0LIST nil PHLIST nil)
    (setq P (car PLIST))
    (setq ANG (cdr (assoc 50 ENTLIST)))
    (setq ANGLIST (list ANG))
    (setq P0 (list (- (car P) (* D0 (cos ANG)))
                   (- (cadr P) (* D0 (sin ANG)))))
    (setq P0LIST (list P0))
    (if (> DH 0.0)
     (progn
      (setq PH (list (+ (car P) (* (- DH D0) (cos ANG)))
                     (+ (cadr P) (* (- DH D0) (sin ANG)))))
      (setq PHLIST (list PH))
     )
    )
    (if (/= nil LB)
     (setq LBLIST (list (list (+ (car P) (* (- LB D0) (cos ANG)))
                              (+ (cadr P) (* (- LB D0) (sin ANG))))))
    )
    (if (/= nil LA)
     (setq LALIST (list (list (+ (car P) (* (- LA D0) (cos ANG)))
                              (+ (cadr P) (* (- LA D0) (sin ANG))))))
    )
    (setq C 1)
    (while (< C (length PLIST))
     (setq P (nth C PLIST))
     (setq ANG (QT:NEWANG ANG C PLIST (- D D0)))
     (setq ANGLIST (append ANGLIST (list ANG)))
     (setq P0 (list (- (car P) (* D0 (cos ANG)))
                    (- (cadr P) (* D0 (sin ANG)))))
     (setq P0LIST (append P0LIST (list P0)))
     (if (> DH 0.0)
      (progn
       (setq PH (list (+ (car P) (* (- DH D0) (cos ANG)))
                      (+ (cadr P) (* (- DH D0) (sin ANG)))))
       (setq PHLIST (append PHLIST (list PH)))
      )
     )
     (if (/= nil LB)
      (progn
       (setq PLB (list (+ (car P) (* (- LB D0) (cos ANG)))
                       (+ (cadr P) (* (- LB D0) (sin ANG)))))
       (setq LBLIST (append LBLIST (list PLB)))
      )
     )
     (if (/= nil LA)
      (progn
       (setq PLA (list (+ (car P) (* (- LA D0) (cos ANG)))
                       (+ (cadr P) (* (- LA D0) (sin ANG)))))
       (setq LALIST (append LALIST (list PLA)))
      )
     )
     (setq C (+ C 1))
    )
    (setq ENT2 (QT:MAKETEMPBLOCK ENT))
    (redraw ENT2 2)
    (setq QTVLIST (append QTVLIST (list (list ENT ANGLIST P0LIST PHLIST ENT2))))
    (setq PLIST PHLIST)
   )
   (princ "\n!!! Problem retrieving vehicle data !!!")
  )
  (if (and (/= nil LBLIST) (/= nil LALIST))
   (progn
    (if (/= nil (setq ENT (car (entsel "\nSelect load vehicle (<return> for none) : "))))
     (progn
      (redraw ENT 2)
      (setq D0 nil DG nil D nil DH nil LA nil LB nil)
      (setq TMP (QT:GETD ENT))
      (setq D0 (nth 0 TMP)
            DG (nth 1 TMP)
            D (nth 2 TMP)
            DH (nth 3 TMP)
            LOCKANG (nth 4 TMP)
            LB (nth 5 TMP)
            LA (nth 6 TMP)
            WF (nth 7 TMP)
            WR (nth 8 TMP)
      )
      (if (and (/= nil LA) (/= nil LB))
       (progn
        (setq ANGLIST nil)
        (setq P0LIST nil)
        (setq C 0)
        (while (< C (length LBLIST))
         (if (< LA LB)
          (setq ANG (angle (nth C LALIST) (nth C LBLIST)))
          (setq ANG (angle (nth C LBLIST) (nth C LALIST)))
         )
         (setq ANGLIST (append ANGLIST (list ANG)))
         (setq P0 (list (- (car (nth C LBLIST)) (* LB (cos ANG)))
                        (- (cadr (nth C LBLIST)) (* LB (sin ANG)))))
         (setq P0LIST (append P0LIST (list P0)))
         (setq C (+ C 1))
        )
        (setq ENT2 (QT:MAKETEMPBLOCK ENT))
        (redraw ENT2 2)
        (setq QTVLIST (append QTVLIST (list (list ENT ANGLIST P0LIST nil ENT2))))
       )
      )
     )
    )
    (setq LBLIST nil)
    (setq LALIST nil)
   )
  )
  (if (= nil PLIST)
   (setq ENT nil)
   (setq ENT (car (entsel "\nSelect vehicle : ")))
  )
 )
 (foreach NODE QTVLIST (redraw (last NODE) 1))
)
;
;
;     Program written by Robert Livingston, 2015
;
;     QTSETWHEELANG updates the wheel angle of all the nested wheel blocks based on their position in a block to the turn angle of the block
;
;
(defun QT:SETWHEELANG (C QTVLIST PLIST / ANG DIRECTION NODE P0 P1 P2 PC R)
 (foreach NODE QTVLIST
  (if (or (= C CMAX) (= nil PLIST))
   (QT:NEWWHEELANG NODE 0.0)
   (progn
    (if (= C 0)
     (setq P0 nil P1 (nth C PLIST) P2 (nth (+ C 1) PLIST))
     (if (= C CMAX)
      (setq P0 (nth (- C 1) PLIST) P1 (nth C PLIST) P2 nil)
      (progn
       (setq P0 (nth (- C 1) PLIST) P1 (nth C PLIST) P2 (nth (+ C 1) PLIST))
       (setq PC (QT:CIRCLE3P P0 P1 P2))
       (if (= PC nil)
        (setq P0 nil)
        (progn
         (setq R (cadr PC))
         (setq PC (car PC))
         (setq ANG (angle P1 PC))
         (if (> (sin (- (angle P2 PC) (angle P1 PC))) 0.0)
          (setq ANG (- ANG (/ pi 2.0)))
          (setq ANG (+ ANG (/ pi 2.0)))
         )
         (setq P2 (list (+ (car P1) (* R (cos ANG)))
                        (+ (cadr P1) (* R (sin ANG)))))
        )
       )
      )
     )
    )	
    (setq ANG (nth C (cadr NODE)))
    (setq ANG (- ANG (angle P2 P1)))
    (while (< ANG 0.0)
     (setq ANG (+ ANG (* 2.0 pi)))
    )
    (while (>= ANG (* 2.0 pi))
     (setq ANG (- ANG (* 2.0 pi)))
    )
    (QT:NEWWHEELANG NODE (* -1.0 ANG))
    (setq PLIST (cadddr NODE))
   )
  )
 )
)
;
;
;   Program written by Robert Livingston, 2016-05-16
;
;   QT:TPATH Traces a user supplied position
;
;
(defun QT:TPATH (/ ANG DX DY N NODE P1 P2 REP)
 (setq N (getint (strcat "\nWhich vehicle (1 to " (itoa (length QTVLIST)) ", <return> to cancel) : ")))
 (if (/= nil N)
  (if (and (> N 0) (<= N (length QTVLIST)))
   (progn
    (setq NODE (nth (- N 1) QTVLIST))
    (setq ANG (nth C (cadr NODE)))
    (setq P2 (getpoint (setq P1 (nth C (caddr NODE))) "\nPick trace point : "))
    (if (/= P2 nil)
     (progn
      (setq DX (* (distance P1 P2) (cos (- (angle P1 P2) ANG))))
      (setq DY (* (distance P1 P2) (sin (- (angle P1 P2) ANG))))
      (setq N 0)
      (setvar "OSMODE" 0)
      (command "._PLINE")
      (while (< N CMAX)
       (setq ANG (nth N (cadr NODE)))
       (setq P1 (nth N (caddr NODE)))
       (setq P2 (list (+ (car P1)
                         (* DX (cos ANG))
                         (* -1.0 DY (sin ANG))
                      )
                      (+ (cadr P1)
                         (* DX (sin ANG))
                         (* DY (cos ANG))
                      )
                )
       )
       (command P2)
       (setq N (+ N 1))
      )
      (command "")
      (setvar "OSMODE" OSMODE)
     )
    )
   )
  )
 )
)
;
;
;   Program written by Robert Livingston, 2016-05-16
;
;   QT:TWHEELS Traces the position of the wheels
;              Note:  Command not implemented
;
;
(defun QT:TWHEELS (/ C CECOLOR COLOR D D0 DG DH DX DY LOCKANG LA LB NODE P1 P2 TRACEWHEEL TMP WF WR)
 (setq CECOLOR (getvar "CECOLOR"))
 (defun TRACEWHEEL (/ N)
  (setq N 0)
  (setvar "OSMODE" 0)
  (command "._PLINE")
  (while (< N CMAX)
   (setq ANG (nth N (cadr NODE)))
   (setq P1 (nth N (caddr NODE)))
   (setq P2 (list (+ (car P1)
                     (* DX (cos ANG))
                     (* -1.0 DY (sin ANG))
                  )
                  (+ (cadr P1)
                     (* DX (sin ANG))
                     (* DY (cos ANG))
                  )
            )
   )
   (command P2)
   (setq N (+ N 1))
  )
  (command "")
  (setvar "OSMODE" OSMODE)
 )
 (setq COLOR (getint "\nEnter colour for trace (0-256, 0=ByBlock, 256=ByLayer) <0> : "))
 (if (= nil COLOR) (setq COLOR 0))
 (if (or (< COLOR 0) (> COLOR 256)) (setq COLOR 0))
 (setvar "CECOLOR" (itoa COLOR))
 (setq C 0)
 (while (< C (length QTVLIST))
  (setq NODE (nth C QTVLIST))
  (setq TMP (QT:GETD (car NODE)))
  (setq D0 (nth 0 TMP)
        DG (nth 1 TMP)
        D (nth 2 TMP)
        DH (nth 3 TMP)
        LOCKANG (nth 4 TMP)
        LB (nth 5 TMP)
        LA (nth 6 TMP)
        WF (nth 7 TMP)
        WR (nth 8 TMP)
  )
  ; Front Left
  (if (/= nil WF)
   (progn
    (setq DX DG)
    (setq DY (* -0.5 WF))
    (TRACEWHEEL)
   )
  )
  ; Front Right
  (if (/= nil WF)
   (progn
    (setq DX DG)
    (setq DY (* 0.5 WF))
    (TRACEWHEEL)
   )
  )
  ; Rear Left
  (if (/= nil WR)
   (progn
    (setq DX D)
    (setq DY (* -0.5 WR))
    (TRACEWHEEL)
   )
  )
  ; Rear Right
  (if (/= nil WR)
   (progn
    (setq DX D)
    (setq DY (* 0.5 WR))
    (TRACEWHEEL)
   )
  )
  (setq C (+ C 1))
 )
 (setvar "CECOLOR" CECOLOR)
)
;
;
;   Program written by Robert Livingston, 2016-05-16
;
;   C:QUICKTURN main routine
;
;   QTWrapperEnd.lsp is the footer wrapper for C:QUICKTURN
;
;
 (setq ENT (entsel "\nSelect polyline path (<return> to insert vehicle) : "))
 (if (= nil ENT)
  (C:QTMAKE)
  (progn
   (setq P (cadr ENT))
   (setq ENT (car ENT))
   (setq ENTFIRST (car (entsel "\nSelect vehicle : ")))
   (setq D0 nil DG nil D nil DH nil LA nil LB nil)
   (setq TMP (QT:GETD ENTFIRST))
   (setq D0 (nth 0 TMP)
         DG (nth 1 TMP)
         D (nth 2 TMP)
         DH (nth 3 TMP)
         FIRSTLOCKANG (nth 4 TMP)
         LB (nth 5 TMP)
         LA (nth 6 TMP)
         WF (nth 7 TMP)
         WR (nth 8 TMP)
   )
   (setq STEP (/ (- D D0) 10.0))
   (setq PLIST (QT:GETPLIST P STEP ENT))
   (if (= nil PLIST)
    (princ "\nProblem getting vehicle path...")
    (progn
     (setq CMAX (- (length PLIST) 1))
     (QT:SETPATH PLIST ENTFIRST)
     (if (= nil LOCKANG) (setq LOCKANG 0.0))
     (setq REP "Forward")
     (setq C 0)
     (while (/= "Exit" REP)
      (QT:PLACE C)
      (initget "Forward Back Move Copy enVelope Step Trace Wheels Exit eXit")
      (QT:SETWHEELANG C QTVLIST PLIST)
      (setq REP2 (getkword (strcat "\nSA:" (QT:GETTURNANG C PLIST FIRSTLOCKANG) " - Forward/Back/Move/Copy/enVelope/Step/Trace/eXit <" REP "> : ")))
      (if (= REP2 nil) (setq REP2 REP))
      (if (or (= REP2 "Forward") (= REP2 "Back")) (setq REP REP2))
      (cond ((= REP2 "Forward")
             (setq C (+ C 1))
            )
            ((= REP2 "Back")
             (setq C (- C 1))
            )
            ((= REP2 "Move")
             (QT:MOVEVEHICLE PLIST)
            )
            ((= REP2 "Copy")
             (QT:COPY)
            )
            ((= REP2 "Step")
             (setq C (+ C (getint "\nEnter steps (+ve = forward, -ve = back) : ")))
            )
            ((= REP2 "Trace")
             (QT:TPATH)
            )
;            ((= REP2 "Wheels")
;             (QT:TWHEELS)
;            )
            ((= REP2 "enVelope")
             (QT:DRAWENVELOPE)
            )
            ((or (= REP2 "Exit") (= REP2 "eXit"))
             (progn
              (foreach NODE QTVLIST (redraw (car NODE) 1))
              (foreach NODE QTVLIST (entdel (last NODE)))
              (setq REP "Exit")
             )
            )
      )
      (if (> C CMAX) (setq C CMAX))
      (if (< C 0) (setq C 0))
     )
    )
   )
  )
 )
 (command "._UCS" "P")
 (setvar "CMDECHO" CMDECHO)
 (setvar "ANGBASE" ANGBASE)
 (setvar "ANGDIR" ANGDIR)
 (setvar "OSMODE" OSMODE)
);
;
;     Program written by Robert Livingston, 2015-04-13
;     Adapted from MAKEENT
;
;     C:QTMAKE is a utility to create QuickTurn Vehicle Blocks
;
;
(defun C:QTMAKE (/ DCL_ID ACCEPTQTMAKE ACTIVEDOC ACTIVESPACE ANGBASE ANGDIR ATTREQ BLOCKINDEX BLOCKLIST CANCELQTMAKE CONTINUEFLAG D D0 DG DH ENT ENTLIST ENTSET L LA LB P PBASE PLA PLB WF WR UPDATEBLOCK TMP)
 (command "._UNDO" "M")
 (setq CMDECHO (getvar "CMDECHO"))
 (setvar "CMDECHO" 0)
 (setq ANGBASE (getvar "ANGBASE"))
 (setvar "ANGBASE" 0)
 (setq ANGDIR (getvar "ANGDIR"))
 (setvar "ANGDIR" 0)
 (setq OSMODE (getvar "OSMODE"))
 (setq ATTREQ (getvar "ATTREQ"))
 (setvar "ATTREQ" 0)
 (vl-load-com)
  
 (defun ACCEPTQTMAKE (/ C ENT ENTLIST NODE P ORTHOMODE OSMODE)
  (done_dialog)
  (unload_dialog DCL_ID)
  (setq CONTINUEFLAG nil)
 )
 
 (defun CANCELQTMAKE ()
  (done_dialog)
  (unload_dialog DCL_ID)
  (setq CONTINUEFLAG nil)
  (setq BLOCKINDEX nil)
 )

 (defun UPDATEBLOCK ()
  (setq BLOCKINDEX (atoi (get_tile "BLOCKNAME")))
  (done_dialog)
  (unload_dialog DCL_ID)
 )

 (setq BLOCKLIST (list (list "TAC-1999-A-BUS" "*WheelLeftM2" "*WheelRightM2" "TAC-1999-A-BUS-FRONT" "TAC-1999-A-BUS-REAR")
                       (list "TAC-1999-ATD" "*WheelLeftM1" "*WheelRightM1" "TAC-1999-ATD-TRUCK" "TAC-1999-ATD-TRAILER1" "TAC-1999-ATD-PUP" "TAC-1999-ATD-TRAILER2")
                       (list "TAC-1999-B-12" "*WheelLeftM1" "*WheelRightM1" "TAC-1999-B-12")
                       (list "TAC-1999-BTD" "*WheelLeftM1" "*WheelRightM1" "TAC-1999-BTD-TRUCK" "TAC-1999-BTD-TRAILER1" "TAC-1999-BTD-TRAILER2")
                       (list "TAC-1999-HSU" "*WheelLeftM2" "*WheelRightM2" "TAC-1999-HSU")
                       (list "TAC-1999-I-BUS" "*WheelLeftM2" "*WheelRightM2" "TAC-1999-I-BUS")
                       (list "TAC-1999-LSU" "*WheelLeftM2" "*WheelRightM2" "TAC-1999-LSU")
                       (list "TAC-1999-MSU" "*WheelLeftM2" "*WheelRightM2" "TAC-1999-MSU")
                       (list "TAC-1999-P" "*WheelLeftM3" "*WheelRightM3" "TAC-1999-P")
                       (list "TAC-1999-WB-19" "*WheelLeftM1" "*WheelRightM1" "TAC-1999-WB-19-TRUCK" "TAC-1999-WB-19-TRAILER")
                       (list "TAC-1999-WB-20" "*WheelLeftM1" "*WheelRightM1" "TAC-1999-WB-20-TRUCK" "TAC-1999-WB-20-TRAILER")
                       (list "Special-19HeavyHaul" "*WheelLeftM2" "*WheelRightM2" "*WheelLeftM6" "*WheelRightM6" "Special-19HeavyHaul-Truck" "Special-19HeavyHaul-Pup1" "Special-19HeavyHaul-Pup2" "Special-19HeavyHaul-Trailer" "Special-19HeavyHaul-Pup3" "Special-19HeavyHaul-Pup4")
                       (list "BC_MOTI-WB-15" "*WheelLeftM1" "*WheelRightM1" "BC_MOTI-WB-15-TRUCK" "BC_MOTI-WB-15-TRAILER")
                       (list "BC_MOTI-LG3" "*WheelLeftM1" "*WheelRightM1" "BC_MOTI-LG3-TRUCK" "BC_MOTI-LG3-TRAILER1" "BC_MOTI-LG3-TRAILER2" "BC_MOTI-LG3-LOAD")
                       (list "BC_MOTI-LG5" "*WheelLeftM1" "*WheelRightM1" "BC_MOTI-LG5-TRUCK" "BC_MOTI-LG5-TRAILER1" "BC_MOTI-LG5-TRAILER2" "BC_MOTI-LG5-LOAD")
                       (list "BC_MOTI-TS7" "*WheelLeftM1" "*WheelRightM1" "BC_MOTI-TS7-TRUCK" "BC_MOTI-TS7-TRAILER")
                       (list "AB_INF-5Axle" "*WheelLeftM1" "*WheelRightM1" "AB_INF-5Axle-Truck" "AB_INF-5Axle-Trailer")
                       (list "AB_INF-ABus" "*WheelLeftM2" "*WheelRightM2" "AB_INF-ABus-Front" "AB_INF-ABus-Rear")
                       (list "AB_INF-BUS" "*WheelLeftM2" "*WheelRightM2" "AB_INF-BUS")
                       (list "AB_INF-HeavyHaul" "*WheelLeftM2" "*WheelRightM2" "*Wheel5" "AB_INF-HeavyHaul-Truck" "AB_INF-HeavyHaul-Pup1" "AB_INF-HeavyHaul-Pup2" "AB_INF-HeavyHaul-Trailer" "AB_INF-HeavyHaul-Pup3")
                       (list "AB_INF-I-BUS" "*WheelLeftM2" "*WheelRightM2" "AB_INF-I-BUS")
                       (list "AB_INF-LogHaul" "*WheelLeftM1" "*WheelRightM1" "AB_INF-LogHaul-Truck" "AB_INF-LogHaul-Trailer1" "AB_INF-LogHaul-Trailer2" "AB_INF-LogHaul-Load")
                       (list "AB_INF-P" "*WheelLeftM3" "*WheelRightM3" "AB_INF-P")
                       (list "AB_INF-Pt" "*WheelLeftM3" "*WheelRightM3" "AB_INF-P" "AB_INF-CAMPER")
                       (list "AB_INF-SU9" "*WheelLeftM2" "*WheelRightM2" "AB_INF-SU9")
                       (list "AB_INF-WB-12" "*WheelLeftM1" "*WheelRightM1" "AB_INF-WB-12-TRUCK" "AB_INF-WB-12-TRAILER")
                       (list "AB_INF-WB-15" "*WheelLeftM1" "*WheelRightM1" "AB_INF-WB-15-TRUCK" "AB_INF-WB-15-TRAILER")
                       (list "AB_INF-WB-17" "*WheelLeftM1" "*WheelRightM1" "AB_INF-WB-17-TRUCK" "AB_INF-WB-17-TRAILER")
                       (list "AB_INF-WB-21" "*WheelLeftM1" "*WheelRightM1" "AB_INF-WB-21-TRUCK" "AB_INF-WB-21-TRAILER")
                       (list "AB_INF-WB-23" "*WheelLeftM1" "*WheelRightM1" "AB_INF-WB-23-TRUCK" "AB_INF-WB-23-TRAILER1" "AB_INF-WB-23-TRAILER2")
                       (list "AB_INF-WB-28" "*WheelLeftM1" "*WheelRightM1" "AB_INF-WB-28-TRUCK" "AB_INF-WB-28-TRAILER1" "AB_INF-WB-28-PUP" "AB_INF-WB-28-TRAILER2")
                       (list "AB_INF-WB-33" "*WheelLeftM1" "*WheelRightM1" "AB_INF-WB-33-TRUCK" "AB_INF-WB-33-TRAILER1" "AB_INF-WB-33-PUP" "AB_INF-WB-33-TRAILER1" "AB_INF-WB-33-PUP" "AB_INF-WB-33-TRAILER2")
                       (list "AB_INF-WB-36" "*WheelLeftM1" "*WheelRightM1" "AB_INF-WB-36-TRUCK" "AB_INF-WB-36-TRAILER1" "AB_INF-WB-36-PUP" "AB_INF-WB-36-TRAILER2")
                       (list "AASHTO-2011-A-BUS" "*WheelLeft2" "*WheelRight2" "AASHTO-2011-A-BUS-FRONT" "AASHTO-2011-A-BUS-REAR")
                       (list "AASHTO-2011-BUS-40" "*WheelLeft2" "*WheelRight2" "AASHTO-2011-BUS-40")
                       (list "AASHTO-2011-BUS-45" "*WheelLeft2" "*WheelRight2" "AASHTO-2011-BUS-45")
                       (list "AASHTO-2011-CITY-BUS" "*WheelLeft2" "*WheelRight2" "AASHTO-2011-CITY-BUS")
                       (list "AASHTO-2011-P" "*WheelLeft4" "*WheelRight4" "AASHTO-2011-P")
                       (list "AASHTO-2011-PB" "*WheelLeft4" "*WheelRight4" "AASHTO-2011-P" "AASHTO-2011-B")
                       (list "AASHTO-2011-PT" "*WheelLeft4" "*WheelRight4" "AASHTO-2011-P" "AASHTO-2011-T")
                       (list "AASHTO-2011-MH" "*WheelLeft2" "*WheelRight2" "AASHTO-2011-MH")
                       (list "AASHTO-2011-MHB" "*WheelLeft2" "*WheelRight2" "AASHTO-2011-MH" "AASHTO-2011-B")
                       (list "AASHTO-2011-MHT" "*WheelLeft2" "*WheelRight2" "AASHTO-2011-MH" "AASHTO-2011-T")
                       (list "AASHTO-2011-S-BUS-36" "*WheelLeft2" "*WheelRight2" "AASHTO-2011-S-BUS-36")
                       (list "AASHTO-2011-S-BUS-40" "*WheelLeft2" "*WheelRight2" "AASHTO-2011-S-BUS-40")
                       (list "AASHTO-2011-SU-30" "*WheelLeft2" "*WheelRight2" "AASHTO-2011-SU-30")
                       (list "AASHTO-2011-SU-40" "*WheelLeft2" "*WheelRight2" "AASHTO-2011-SU-40")
                       (list "AASHTO-2011-WB-40" "*WheelLeft1" "*WheelRight1" "AASHTO-2011-WB-40-TRUCK" "AASHTO-2011-WB-40-TRAILER")
                       (list "AASHTO-2011-WB-62" "*WheelLeft1" "*WheelRight1" "AASHTO-2011-WB-62-TRUCK" "AASHTO-2011-WB-62-TRAILER")
                       (list "AASHTO-2011-WB-67" "*WheelLeft1" "*WheelRight1" "AASHTO-2011-WB-67-TRUCK" "AASHTO-2011-WB-67-TRAILER")
                       (list "AASHTO-2011-WB-67D" "*WheelLeft2" "*WheelRight2" "AASHTO-2011-WB-67D-TRUCK" "AASHTO-2011-WB-67D-TRAILER1" "AASHTO-2011-WB-67D-PUP" "AASHTO-2011-WB-67D-TRAILER2")
                       (list "AASHTO-2011-WB-92D" "*WheelLeft2" "*WheelRight2" "AASHTO-2011-WB-92D-TRUCK" "AASHTO-2011-WB-92D-TRAILER1" "AASHTO-2011-WB-92D-PUP" "AASHTO-2011-WB-92D-TRAILER2")
                       (list "AASHTO-2011-WB-100T" "*WheelLeft2" "*WheelRight2" "AASHTO-2011-WB-100T-TRUCK" "AASHTO-2011-WB-100T-TRAILER" "AASHTO-2011-WB-100T-PUP" "AASHTO-2011-WB-100T-TRAILER" "AASHTO-2011-WB-100T-PUP" "AASHTO-2011-WB-100T-TRAILER")
                       (list "AASHTO-2011-WB-109D" "*WheelLeft2" "*WheelRight2" "AASHTO-2011-WB-109D-TRUCK" "AASHTO-2011-WB-109D-TRAILER" "AASHTO-2011-WB-109D-PUP" "AASHTO-2011-WB-109D-TRAILER")
                 )
 )

 (setq BLOCKINDEX 0)
 (setq CONTINUEFLAG T)

 (while CONTINUEFLAG
  (if (= QTMAKEDCLNAME nil)
   (progn
    (setq QTMAKEDCLNAME (vl-filename-mktemp "rfl.dcl"))
    (QT:MAKEDCL QTMAKEDCLNAME "QTMAKE")
   )
   (if (= nil (findfile QTMAKEDCLNAME))
    (progn
     (setq QTMAKEDCLNAME (vl-filename-mktemp "rfl.dcl"))
     (QT:MAKEDCL QTMAKEDCLNAME "QTMAKE")
    )
   )
  )
  (setq DCL_ID (load_dialog QTMAKEDCLNAME))
  (if (not (new_dialog "QTMAKE" DCL_ID)) (exit))

  (start_list "BLOCKNAME")
  (foreach NODE BLOCKLIST
   (add_list (car NODE))
  )
  (end_list)

  (set_tile "BLOCKNAME" (itoa BLOCKINDEX))

  (setq QTMAKESLBNAME "quickturn.slb")
  (if (= nil (findfile QTMAKESLBNAME))
   (progn
    (setq QTMAKESLBNAME (vl-filename-mktemp "rfl.slb"))
    (QT:MAKESLB QTMAKESLBNAME)
   )
  )
  (start_image "IMAGE")
  (slide_image 0 0 (- (dimx_tile "IMAGE") 1)
                   (- (dimy_tile "IMAGE") 1)
                   (strcat QTMAKESLBNAME "(" (car (nth BLOCKINDEX BLOCKLIST)) ")")
  )
  (end_image)

  (action_tile "BLOCKNAME" "(UPDATEBLOCK)")
  (action_tile "OK" "(ACCEPTQTMAKE)")
  (action_tile "CANCEL" "(CANCELQTMAKE)")

  (start_dialog)
 )
 
 (if (/= nil BLOCKINDEX)
  (progn
   (if (= nil (cdr (nth BLOCKINDEX BLOCKLIST)))
    (QT:MAKE (car (nth BLOCKINDEX BLOCKLIST)))
    (foreach NODE (cdr (nth BLOCKINDEX BLOCKLIST))
     (if (= "*" (substr NODE 1 1))
      (if (= nil (tblsearch "BLOCK" (substr NODE 2))) (QT:MAKE (substr NODE 2)))
      (if (= nil (tblsearch "BLOCK" NODE)) (QT:MAKE NODE))
     )
    )
   )
   
   (setq ACTIVEDOC (vla-get-activedocument (vlax-get-acad-object)))
   (setq ACTIVESPC
         (vlax-get-property ACTIVEDOC
          (if (or (eq acmodelspace (vla-get-activespace ACTIVEDOC)) (eq :vlax-true (vla-get-mspace ACTIVEDOC)))
           'modelspace
           'paperspace
          )
         )
   )
   
   (setq PLA nil)
   (setq PLB nil)
   (setq PBASE (getpoint "\nSelect point to insert vehicle : "))
   (setvar "OSMODE" 0)
   (setq P PBASE)
   (setq ENTSET (ssadd))
   (setq LA nil LB nil)
   (foreach NODE (cdr (nth BLOCKINDEX BLOCKLIST))
    (if (/= "*" (substr NODE 1 1))
     (progn
;      (setq D nil D0 nil DG nil DH nil L nil LA nil LB nil WF nil WR nil)
      (setq D nil D0 nil DG nil DH nil L nil WF nil WR nil)
      (vla-insertblock ACTIVESPC
                       (vlax-3D-point P)
                       NODE
                       1.0
                       1.0
                       1.0
                       0.0
      )
      (setq ENT (entlast))
      (setq ENTLIST (entget ENT))
      (ssadd ENT ENTSET)
      (setq TMP (QT:GETD ENT))
      (setq D0 (nth 0 TMP)
            DG (nth 1 TMP)
            D (nth 2 TMP)
            DH (nth 3 TMP)
            LOCKANG (nth 4 TMP)
            LB (nth 5 TMP)
            LA (nth 6 TMP)
            WF (nth 7 TMP)
            WR (nth 8 TMP)
      )
      (if (and (= nil PLB) (/= nil LB))
       (progn
        (setq PLB (list (- (+ (car P) LB) D0) (cadr P) (caddr P)))
        (setq LB nil)
       )
      )
      (if (and (/= nil PLB) (/= nil LB))
       (progn
        (setq ENTLIST (subst (list 10 (- (car PLB) LB) (cadr PLB) (caddr PLB)) (assoc 10 ENTLIST) ENTLIST))
        (entmod ENTLIST)
        (setq PLB nil)
       )
      )
      (if (or (= nil LA) (= nil LB))
       (progn
        (setq P (cdr (assoc 10 ENTLIST)))
        (setq P (list (- (car P) D0) (cadr P) (caddr P)))
        (setq ENTLIST (subst (cons 10 P) (assoc 10 ENTLIST) ENTLIST))
        (entmod ENTLIST)
        (if (/= nil DH) (setq P (list (+ (car P) DH) (cadr P) (caddr P))))
       )
;       (progn
;       )
      )
     )
    )
   )
  )
 )
 
 (setvar "CMDECHO" CMDECHO)
 (setvar "ANGBASE" ANGBASE)
 (setvar "ANGDIR" ANGDIR)
 (setvar "OSMODE" OSMODE)
 (setvar "ATTREQ" ATTREQ)
 (eval nil)
)
;
;
;     Program written by Robert Livingston, 03-03-11
;
;     QT:MAKEDCL is a utility for writing temporary DCL files
;                2015-11-17 : Revised to be standalone for QTMAKE
;
;     DCL's included:
;                              QTMAKE.dcl
;
(defun QT:MAKEDCL (OUTFILENAME DCLNAME / OUTFILE)
 (cond ((= (strcase DCLNAME) "QTMAKE")
        (progn
         (setq OUTFILE (open OUTFILENAME "w"))
         (princ "QTMAKE : dialog {\n" OUTFILE)
         (princ "                  label = \"QuickTurn Vehicle Block Creator\";\n" OUTFILE)
         (princ "                  : row {\n" OUTFILE)
         (princ "                          : column {\n" OUTFILE)
         (princ "                                     width = 40;\n" OUTFILE)
         (princ "                                     : list_box {\n" OUTFILE)
         (princ "                                                  key = \"BLOCKNAME\";\n" OUTFILE)
         (princ "                                                }\n" OUTFILE)
         (princ "                                   }\n" OUTFILE)
         (princ "                          : column {\n" OUTFILE)
         (princ "                                     : image {\n" OUTFILE)
         (princ "                                               key = \"IMAGE\";\n" OUTFILE)
         (princ "                                               width = 40;\n" OUTFILE)
         (princ "                                               height = 18;\n" OUTFILE)
         (princ "                                               color = 0;\n" OUTFILE)
         (princ "                                             }\n" OUTFILE)
         (princ "                                   }\n" OUTFILE)
         (princ "                        }\n" OUTFILE)
         (princ "                  : row {\n" OUTFILE)
         (princ "                          : ok_button {\n" OUTFILE)
         (princ "                                        label = \"OK\";\n" OUTFILE)
         (princ "                                        key = \"OK\";\n" OUTFILE)
         (princ "                                        is_default = true;\n" OUTFILE)
         (princ "                                      }\n" OUTFILE)
         (princ "                          : cancel_button {\n" OUTFILE)
         (princ "                                            label = \"Cancel\";\n" OUTFILE)
         (princ "                                            key = \"CANCEL\";\n" OUTFILE)
         (princ "                                          }\n" OUTFILE)
         (princ "                        }\n" OUTFILE)
         (princ "                }\n" OUTFILE)
         (close OUTFILE)
        )
       )
       ((= (strcase DCLNAME) "PROTOTYPE")
        (progn
         (setq OUTFILE (open OUTFILENAME "w"))



         (close OUTFILE)
        )
       )
       (T
        (progn
         (alert "!!! DCL DOES NOT EXIST !!!")
        )
       )
 )
)(defun QT:MAKE (BLKNAME / )
 (cond
       ((= (strcase BLKNAME) (strcase "AB_INF-WB-21-TRUCK"))
        (progn
         (entmake)
         (entmake
          (list
           (cons 0 "BLOCK")
           (cons 2 "AB_INF-WB-21-TRUCK")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 8.75 -1.3)
           (cons 40 0)
           (cons 41 0)
           (cons 42 0)
           (cons 91 0)
           (list 10 8.75 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.2 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.2 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.75 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.75 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.2 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.2 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 8.1 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 8.36263966 -0.26263966 0)
           (list 11 8.36263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.8912 -0.7445528)
           (cons 40 0)
           (cons 41 0)
           (cons 42 0)
           (cons 91 0)
           (list 10 6.8912 -0.5702072)
           (cons 40 0)
           (cons 41 0)
           (cons 42 0)
           (cons 91 0)
           (list 10 7.047664 -0.51768)
           (cons 40 0)
           (cons 41 0)
           (cons 42 0)
           (cons 91 0)
           (list 10 7.852336 -0.51768)
           (cons 40 0)
           (cons 41 0)
           (cons 42 0)
           (cons 91 0)
           (list 10 8.0088 -0.5702072)
           (cons 40 0)
           (cons 41 0)
           (cons 42 0)
           (cons 91 0)
           (list 10 8.0088 -0.7445528)
           (cons 40 0)
           (cons 41 0)
           (cons 42 0)
           (cons 91 0)
           (list 10 7.852336 -0.79708)
           (cons 40 0)
           (cons 41 0)
           (cons 42 0)
           (cons 91 0)
           (list 10 7.047664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.8912 -1.2474728)
           (cons 40 0)
           (cons 41 0)
           (cons 42 0)
           (cons 91 0)
           (list 10 6.8912 -1.0731272)
           (cons 40 0)
           (cons 41 0)
           (cons 42 0)
           (cons 91 0)
           (list 10 7.047664 -1.0206)
           (cons 40 0)
           (cons 41 0)
           (cons 42 0)
           (cons 91 0)
           (list 10 7.852336 -1.0206)
           (cons 40 0)
           (cons 41 0)
           (cons 42 0)
           (cons 91 0)
           (list 10 8.0088 -1.0731272)
           (cons 40 0)
           (cons 41 0)
           (cons 42 0)
           (cons 91 0)
           (list 10 8.0088 -1.2474728)
           (cons 40 0)
           (cons 41 0)
           (cons 42 0)
           (cons 91 0)
           (list 10 7.852336 -1.3)
           (cons 40 0)
           (cons 41 0)
           (cons 42 0)
           (cons 91 0)
           (list 10 7.047664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.8912 0.5702072)
           (cons 40 0)
           (cons 41 0)
           (cons 42 0)
           (cons 91 0)
           (list 10 6.8912 0.7445528)
           (cons 40 0)
           (cons 41 0)
           (cons 42 0)
           (cons 91 0)
           (list 10 7.047664 0.79708)
           (cons 40 0)
           (cons 41 0)
           (cons 42 0)
           (cons 91 0)
           (list 10 7.852336 0.79708)
           (cons 40 0)
           (cons 41 0)
           (cons 42 0)
           (cons 91 0)
           (list 10 8.0088 0.7445528)
           (cons 40 0)
           (cons 41 0)
           (cons 42 0)
           (cons 91 0)
           (list 10 8.0088 0.5702072)
           (cons 40 0)
           (cons 41 0)
           (cons 42 0)
           (cons 91 0)
           (list 10 7.852336 0.51768)
           (cons 40 0)
           (cons 41 0)
           (cons 42 0)
           (cons 91 0)
           (list 10 7.047664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.8912 1.0731272)
           (cons 40 0)
           (cons 41 0)
           (cons 42 0)
           (cons 91 0)
           (list 10 6.8912 1.2474728)
           (cons 40 0)
           (cons 41 0)
           (cons 42 0)
           (cons 91 0)
           (list 10 7.047664 1.3)
           (cons 40 0)
           (cons 41 0)
           (cons 42 0)
           (cons 91 0)
           (list 10 7.852336 1.3)
           (cons 40 0)
           (cons 41 0)
           (cons 42 0)
           (cons 91 0)
           (list 10 8.0088 1.2474728)
           (cons 40 0)
           (cons 41 0)
           (cons 42 0)
           (cons 91 0)
           (list 10 8.0088 1.0731272)
           (cons 40 0)
           (cons 41 0)
           (cons 42 0)
           (cons 91 0)
           (list 10 7.852336 1.0206)
           (cons 40 0)
           (cons 41 0)
           (cons 42 0)
           (cons 91 0)
           (list 10 7.047664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.1912 -0.7445528)
           (cons 40 0)
           (cons 41 0)
           (cons 42 0)
           (cons 91 0)
           (list 10 8.1912 -0.5702072)
           (cons 40 0)
           (cons 41 0)
           (cons 42 0)
           (cons 91 0)
           (list 10 8.347664 -0.51768)
           (cons 40 0)
           (cons 41 0)
           (cons 42 0)
           (cons 91 0)
           (list 10 9.152336 -0.51768)
           (cons 40 0)
           (cons 41 0)
           (cons 42 0)
           (cons 91 0)
           (list 10 9.3088 -0.5702072)
           (cons 40 0)
           (cons 41 0)
           (cons 42 0)
           (cons 91 0)
           (list 10 9.3088 -0.7445528)
           (cons 40 0)
           (cons 41 0)
           (cons 42 0)
           (cons 91 0)
           (list 10 9.152336 -0.79708)
           (cons 40 0)
           (cons 41 0)
           (cons 42 0)
           (cons 91 0)
           (list 10 8.347664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.1912 -1.2474728)
           (cons 40 0)
           (cons 41 0)
           (cons 42 0)
           (cons 91 0)
           (list 10 8.1912 -1.0731272)
           (cons 40 0)
           (cons 41 0)
           (cons 42 0)
           (cons 91 0)
           (list 10 8.347664 -1.0206)
           (cons 40 0)
           (cons 41 0)
           (cons 42 0)
           (cons 91 0)
           (list 10 9.152336 -1.0206)
           (cons 40 0)
           (cons 41 0)
           (cons 42 0)
           (cons 91 0)
           (list 10 9.3088 -1.0731272)
           (cons 40 0)
           (cons 41 0)
           (cons 42 0)
           (cons 91 0)
           (list 10 9.3088 -1.2474728)
           (cons 40 0)
           (cons 41 0)
           (cons 42 0)
           (cons 91 0)
           (list 10 9.152336 -1.3)
           (cons 40 0)
           (cons 41 0)
           (cons 42 0)
           (cons 91 0)
           (list 10 8.347664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.1912 0.5702072)
           (cons 40 0)
           (cons 41 0)
           (cons 42 0)
           (cons 91 0)
           (list 10 8.1912 0.7445528)
           (cons 40 0)
           (cons 41 0)
           (cons 42 0)
           (cons 91 0)
           (list 10 8.347664 0.79708)
           (cons 40 0)
           (cons 41 0)
           (cons 42 0)
           (cons 91 0)
           (list 10 9.152336 0.79708)
           (cons 40 0)
           (cons 41 0)
           (cons 42 0)
           (cons 91 0)
           (list 10 9.3088 0.7445528)
           (cons 40 0)
           (cons 41 0)
           (cons 42 0)
           (cons 91 0)
           (list 10 9.3088 0.5702072)
           (cons 40 0)
           (cons 41 0)
           (cons 42 0)
           (cons 91 0)
           (list 10 9.152336 0.51768)
           (cons 40 0)
           (cons 41 0)
           (cons 42 0)
           (cons 91 0)
           (list 10 8.347664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.1912 1.0731272)
           (cons 40 0)
           (cons 41 0)
           (cons 42 0)
           (cons 91 0)
           (list 10 8.1912 1.2474728)
           (cons 40 0)
           (cons 41 0)
           (cons 42 0)
           (cons 91 0)
           (list 10 8.347664 1.3)
           (cons 40 0)
           (cons 41 0)
           (cons 42 0)
           (cons 91 0)
           (list 10 9.152336 1.3)
           (cons 40 0)
           (cons 41 0)
           (cons 42 0)
           (cons 91 0)
           (list 10 9.3088 1.2474728)
           (cons 40 0)
           (cons 41 0)
           (cons 42 0)
           (cons 91 0)
           (list 10 9.3088 1.0731272)
           (cons 40 0)
           (cons 41 0)
           (cons 42 0)
           (cons 91 0)
           (list 10 9.152336 1.0206)
           (cons 40 0)
           (cons 41 0)
           (cons 42 0)
           (cons 91 0)
           (list 10 8.347664 1.0206)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelRightM1")
           (list 10 1.9 1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM1")
           (list 10 1.9 -1.0206 0)
           (cons 41 1)
           (cons 42 1)
           (cons 43 1)
           (cons 50 0)
           (cons 70 0)
           (cons 71 0)
           (cons 44 0)
           (cons 45 0)
          )
         )
         (entmake
          (list
           (cons 0 "POINT")
           (cons 100 "AcDbEntity")
           (cons 67 0)
           (cons 8 "0")
           (cons 100 "AcDbPoint")
           (list 10 1.9 -1.3 0)
           (cons 50 0)
          )
         )
         (entmake
          (list
           (cons 0 "POINT")
           (cons 100 "AcDbEntity")
           (cons 67 0)
           (cons 8 "0")
           (cons 100 "AcDbPoint")
           (list 10 1.9 1.3 0)
           (cons 50 0)
          )
         )
         (entmake
          (list
           (cons 0 "POINT")
           (cons 100 "AcDbEntity")
           (cons 67 0)
           (cons 8 "0")
           (cons 100 "AcDbPoint")
           (list 10 1.9 0 0)
           (cons 50 0)
          )
         )
         (entmake
          (list
           (cons 0 "POINT")
           (cons 100 "AcDbEntity")
           (cons 67 0)
           (cons 8 "0")
           (cons 100 "AcDbPoint")
           (list 10 8.1 1.3 0)
           (cons 50 0)
          )
         )
         (entmake
          (list
           (cons 0 "POINT")
           (cons 100 "AcDbEntity")
           (cons 67 0)
           (cons 8 "0")
           (cons 100 "AcDbPoint")
           (list 10 8.1 0 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 8.1 -1.3 0)
           (cons 50 0)
          )
         )
         (entmake
          (list
           (cons 0 "ATTDEF")
           (cons 100 "AcDbEntity")
           (cons 67 0)
           (cons 8 "0")
           (cons 100 "AcDbText")
           (list 10 1.2 0.56666667 0)
           (cons 40 0.2)
           (cons 1 "1.900")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.2 0.23333333 0)
           (cons 40 0.2)
           (cons 1 "1.900")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.2 -0.1 0)
           (cons 40 0.2)
           (cons 1 "8.100")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.2 -0.43333333 0)
           (cons 40 0.2)
           (cons 1 "8.100")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.2 -0.76666667 0)
           (cons 40 0.2)
           (cons 1 "26.64")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "BC_MOTI-TS7-Trailer"))
        (progn
         (entmake)
         (entmake
          (list
           (cons 0 "BLOCK")
           (cons 2 "BC_MOTI-TS7-Trailer")
           (cons 70 2)
           (cons 4 "")
           (list 10 0 0 0)
          )
         )
         (entmake
          (list
           (cons 0 "LWPOLYLINE")
           (cons 100 "AcDbEntity")
           (cons 67 0)
           (cons 8 "Defpoints")
           (cons 6 "Continuous")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 17.25 -1.3)
           (cons 40 0)
           (cons 41 0)
           (cons 42 0)
           (cons 91 0)
           (list 10 17.25 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 17.25 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 17.25 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.4912 -0.7445528)
           (cons 40 0)
           (cons 41 0)
           (cons 42 0)
           (cons 91 0)
           (list 10 13.4912 -0.5702072)
           (cons 40 0)
           (cons 41 0)
           (cons 42 0)
           (cons 91 0)
           (list 10 13.647664 -0.51768)
           (cons 40 0)
           (cons 41 0)
           (cons 42 0)
           (cons 91 0)
           (list 10 14.452336 -0.51768)
           (cons 40 0)
           (cons 41 0)
           (cons 42 0)
           (cons 91 0)
           (list 10 14.6088 -0.5702072)
           (cons 40 0)
           (cons 41 0)
           (cons 42 0)
           (cons 91 0)
           (list 10 14.6088 -0.7445528)
           (cons 40 0)
           (cons 41 0)
           (cons 42 0)
           (cons 91 0)
           (list 10 14.452336 -0.79708)
           (cons 40 0)
           (cons 41 0)
           (cons 42 0)
           (cons 91 0)
           (list 10 13.647664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.4912 -1.2474728)
           (cons 40 0)
           (cons 41 0)
           (cons 42 0)
           (cons 91 0)
           (list 10 13.4912 -1.0731272)
           (cons 40 0)
           (cons 41 0)
           (cons 42 0)
           (cons 91 0)
           (list 10 13.647664 -1.0206)
           (cons 40 0)
           (cons 41 0)
           (cons 42 0)
           (cons 91 0)
           (list 10 14.452336 -1.0206)
           (cons 40 0)
           (cons 41 0)
           (cons 42 0)
           (cons 91 0)
           (list 10 14.6088 -1.0731272)
           (cons 40 0)
           (cons 41 0)
           (cons 42 0)
           (cons 91 0)
           (list 10 14.6088 -1.2474728)
           (cons 40 0)
           (cons 41 0)
           (cons 42 0)
           (cons 91 0)
           (list 10 14.452336 -1.3)
           (cons 40 0)
           (cons 41 0)
           (cons 42 0)
           (cons 91 0)
           (list 10 13.647664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.4912 0.5702072)
           (cons 40 0)
           (cons 41 0)
           (cons 42 0)
           (cons 91 0)
           (list 10 13.4912 0.7445528)
           (cons 40 0)
           (cons 41 0)
           (cons 42 0)
           (cons 91 0)
           (list 10 13.647664 0.79708)
           (cons 40 0)
           (cons 41 0)
           (cons 42 0)
           (cons 91 0)
           (list 10 14.452336 0.79708)
           (cons 40 0)
           (cons 41 0)
           (cons 42 0)
           (cons 91 0)
           (list 10 14.6088 0.7445528)
           (cons 40 0)
           (cons 41 0)
           (cons 42 0)
           (cons 91 0)
           (list 10 14.6088 0.5702072)
           (cons 40 0)
           (cons 41 0)
           (cons 42 0)
           (cons 91 0)
           (list 10 14.452336 0.51768)
           (cons 40 0)
           (cons 41 0)
           (cons 42 0)
           (cons 91 0)
           (list 10 13.647664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.4912 1.0731272)
           (cons 40 0)
           (cons 41 0)
           (cons 42 0)
           (cons 91 0)
           (list 10 13.4912 1.2474728)
           (cons 40 0)
           (cons 41 0)
           (cons 42 0)
           (cons 91 0)
           (list 10 13.647664 1.3)
           (cons 40 0)
           (cons 41 0)
           (cons 42 0)
           (cons 91 0)
           (list 10 14.452336 1.3)
           (cons 40 0)
           (cons 41 0)
           (cons 42 0)
           (cons 91 0)
           (list 10 14.6088 1.2474728)
           (cons 40 0)
           (cons 41 0)
           (cons 42 0)
           (cons 91 0)
           (list 10 14.6088 1.0731272)
           (cons 40 0)
           (cons 41 0)
           (cons 42 0)
           (cons 91 0)
           (list 10 14.452336 1.0206)
           (cons 40 0)
           (cons 41 0)
           (cons 42 0)
           (cons 91 0)
           (list 10 13.647664 1.0206)
           (cons 40 0)
           (cons 41 0)
           (cons 42 0)
           (cons 91 0)
          )
         )
         (entmake
          (list
           (cons 0 "POINT")
           (cons 100 "AcDbEntity")
           (cons 67 0)
           (cons 8 "0")
           (cons 6 "Continuous")
           (cons 100 "AcDbPoint")
           (list 10 14.05 1.3 0)
           (cons 50 0)
          )
         )
         (entmake
          (list
           (cons 0 "POINT")
           (cons 100 "AcDbEntity")
           (cons 67 0)
           (cons 8 "0")
           (cons 6 "Continuous")
           (cons 100 "AcDbPoint")
           (list 10 14.05 -1.3 0)
           (cons 50 0)
          )
         )
         (entmake
          (list
           (cons 0 "POINT")
           (cons 100 "AcDbEntity")
           (cons 67 0)
           (cons 8 "0")
           (cons 6 "Continuous")
           (cons 100 "AcDbPoint")
           (list 10 17.25 -1.3 0)
           (cons 50 0)
          )
         )
         (entmake
          (list
           (cons 0 "POINT")
           (cons 100 "AcDbEntity")
           (cons 67 0)
           (cons 8 "0")
           (cons 6 "Continuous")
           (cons 100 "AcDbPoint")
           (list 10 17.25 1.3 0)
           (cons 50 0)
          )
         )
         (entmake
          (list
           (cons 0 "POINT")
           (cons 100 "AcDbEntity")
           (cons 67 0)
           (cons 8 "0")
           (cons 6 "Continuous")
           (cons 100 "AcDbPoint")
           (list 10 0 -1.3 0)
           (cons 50 0)
          )
         )
         (entmake
          (list
           (cons 0 "POINT")
           (cons 100 "AcDbEntity")
           (cons 67 0)
           (cons 8 "0")
           (cons 6 "Continuous")
           (cons 100 "AcDbPoint")
           (list 10 0 1.3 0)
           (cons 50 0)
          )
         )
         (entmake
          (list
           (cons 0 "POINT")
           (cons 100 "AcDbEntity")
           (cons 67 0)
           (cons 8 "0")
           (cons 6 "Continuous")
           (cons 100 "AcDbPoint")
           (list 10 1.55 0 0)
           (cons 50 0)
          )
         )
         (entmake
          (list
           (cons 0 "ATTDEF")
           (cons 100 "AcDbEntity")
           (cons 67 0)
           (cons 8 "0")
           (cons 6 "Continuous")
           (cons 100 "AcDbText")
           (list 10 0.85 0.56666667 0)
           (cons 40 0.2)
           (cons 1 "1.550")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 6 "Continuous")
           (cons 100 "AcDbText")
           (list 10 0.85 0.23333333 0)
           (cons 40 0.2)
           (cons 1 "1.550")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 6 "Continuous")
           (cons 100 "AcDbText")
           (list 10 0.85 -0.1 0)
           (cons 40 0.2)
           (cons 1 "14.050")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 6 "Continuous")
           (cons 100 "AcDbText")
           (list 10 0.85 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 6 "Continuous")
           (cons 100 "AcDbText")
           (list 10 0.85 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "BC_MOTI-TS7-Truck"))
        (progn
         (entmake)
         (entmake
          (list
           (cons 0 "BLOCK")
           (cons 2 "BC_MOTI-TS7-Truck")
           (cons 70 2)
           (cons 4 "")
           (list 10 0 0 0)
          )
         )
         (entmake
          (list
           (cons 0 "POINT")
           (cons 100 "AcDbEntity")
           (cons 67 0)
           (cons 8 "0")
           (cons 6 "Continuous")
           (cons 100 "AcDbPoint")
           (list 10 0 1.3 0)
           (cons 50 0)
          )
         )
         (entmake
          (list
           (cons 0 "POINT")
           (cons 100 "AcDbEntity")
           (cons 67 0)
           (cons 8 "0")
           (cons 6 "Continuous")
           (cons 100 "AcDbPoint")
           (list 10 0 -1.3 0)
           (cons 50 0)
          )
         )
         (entmake
          (list
           (cons 0 "POINT")
           (cons 100 "AcDbEntity")
           (cons 67 0)
           (cons 8 "0")
           (cons 6 "Continuous")
           (cons 100 "AcDbPoint")
           (list 10 7.9 -1.3 0)
           (cons 50 0)
          )
         )
         (entmake
          (list
           (cons 0 "POINT")
           (cons 100 "AcDbEntity")
           (cons 67 0)
           (cons 8 "0")
           (cons 6 "Continuous")
           (cons 100 "AcDbPoint")
           (list 10 7.9 1.3 0)
           (cons 50 0)
          )
         )
         (entmake
          (list
           (cons 0 "POINT")
           (cons 100 "AcDbEntity")
           (cons 67 0)
           (cons 8 "0")
           (cons 6 "Continuous")
           (cons 100 "AcDbPoint")
           (list 10 1.1 -1.3 0)
           (cons 50 0)
          )
         )
         (entmake
          (list
           (cons 0 "POINT")
           (cons 100 "AcDbEntity")
           (cons 67 0)
           (cons 8 "0")
           (cons 6 "Continuous")
           (cons 100 "AcDbPoint")
           (list 10 1.1 1.3 0)
           (cons 50 0)
          )
         )
         (entmake
          (list
           (cons 0 "POINT")
           (cons 100 "AcDbEntity")
           (cons 67 0)
           (cons 8 "0")
           (cons 6 "Continuous")
           (cons 100 "AcDbPoint")
           (list 10 1.1 0 0)
           (cons 50 0)
          )
         )
         (entmake
          (list
           (cons 0 "INSERT")
           (cons 100 "AcDbEntity")
           (cons 67 0)
           (cons 8 "0")
           (cons 6 "Continuous")
           (cons 100 "AcDbBlockReference")
           (cons 2 "WheelLeftM1")
           (list 10 1.1 -1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 6 "Continuous")
           (cons 100 "AcDbBlockReference")
           (cons 2 "WheelRightM1")
           (list 10 1.1 1.0206 0)
           (cons 41 1)
           (cons 42 1)
           (cons 43 1)
           (cons 50 0)
           (cons 70 0)
           (cons 71 0)
           (cons 44 0)
           (cons 45 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.341 1.073452)
           (cons 40 0)
           (cons 41 0)
           (cons 42 0)
           (cons 91 0)
           (list 10 7.341 1.247548)
           (cons 40 0)
           (cons 41 0)
           (cons 42 0)
           (cons 91 0)
           (list 10 7.49752 1.3)
           (cons 40 0)
           (cons 41 0)
           (cons 42 0)
           (cons 91 0)
           (list 10 8.30248 1.3)
           (cons 40 0)
           (cons 41 0)
           (cons 42 0)
           (cons 91 0)
           (list 10 8.459 1.247548)
           (cons 40 0)
           (cons 41 0)
           (cons 42 0)
           (cons 91 0)
           (list 10 8.459 1.073452)
           (cons 40 0)
           (cons 41 0)
           (cons 42 0)
           (cons 91 0)
           (list 10 8.30248 1.021)
           (cons 40 0)
           (cons 41 0)
           (cons 42 0)
           (cons 91 0)
           (list 10 7.49752 1.021)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.341 0.570452)
           (cons 40 0)
           (cons 41 0)
           (cons 42 0)
           (cons 91 0)
           (list 10 7.341 0.744548)
           (cons 40 0)
           (cons 41 0)
           (cons 42 0)
           (cons 91 0)
           (list 10 7.49752 0.797)
           (cons 40 0)
           (cons 41 0)
           (cons 42 0)
           (cons 91 0)
           (list 10 8.30248 0.797)
           (cons 40 0)
           (cons 41 0)
           (cons 42 0)
           (cons 91 0)
           (list 10 8.459 0.744548)
           (cons 40 0)
           (cons 41 0)
           (cons 42 0)
           (cons 91 0)
           (list 10 8.459 0.570452)
           (cons 40 0)
           (cons 41 0)
           (cons 42 0)
           (cons 91 0)
           (list 10 8.30248 0.518)
           (cons 40 0)
           (cons 41 0)
           (cons 42 0)
           (cons 91 0)
           (list 10 7.49752 0.518)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.341 -0.744548)
           (cons 40 0)
           (cons 41 0)
           (cons 42 0)
           (cons 91 0)
           (list 10 7.341 -0.570452)
           (cons 40 0)
           (cons 41 0)
           (cons 42 0)
           (cons 91 0)
           (list 10 7.49752 -0.518)
           (cons 40 0)
           (cons 41 0)
           (cons 42 0)
           (cons 91 0)
           (list 10 8.30248 -0.518)
           (cons 40 0)
           (cons 41 0)
           (cons 42 0)
           (cons 91 0)
           (list 10 8.459 -0.570452)
           (cons 40 0)
           (cons 41 0)
           (cons 42 0)
           (cons 91 0)
           (list 10 8.459 -0.744548)
           (cons 40 0)
           (cons 41 0)
           (cons 42 0)
           (cons 91 0)
           (list 10 8.30248 -0.797)
           (cons 40 0)
           (cons 41 0)
           (cons 42 0)
           (cons 91 0)
           (list 10 7.49752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.341 -1.247548)
           (cons 40 0)
           (cons 41 0)
           (cons 42 0)
           (cons 91 0)
           (list 10 7.341 -1.073452)
           (cons 40 0)
           (cons 41 0)
           (cons 42 0)
           (cons 91 0)
           (list 10 7.49752 -1.021)
           (cons 40 0)
           (cons 41 0)
           (cons 42 0)
           (cons 91 0)
           (list 10 8.30248 -1.021)
           (cons 40 0)
           (cons 41 0)
           (cons 42 0)
           (cons 91 0)
           (list 10 8.459 -1.073452)
           (cons 40 0)
           (cons 41 0)
           (cons 42 0)
           (cons 91 0)
           (list 10 8.459 -1.247548)
           (cons 40 0)
           (cons 41 0)
           (cons 42 0)
           (cons 91 0)
           (list 10 8.30248 -1.3)
           (cons 40 0)
           (cons 41 0)
           (cons 42 0)
           (cons 91 0)
           (list 10 7.49752 -1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.38016 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.38016 -0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 10.4 -0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 10.4 0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.38016 0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.38016 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "Defpoints")
           (cons 6 "Continuous")
           (cons 100 "AcDbPolyline")
           (cons 90 8)
           (cons 70 1)
           (cons 43 0)
           (cons 38 0)
           (cons 39 0)
           (list 10 0 -1.3)
           (cons 40 0)
           (cons 41 0)
           (cons 42 0)
           (cons 91 0)
           (list 10 8.459 -1.3)
           (cons 40 0)
           (cons 41 0)
           (cons 42 0)
           (cons 91 0)
           (list 10 8.459 -0.5188)
           (cons 40 0)
           (cons 41 0)
           (cons 42 0)
           (cons 91 0)
           (list 10 10.4 -0.5188)
           (cons 40 0)
           (cons 41 0)
           (cons 42 0)
           (cons 91 0)
           (list 10 10.4 0.5188)
           (cons 40 0)
           (cons 41 0)
           (cons 42 0)
           (cons 91 0)
           (list 10 8.459 0.5188)
           (cons 40 0)
           (cons 41 0)
           (cons 42 0)
           (cons 91 0)
           (list 10 8.459 1.3)
           (cons 40 0)
           (cons 41 0)
           (cons 42 0)
           (cons 91 0)
           (list 10 0 1.3)
           (cons 40 0)
           (cons 41 0)
           (cons 42 0)
           (cons 91 0)
          )
         )
         (entmake
          (list
           (cons 0 "POINT")
           (cons 100 "AcDbEntity")
           (cons 67 0)
           (cons 8 "0")
           (cons 6 "Continuous")
           (cons 100 "AcDbPoint")
           (list 10 7.3 0 0)
           (cons 50 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 7.3 0 0)
           (cons 40 0.17333333)
          )
         )
         (entmake
          (list
           (cons 0 "ATTDEF")
           (cons 100 "AcDbEntity")
           (cons 67 0)
           (cons 8 "0")
           (cons 6 "Continuous")
           (cons 100 "AcDbText")
           (list 10 0.4 0.56666667 0)
           (cons 40 0.2)
           (cons 1 "1.100")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 6 "Continuous")
           (cons 100 "AcDbText")
           (list 10 0.4 0.23333333 0)
           (cons 40 0.2)
           (cons 1 "1.100")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 6 "Continuous")
           (cons 100 "AcDbText")
           (list 10 0.4 -0.1 0)
           (cons 40 0.2)
           (cons 1 "7.900")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 6 "Continuous")
           (cons 100 "AcDbText")
           (list 10 0.4 -0.43333333 0)
           (cons 40 0.2)
           (cons 1 "7.300")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 6 "Continuous")
           (cons 100 "AcDbText")
           (list 10 0.4 -0.76666667 0)
           (cons 40 0.2)
           (cons 1 "32.983")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "BC_MOTI-WB-15-Truck"))
        (progn
         (entmake)
         (entmake
          (list
           (cons 0 "BLOCK")
           (cons 2 "BC_MOTI-WB-15-Truck")
           (cons 70 2)
           (cons 4 "")
           (list 10 0 0 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 6.4 -1.3 0)
           (cons 50 0)
          )
         )
         (entmake
          (list
           (cons 0 "POINT")
           (cons 100 "AcDbEntity")
           (cons 67 0)
           (cons 8 "0")
           (cons 100 "AcDbPoint")
           (list 10 6.4 1.3 0)
           (cons 50 0)
          )
         )
         (entmake
          (list
           (cons 0 "POINT")
           (cons 100 "AcDbEntity")
           (cons 67 0)
           (cons 8 "0")
           (cons 100 "AcDbPoint")
           (list 10 0.9 -1.3 0)
           (cons 50 0)
          )
         )
         (entmake
          (list
           (cons 0 "POINT")
           (cons 100 "AcDbEntity")
           (cons 67 0)
           (cons 8 "0")
           (cons 100 "AcDbPoint")
           (list 10 0.9 1.3 0)
           (cons 50 0)
          )
         )
         (entmake
          (list
           (cons 0 "POINT")
           (cons 100 "AcDbEntity")
           (cons 67 0)
           (cons 8 "0")
           (cons 100 "AcDbPoint")
           (list 10 0.9 0 0)
           (cons 50 0)
          )
         )
         (entmake
          (list
           (cons 0 "INSERT")
           (cons 100 "AcDbEntity")
           (cons 67 0)
           (cons 8 "0")
           (cons 100 "AcDbBlockReference")
           (cons 2 "WheelLeftM1")
           (list 10 0.9 -1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM1")
           (list 10 0.9 1.0206 0)
           (cons 41 1)
           (cons 42 1)
           (cons 43 1)
           (cons 50 0)
           (cons 70 0)
           (cons 71 0)
           (cons 44 0)
           (cons 45 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.841 1.073452)
           (cons 40 0)
           (cons 41 0)
           (cons 42 0)
           (cons 91 0)
           (list 10 5.841 1.247548)
           (cons 40 0)
           (cons 41 0)
           (cons 42 0)
           (cons 91 0)
           (list 10 5.99752 1.3)
           (cons 40 0)
           (cons 41 0)
           (cons 42 0)
           (cons 91 0)
           (list 10 6.80248 1.3)
           (cons 40 0)
           (cons 41 0)
           (cons 42 0)
           (cons 91 0)
           (list 10 6.959 1.247548)
           (cons 40 0)
           (cons 41 0)
           (cons 42 0)
           (cons 91 0)
           (list 10 6.959 1.073452)
           (cons 40 0)
           (cons 41 0)
           (cons 42 0)
           (cons 91 0)
           (list 10 6.80248 1.021)
           (cons 40 0)
           (cons 41 0)
           (cons 42 0)
           (cons 91 0)
           (list 10 5.99752 1.021)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.841 0.570452)
           (cons 40 0)
           (cons 41 0)
           (cons 42 0)
           (cons 91 0)
           (list 10 5.841 0.744548)
           (cons 40 0)
           (cons 41 0)
           (cons 42 0)
           (cons 91 0)
           (list 10 5.99752 0.797)
           (cons 40 0)
           (cons 41 0)
           (cons 42 0)
           (cons 91 0)
           (list 10 6.80248 0.797)
           (cons 40 0)
           (cons 41 0)
           (cons 42 0)
           (cons 91 0)
           (list 10 6.959 0.744548)
           (cons 40 0)
           (cons 41 0)
           (cons 42 0)
           (cons 91 0)
           (list 10 6.959 0.570452)
           (cons 40 0)
           (cons 41 0)
           (cons 42 0)
           (cons 91 0)
           (list 10 6.80248 0.518)
           (cons 40 0)
           (cons 41 0)
           (cons 42 0)
           (cons 91 0)
           (list 10 5.99752 0.518)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.841 -0.744548)
           (cons 40 0)
           (cons 41 0)
           (cons 42 0)
           (cons 91 0)
           (list 10 5.841 -0.570452)
           (cons 40 0)
           (cons 41 0)
           (cons 42 0)
           (cons 91 0)
           (list 10 5.99752 -0.518)
           (cons 40 0)
           (cons 41 0)
           (cons 42 0)
           (cons 91 0)
           (list 10 6.80248 -0.518)
           (cons 40 0)
           (cons 41 0)
           (cons 42 0)
           (cons 91 0)
           (list 10 6.959 -0.570452)
           (cons 40 0)
           (cons 41 0)
           (cons 42 0)
           (cons 91 0)
           (list 10 6.959 -0.744548)
           (cons 40 0)
           (cons 41 0)
           (cons 42 0)
           (cons 91 0)
           (list 10 6.80248 -0.797)
           (cons 40 0)
           (cons 41 0)
           (cons 42 0)
           (cons 91 0)
           (list 10 5.99752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.841 -1.247548)
           (cons 40 0)
           (cons 41 0)
           (cons 42 0)
           (cons 91 0)
           (list 10 5.841 -1.073452)
           (cons 40 0)
           (cons 41 0)
           (cons 42 0)
           (cons 91 0)
           (list 10 5.99752 -1.021)
           (cons 40 0)
           (cons 41 0)
           (cons 42 0)
           (cons 91 0)
           (list 10 6.80248 -1.021)
           (cons 40 0)
           (cons 41 0)
           (cons 42 0)
           (cons 91 0)
           (list 10 6.959 -1.073452)
           (cons 40 0)
           (cons 41 0)
           (cons 42 0)
           (cons 91 0)
           (list 10 6.959 -1.247548)
           (cons 40 0)
           (cons 41 0)
           (cons 42 0)
           (cons 91 0)
           (list 10 6.80248 -1.3)
           (cons 40 0)
           (cons 41 0)
           (cons 42 0)
           (cons 91 0)
           (list 10 5.99752 -1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.18016 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.18016 -0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.6 -0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.6 0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.18016 0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.18016 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "Defpoints")
           (cons 100 "AcDbPolyline")
           (cons 90 8)
           (cons 70 1)
           (cons 43 0)
           (cons 38 0)
           (cons 39 0)
           (list 10 0 -1.3)
           (cons 40 0)
           (cons 41 0)
           (cons 42 0)
           (cons 91 0)
           (list 10 6.959 -1.3)
           (cons 40 0)
           (cons 41 0)
           (cons 42 0)
           (cons 91 0)
           (list 10 6.959 -0.5188)
           (cons 40 0)
           (cons 41 0)
           (cons 42 0)
           (cons 91 0)
           (list 10 7.6 -0.5188)
           (cons 40 0)
           (cons 41 0)
           (cons 42 0)
           (cons 91 0)
           (list 10 7.6 0.5188)
           (cons 40 0)
           (cons 41 0)
           (cons 42 0)
           (cons 91 0)
           (list 10 6.959 0.5188)
           (cons 40 0)
           (cons 41 0)
           (cons 42 0)
           (cons 91 0)
           (list 10 6.959 1.3)
           (cons 40 0)
           (cons 41 0)
           (cons 42 0)
           (cons 91 0)
           (list 10 0 1.3)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 6.4 0 0)
           (cons 50 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 6.4 0 0)
           (cons 40 0.17333333)
          )
         )
         (entmake
          (list
           (cons 0 "ATTDEF")
           (cons 100 "AcDbEntity")
           (cons 67 0)
           (cons 8 "0")
           (cons 100 "AcDbText")
           (list 10 0.2 0.56666667 0)
           (cons 40 0.2)
           (cons 1 "0.900")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.2 0.23333333 0)
           (cons 40 0.2)
           (cons 1 "0.900")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.2 -0.1 0)
           (cons 40 0.2)
           (cons 1 "6.400")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.2 -0.43333333 0)
           (cons 40 0.2)
           (cons 1 "6.400")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.2 -0.76666667 0)
           (cons 40 0.2)
           (cons 1 "26.059")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "BC_MOTI-WB-15-Trailer"))
        (progn
         (entmake)
         (entmake
          (list
           (cons 0 "BLOCK")
           (cons 2 "BC_MOTI-WB-15-Trailer")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 14.7 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 14.7 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.9912 -0.7445528)
           (cons 40 0)
           (cons 41 0)
           (cons 42 0)
           (cons 91 0)
           (list 10 11.9912 -0.5702072)
           (cons 40 0)
           (cons 41 0)
           (cons 42 0)
           (cons 91 0)
           (list 10 12.147664 -0.51768)
           (cons 40 0)
           (cons 41 0)
           (cons 42 0)
           (cons 91 0)
           (list 10 12.952336 -0.51768)
           (cons 40 0)
           (cons 41 0)
           (cons 42 0)
           (cons 91 0)
           (list 10 13.1088 -0.5702072)
           (cons 40 0)
           (cons 41 0)
           (cons 42 0)
           (cons 91 0)
           (list 10 13.1088 -0.7445528)
           (cons 40 0)
           (cons 41 0)
           (cons 42 0)
           (cons 91 0)
           (list 10 12.952336 -0.79708)
           (cons 40 0)
           (cons 41 0)
           (cons 42 0)
           (cons 91 0)
           (list 10 12.147664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.9912 -1.2474728)
           (cons 40 0)
           (cons 41 0)
           (cons 42 0)
           (cons 91 0)
           (list 10 11.9912 -1.0731272)
           (cons 40 0)
           (cons 41 0)
           (cons 42 0)
           (cons 91 0)
           (list 10 12.147664 -1.0206)
           (cons 40 0)
           (cons 41 0)
           (cons 42 0)
           (cons 91 0)
           (list 10 12.952336 -1.0206)
           (cons 40 0)
           (cons 41 0)
           (cons 42 0)
           (cons 91 0)
           (list 10 13.1088 -1.0731272)
           (cons 40 0)
           (cons 41 0)
           (cons 42 0)
           (cons 91 0)
           (list 10 13.1088 -1.2474728)
           (cons 40 0)
           (cons 41 0)
           (cons 42 0)
           (cons 91 0)
           (list 10 12.952336 -1.3)
           (cons 40 0)
           (cons 41 0)
           (cons 42 0)
           (cons 91 0)
           (list 10 12.147664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.9912 0.5702072)
           (cons 40 0)
           (cons 41 0)
           (cons 42 0)
           (cons 91 0)
           (list 10 11.9912 0.7445528)
           (cons 40 0)
           (cons 41 0)
           (cons 42 0)
           (cons 91 0)
           (list 10 12.147664 0.79708)
           (cons 40 0)
           (cons 41 0)
           (cons 42 0)
           (cons 91 0)
           (list 10 12.952336 0.79708)
           (cons 40 0)
           (cons 41 0)
           (cons 42 0)
           (cons 91 0)
           (list 10 13.1088 0.7445528)
           (cons 40 0)
           (cons 41 0)
           (cons 42 0)
           (cons 91 0)
           (list 10 13.1088 0.5702072)
           (cons 40 0)
           (cons 41 0)
           (cons 42 0)
           (cons 91 0)
           (list 10 12.952336 0.51768)
           (cons 40 0)
           (cons 41 0)
           (cons 42 0)
           (cons 91 0)
           (list 10 12.147664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.9912 1.0731272)
           (cons 40 0)
           (cons 41 0)
           (cons 42 0)
           (cons 91 0)
           (list 10 11.9912 1.2474728)
           (cons 40 0)
           (cons 41 0)
           (cons 42 0)
           (cons 91 0)
           (list 10 12.147664 1.3)
           (cons 40 0)
           (cons 41 0)
           (cons 42 0)
           (cons 91 0)
           (list 10 12.952336 1.3)
           (cons 40 0)
           (cons 41 0)
           (cons 42 0)
           (cons 91 0)
           (list 10 13.1088 1.2474728)
           (cons 40 0)
           (cons 41 0)
           (cons 42 0)
           (cons 91 0)
           (list 10 13.1088 1.0731272)
           (cons 40 0)
           (cons 41 0)
           (cons 42 0)
           (cons 91 0)
           (list 10 12.952336 1.0206)
           (cons 40 0)
           (cons 41 0)
           (cons 42 0)
           (cons 91 0)
           (list 10 12.147664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 1.55 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 14.7 -1.3)
           (cons 40 0)
           (cons 41 0)
           (cons 42 0)
           (cons 91 0)
           (list 10 14.7 1.3)
           (cons 40 0)
           (cons 41 0)
           (cons 42 0)
           (cons 91 0)
           (list 10 0 1.3)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 14.7 -1.3 0)
           (cons 50 0)
          )
         )
         (entmake
          (list
           (cons 0 "POINT")
           (cons 100 "AcDbEntity")
           (cons 67 0)
           (cons 8 "0")
           (cons 100 "AcDbPoint")
           (list 10 14.7 1.3 0)
           (cons 50 0)
          )
         )
         (entmake
          (list
           (cons 0 "POINT")
           (cons 100 "AcDbEntity")
           (cons 67 0)
           (cons 8 "0")
           (cons 100 "AcDbPoint")
           (list 10 12.55 1.3 0)
           (cons 50 0)
          )
         )
         (entmake
          (list
           (cons 0 "POINT")
           (cons 100 "AcDbEntity")
           (cons 67 0)
           (cons 8 "0")
           (cons 100 "AcDbPoint")
           (list 10 12.55 -1.3 0)
           (cons 50 0)
          )
         )
         (entmake
          (list
           (cons 0 "ATTDEF")
           (cons 100 "AcDbEntity")
           (cons 67 0)
           (cons 8 "0")
           (cons 100 "AcDbText")
           (list 10 0.85 0.56666667 0)
           (cons 40 0.2)
           (cons 1 "1.550")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.85 0.23333333 0)
           (cons 40 0.2)
           (cons 1 "1.550")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.85 -0.1 0)
           (cons 40 0.2)
           (cons 1 "12.550")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.85 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.85 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "BC_MOTI-LG5-Trailer1"))
        (progn
         (entmake)
         (entmake
          (list
           (cons 0 "BLOCK")
           (cons 2 "BC_MOTI-LG5-Trailer1")
           (cons 70 2)
           (cons 4 "")
           (list 10 0 0 0)
          )
         )
         (entmake
          (list
           (cons 0 "POINT")
           (cons 100 "AcDbEntity")
           (cons 67 0)
           (cons 8 "0")
           (cons 62 1)
           (cons 100 "AcDbPoint")
           (list 10 4.09 0 0)
           (cons 50 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 4.09 0 0)
           (cons 40 0.1524)
          )
         )
         (entmake
          (list
           (cons 0 "POINT")
           (cons 100 "AcDbEntity")
           (cons 67 0)
           (cons 8 "0")
           (cons 100 "AcDbPoint")
           (list 10 7.29 -1.3 0)
           (cons 50 0)
          )
         )
         (entmake
          (list
           (cons 0 "POINT")
           (cons 100 "AcDbEntity")
           (cons 67 0)
           (cons 8 "0")
           (cons 100 "AcDbPoint")
           (list 10 7.29 1.3 0)
           (cons 50 0)
          )
         )
         (entmake
          (list
           (cons 0 "POINT")
           (cons 100 "AcDbEntity")
           (cons 67 0)
           (cons 8 "0")
           (cons 100 "AcDbPoint")
           (list 10 0.7 0 0)
           (cons 50 0)
          )
         )
         (entmake
          (list
           (cons 0 "POINT")
           (cons 100 "AcDbEntity")
           (cons 67 0)
           (cons 8 "0")
           (cons 100 "AcDbPoint")
           (list 10 8.89 0 0)
           (cons 50 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 8.89 0 0)
           (cons 40 0.17333333)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.731 1.073452)
           (cons 40 0)
           (cons 41 0)
           (cons 42 0)
           (cons 91 0)
           (list 10 6.731 1.247548)
           (cons 40 0)
           (cons 41 0)
           (cons 42 0)
           (cons 91 0)
           (list 10 6.88752 1.3)
           (cons 40 0)
           (cons 41 0)
           (cons 42 0)
           (cons 91 0)
           (list 10 7.69248 1.3)
           (cons 40 0)
           (cons 41 0)
           (cons 42 0)
           (cons 91 0)
           (list 10 7.849 1.247548)
           (cons 40 0)
           (cons 41 0)
           (cons 42 0)
           (cons 91 0)
           (list 10 7.849 1.073452)
           (cons 40 0)
           (cons 41 0)
           (cons 42 0)
           (cons 91 0)
           (list 10 7.69248 1.021)
           (cons 40 0)
           (cons 41 0)
           (cons 42 0)
           (cons 91 0)
           (list 10 6.88752 1.021)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.731 0.570452)
           (cons 40 0)
           (cons 41 0)
           (cons 42 0)
           (cons 91 0)
           (list 10 6.731 0.744548)
           (cons 40 0)
           (cons 41 0)
           (cons 42 0)
           (cons 91 0)
           (list 10 6.88752 0.797)
           (cons 40 0)
           (cons 41 0)
           (cons 42 0)
           (cons 91 0)
           (list 10 7.69248 0.797)
           (cons 40 0)
           (cons 41 0)
           (cons 42 0)
           (cons 91 0)
           (list 10 7.849 0.744548)
           (cons 40 0)
           (cons 41 0)
           (cons 42 0)
           (cons 91 0)
           (list 10 7.849 0.570452)
           (cons 40 0)
           (cons 41 0)
           (cons 42 0)
           (cons 91 0)
           (list 10 7.69248 0.518)
           (cons 40 0)
           (cons 41 0)
           (cons 42 0)
           (cons 91 0)
           (list 10 6.88752 0.518)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.731 -0.744548)
           (cons 40 0)
           (cons 41 0)
           (cons 42 0)
           (cons 91 0)
           (list 10 6.731 -0.570452)
           (cons 40 0)
           (cons 41 0)
           (cons 42 0)
           (cons 91 0)
           (list 10 6.88752 -0.518)
           (cons 40 0)
           (cons 41 0)
           (cons 42 0)
           (cons 91 0)
           (list 10 7.69248 -0.518)
           (cons 40 0)
           (cons 41 0)
           (cons 42 0)
           (cons 91 0)
           (list 10 7.849 -0.570452)
           (cons 40 0)
           (cons 41 0)
           (cons 42 0)
           (cons 91 0)
           (list 10 7.849 -0.744548)
           (cons 40 0)
           (cons 41 0)
           (cons 42 0)
           (cons 91 0)
           (list 10 7.69248 -0.797)
           (cons 40 0)
           (cons 41 0)
           (cons 42 0)
           (cons 91 0)
           (list 10 6.88752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.731 -1.247548)
           (cons 40 0)
           (cons 41 0)
           (cons 42 0)
           (cons 91 0)
           (list 10 6.731 -1.073452)
           (cons 40 0)
           (cons 41 0)
           (cons 42 0)
           (cons 91 0)
           (list 10 6.88752 -1.021)
           (cons 40 0)
           (cons 41 0)
           (cons 42 0)
           (cons 91 0)
           (list 10 7.69248 -1.021)
           (cons 40 0)
           (cons 41 0)
           (cons 42 0)
           (cons 91 0)
           (list 10 7.849 -1.073452)
           (cons 40 0)
           (cons 41 0)
           (cons 42 0)
           (cons 91 0)
           (list 10 7.849 -1.247548)
           (cons 40 0)
           (cons 41 0)
           (cons 42 0)
           (cons 91 0)
           (list 10 7.69248 -1.3)
           (cons 40 0)
           (cons 41 0)
           (cons 42 0)
           (cons 91 0)
           (list 10 6.88752 -1.3)
           (cons 40 0)
           (cons 41 0)
           (cons 42 0)
           (cons 91 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0.7 0 0)
           (cons 40 0.104)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.89 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.89 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "POLYLINE")
           (cons 100 "AcDbEntity")
           (cons 67 0)
           (cons 8 "Defpoints")
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "Defpoints")
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.731 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.731 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 7.849 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 7.849 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 8.89 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 8.89 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 7.849 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 7.849 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.731 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.731 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 0 0.5 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "Defpoints")
          )
         )
         (entmake
          (list
           (cons 0 "TEXT")
           (cons 100 "AcDbEntity")
           (cons 67 0)
           (cons 8 "0")
           (cons 100 "AcDbText")
           (list 10 1.53333333 -0.25 0)
           (cons 40 0.5)
           (cons 1 "2")
           (cons 50 0)
           (cons 41 1)
           (cons 51 0)
           (cons 7 "Standard")
           (cons 71 0)
           (cons 72 4)
           (list 11 1.7 0 0)
           (cons 100 "AcDbText")
           (cons 73 0)
          )
         )
         (entmake
          (list
           (cons 0 "ATTDEF")
           (cons 100 "AcDbEntity")
           (cons 67 0)
           (cons 8 "0")
           (cons 100 "AcDbText")
           (list 10 -0.3 0.56666667 0)
           (cons 40 0.2)
           (cons 1 "0.700")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 0.23333333 0)
           (cons 40 0.2)
           (cons 1 "0.700")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.1 0)
           (cons 40 0.2)
           (cons 1 "7.290")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.43333333 0)
           (cons 40 0.2)
           (cons 1 "8.890")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -1.10000001 0)
           (cons 40 0.2)
           (cons 1 "4.090")
           (cons 50 0)
           (cons 41 1)
           (cons 51 0)
           (cons 7 "Standard")
           (cons 71 0)
           (cons 72 0)
           (list 11 0 0 0)
           (cons 100 "AcDbAttributeDefinition")
           (cons 3 "Load Angle Point (LA)")
           (cons 2 "LA")
           (cons 70 9)
           (cons 73 0)
           (cons 74 0)
          )
         )
         (entmake (list (cons 0 "ENDBLK")))
        )
       )
       ((= (strcase BLKNAME) (strcase "BC_MOTI-LG5-Load"))
        (progn
         (entmake)
         (entmake
          (list
           (cons 0 "BLOCK")
           (cons 2 "BC_MOTI-LG5-Load")
           (cons 70 2)
           (cons 4 "")
           (list 10 0 0 0)
          )
         )
         (entmake
          (list
           (cons 0 "POINT")
           (cons 100 "AcDbEntity")
           (cons 67 0)
           (cons 8 "0")
           (cons 100 "AcDbPoint")
           (list 10 16.8 1.3 0)
           (cons 50 0)
          )
         )
         (entmake
          (list
           (cons 0 "POINT")
           (cons 100 "AcDbEntity")
           (cons 67 0)
           (cons 8 "0")
           (cons 100 "AcDbPoint")
           (list 10 16.8 -1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 62 3)
           (cons 100 "AcDbPoint")
           (list 10 15 0 0)
           (cons 50 0)
          )
         )
         (entmake
          (list
           (cons 0 "POINT")
           (cons 100 "AcDbEntity")
           (cons 67 0)
           (cons 8 "0")
           (cons 62 3)
           (cons 100 "AcDbPoint")
           (list 10 4.2 0 0)
           (cons 50 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 4.2 0 0)
           (cons 40 0.1524)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 16.8 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 16.8 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 15 0 0)
           (cons 40 0.1524)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 16.8 -1.3)
           (cons 40 0)
           (cons 41 0)
           (cons 42 0)
           (cons 91 0)
           (list 10 16.8 1.3)
           (cons 40 0)
           (cons 41 0)
           (cons 42 0)
           (cons 91 0)
           (list 10 0 1.3)
           (cons 40 0)
           (cons 41 0)
           (cons 42 0)
           (cons 91 0)
          )
         )
         (entmake
          (list
           (cons 0 "TEXT")
           (cons 100 "AcDbEntity")
           (cons 67 0)
           (cons 8 "0")
           (cons 100 "AcDbText")
           (list 10 5.02142857 -0.25 0)
           (cons 40 0.5)
           (cons 1 "4")
           (cons 50 0)
           (cons 41 1)
           (cons 51 0)
           (cons 7 "Standard")
           (cons 71 0)
           (cons 72 4)
           (list 11 5.2 0 0)
           (cons 100 "AcDbText")
           (cons 73 0)
          )
         )
         (entmake
          (list
           (cons 0 "ATTDEF")
           (cons 100 "AcDbEntity")
           (cons 67 0)
           (cons 8 "0")
           (cons 100 "AcDbText")
           (list 10 3.5 -0.1 0)
           (cons 40 0.2)
           (cons 1 "15.000")
           (cons 50 0)
           (cons 41 1)
           (cons 51 0)
           (cons 7 "Standard")
           (cons 71 0)
           (cons 72 0)
           (list 11 0 0 0)
           (cons 100 "AcDbAttributeDefinition")
           (cons 3 "Load Base Point (LB)")
           (cons 2 "LB")
           (cons 70 9)
           (cons 73 0)
           (cons 74 0)
          )
         )
         (entmake
          (list
           (cons 0 "ATTDEF")
           (cons 100 "AcDbEntity")
           (cons 67 0)
           (cons 8 "0")
           (cons 100 "AcDbText")
           (list 10 3.5 -0.43333333 0)
           (cons 40 0.2)
           (cons 1 "4.200")
           (cons 50 0)
           (cons 41 1)
           (cons 51 0)
           (cons 7 "Standard")
           (cons 71 0)
           (cons 72 0)
           (list 11 0 0 0)
           (cons 100 "AcDbAttributeDefinition")
           (cons 3 "Load Angle Point (LA)")
           (cons 2 "LA")
           (cons 70 9)
           (cons 73 0)
           (cons 74 0)
          )
         )
         (entmake (list (cons 0 "ENDBLK")))
        )
       )
       ((= (strcase BLKNAME) (strcase "BC_MOTI-LG5-Trailer2"))
        (progn
         (entmake)
         (entmake
          (list
           (cons 0 "BLOCK")
           (cons 2 "BC_MOTI-LG5-Trailer2")
           (cons 70 2)
           (cons 4 "")
           (list 10 0 0 0)
          )
         )
         (entmake
          (list
           (cons 0 "POINT")
           (cons 100 "AcDbEntity")
           (cons 67 0)
           (cons 8 "0")
           (cons 100 "AcDbPoint")
           (list 10 5.95 -1.3 0)
           (cons 50 0)
          )
         )
         (entmake
          (list
           (cons 0 "POINT")
           (cons 100 "AcDbEntity")
           (cons 67 0)
           (cons 8 "0")
           (cons 100 "AcDbPoint")
           (list 10 5.95 1.3 0)
           (cons 50 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 6 0 0)
           (cons 40 0.1524)
          )
         )
         (entmake
          (list
           (cons 0 "POINT")
           (cons 100 "AcDbEntity")
           (cons 67 0)
           (cons 8 "0")
           (cons 62 1)
           (cons 6 "Continuous")
           (cons 48 1.524)
           (cons 100 "AcDbPoint")
           (list 10 6 0 0)
           (cons 50 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.391 0.570452)
           (cons 40 0)
           (cons 41 0)
           (cons 42 0)
           (cons 91 0)
           (list 10 5.391 0.744548)
           (cons 40 0)
           (cons 41 0)
           (cons 42 0)
           (cons 91 0)
           (list 10 5.54752 0.797)
           (cons 40 0)
           (cons 41 0)
           (cons 42 0)
           (cons 91 0)
           (list 10 6.35248 0.797)
           (cons 40 0)
           (cons 41 0)
           (cons 42 0)
           (cons 91 0)
           (list 10 6.509 0.744548)
           (cons 40 0)
           (cons 41 0)
           (cons 42 0)
           (cons 91 0)
           (list 10 6.509 0.570452)
           (cons 40 0)
           (cons 41 0)
           (cons 42 0)
           (cons 91 0)
           (list 10 6.35248 0.518)
           (cons 40 0)
           (cons 41 0)
           (cons 42 0)
           (cons 91 0)
           (list 10 5.54752 0.518)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.391 -0.744548)
           (cons 40 0)
           (cons 41 0)
           (cons 42 0)
           (cons 91 0)
           (list 10 5.391 -0.570452)
           (cons 40 0)
           (cons 41 0)
           (cons 42 0)
           (cons 91 0)
           (list 10 5.54752 -0.518)
           (cons 40 0)
           (cons 41 0)
           (cons 42 0)
           (cons 91 0)
           (list 10 6.35248 -0.518)
           (cons 40 0)
           (cons 41 0)
           (cons 42 0)
           (cons 91 0)
           (list 10 6.509 -0.570452)
           (cons 40 0)
           (cons 41 0)
           (cons 42 0)
           (cons 91 0)
           (list 10 6.509 -0.744548)
           (cons 40 0)
           (cons 41 0)
           (cons 42 0)
           (cons 91 0)
           (list 10 6.35248 -0.797)
           (cons 40 0)
           (cons 41 0)
           (cons 42 0)
           (cons 91 0)
           (list 10 5.54752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.391 -1.247548)
           (cons 40 0)
           (cons 41 0)
           (cons 42 0)
           (cons 91 0)
           (list 10 5.391 -1.073452)
           (cons 40 0)
           (cons 41 0)
           (cons 42 0)
           (cons 91 0)
           (list 10 5.54752 -1.021)
           (cons 40 0)
           (cons 41 0)
           (cons 42 0)
           (cons 91 0)
           (list 10 6.35248 -1.021)
           (cons 40 0)
           (cons 41 0)
           (cons 42 0)
           (cons 91 0)
           (list 10 6.509 -1.073452)
           (cons 40 0)
           (cons 41 0)
           (cons 42 0)
           (cons 91 0)
           (list 10 6.509 -1.247548)
           (cons 40 0)
           (cons 41 0)
           (cons 42 0)
           (cons 91 0)
           (list 10 6.35248 -1.3)
           (cons 40 0)
           (cons 41 0)
           (cons 42 0)
           (cons 91 0)
           (list 10 5.54752 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.391 1.073452)
           (cons 40 0)
           (cons 41 0)
           (cons 42 0)
           (cons 91 0)
           (list 10 5.391 1.247548)
           (cons 40 0)
           (cons 41 0)
           (cons 42 0)
           (cons 91 0)
           (list 10 5.54752 1.3)
           (cons 40 0)
           (cons 41 0)
           (cons 42 0)
           (cons 91 0)
           (list 10 6.35248 1.3)
           (cons 40 0)
           (cons 41 0)
           (cons 42 0)
           (cons 91 0)
           (list 10 6.509 1.247548)
           (cons 40 0)
           (cons 41 0)
           (cons 42 0)
           (cons 91 0)
           (list 10 6.509 1.073452)
           (cons 40 0)
           (cons 41 0)
           (cons 42 0)
           (cons 91 0)
           (list 10 6.35248 1.021)
           (cons 40 0)
           (cons 41 0)
           (cons 42 0)
           (cons 91 0)
           (list 10 5.54752 1.021)
           (cons 40 0)
           (cons 41 0)
           (cons 42 0)
           (cons 91 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.1016)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.8 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.8 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "POLYLINE")
           (cons 100 "AcDbEntity")
           (cons 67 0)
           (cons 8 "Defpoints")
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "Defpoints")
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 5.391 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 5.391 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.509 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.509 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 7.8 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 7.8 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.509 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.509 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 5.391 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 5.391 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 0 0.5 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "Defpoints")
          )
         )
         (entmake
          (list
           (cons 0 "TEXT")
           (cons 100 "AcDbEntity")
           (cons 67 0)
           (cons 8 "0")
           (cons 100 "AcDbText")
           (list 10 0.83333333 -0.25 0)
           (cons 40 0.5)
           (cons 1 "3")
           (cons 50 0)
           (cons 41 1)
           (cons 51 0)
           (cons 7 "Standard")
           (cons 71 0)
           (cons 72 4)
           (list 11 1 0 0)
           (cons 100 "AcDbText")
           (cons 73 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "5.950")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -1.1 0)
           (cons 40 0.2)
           (cons 1 "6.000")
           (cons 50 0)
           (cons 41 1)
           (cons 51 0)
           (cons 7 "Standard")
           (cons 71 0)
           (cons 72 0)
           (list 11 0 0 0)
           (cons 100 "AcDbAttributeDefinition")
           (cons 3 "Load Base Point (LB)")
           (cons 2 "LB")
           (cons 70 9)
           (cons 73 0)
           (cons 74 0)
          )
         )
         (entmake (list (cons 0 "ENDBLK")))
        )
       )
       ((= (strcase BLKNAME) (strcase "BC_MOTI-LG5-Truck"))
        (progn
         (entmake)
         (entmake
          (list
           (cons 0 "BLOCK")
           (cons 2 "BC_MOTI-LG5-Truck")
           (cons 70 2)
           (cons 4 "")
           (list 10 0 0 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 7 -1.3 0)
           (cons 50 0)
          )
         )
         (entmake
          (list
           (cons 0 "POINT")
           (cons 100 "AcDbEntity")
           (cons 67 0)
           (cons 8 "0")
           (cons 100 "AcDbPoint")
           (list 10 7 1.3 0)
           (cons 50 0)
          )
         )
         (entmake
          (list
           (cons 0 "POINT")
           (cons 100 "AcDbEntity")
           (cons 67 0)
           (cons 8 "0")
           (cons 100 "AcDbPoint")
           (list 10 1.1 -1.3 0)
           (cons 50 0)
          )
         )
         (entmake
          (list
           (cons 0 "POINT")
           (cons 100 "AcDbEntity")
           (cons 67 0)
           (cons 8 "0")
           (cons 100 "AcDbPoint")
           (list 10 1.1 1.3 0)
           (cons 50 0)
          )
         )
         (entmake
          (list
           (cons 0 "POINT")
           (cons 100 "AcDbEntity")
           (cons 67 0)
           (cons 8 "0")
           (cons 100 "AcDbPoint")
           (list 10 1.1 0 0)
           (cons 50 0)
          )
         )
         (entmake
          (list
           (cons 0 "INSERT")
           (cons 100 "AcDbEntity")
           (cons 67 0)
           (cons 8 "0")
           (cons 100 "AcDbBlockReference")
           (cons 2 "WheelLeftM1")
           (list 10 1.1 -1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM1")
           (list 10 1.1 1.0206 0)
           (cons 41 1)
           (cons 42 1)
           (cons 43 1)
           (cons 50 0)
           (cons 70 0)
           (cons 71 0)
           (cons 44 0)
           (cons 45 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.441 1.073452)
           (cons 40 0)
           (cons 41 0)
           (cons 42 0)
           (cons 91 0)
           (list 10 6.441 1.247548)
           (cons 40 0)
           (cons 41 0)
           (cons 42 0)
           (cons 91 0)
           (list 10 6.59752 1.3)
           (cons 40 0)
           (cons 41 0)
           (cons 42 0)
           (cons 91 0)
           (list 10 7.40248 1.3)
           (cons 40 0)
           (cons 41 0)
           (cons 42 0)
           (cons 91 0)
           (list 10 7.559 1.247548)
           (cons 40 0)
           (cons 41 0)
           (cons 42 0)
           (cons 91 0)
           (list 10 7.559 1.073452)
           (cons 40 0)
           (cons 41 0)
           (cons 42 0)
           (cons 91 0)
           (list 10 7.40248 1.021)
           (cons 40 0)
           (cons 41 0)
           (cons 42 0)
           (cons 91 0)
           (list 10 6.59752 1.021)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.441 0.570452)
           (cons 40 0)
           (cons 41 0)
           (cons 42 0)
           (cons 91 0)
           (list 10 6.441 0.744548)
           (cons 40 0)
           (cons 41 0)
           (cons 42 0)
           (cons 91 0)
           (list 10 6.59752 0.797)
           (cons 40 0)
           (cons 41 0)
           (cons 42 0)
           (cons 91 0)
           (list 10 7.40248 0.797)
           (cons 40 0)
           (cons 41 0)
           (cons 42 0)
           (cons 91 0)
           (list 10 7.559 0.744548)
           (cons 40 0)
           (cons 41 0)
           (cons 42 0)
           (cons 91 0)
           (list 10 7.559 0.570452)
           (cons 40 0)
           (cons 41 0)
           (cons 42 0)
           (cons 91 0)
           (list 10 7.40248 0.518)
           (cons 40 0)
           (cons 41 0)
           (cons 42 0)
           (cons 91 0)
           (list 10 6.59752 0.518)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.441 -0.744548)
           (cons 40 0)
           (cons 41 0)
           (cons 42 0)
           (cons 91 0)
           (list 10 6.441 -0.570452)
           (cons 40 0)
           (cons 41 0)
           (cons 42 0)
           (cons 91 0)
           (list 10 6.59752 -0.518)
           (cons 40 0)
           (cons 41 0)
           (cons 42 0)
           (cons 91 0)
           (list 10 7.40248 -0.518)
           (cons 40 0)
           (cons 41 0)
           (cons 42 0)
           (cons 91 0)
           (list 10 7.559 -0.570452)
           (cons 40 0)
           (cons 41 0)
           (cons 42 0)
           (cons 91 0)
           (list 10 7.559 -0.744548)
           (cons 40 0)
           (cons 41 0)
           (cons 42 0)
           (cons 91 0)
           (list 10 7.40248 -0.797)
           (cons 40 0)
           (cons 41 0)
           (cons 42 0)
           (cons 91 0)
           (list 10 6.59752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.441 -1.247548)
           (cons 40 0)
           (cons 41 0)
           (cons 42 0)
           (cons 91 0)
           (list 10 6.441 -1.073452)
           (cons 40 0)
           (cons 41 0)
           (cons 42 0)
           (cons 91 0)
           (list 10 6.59752 -1.021)
           (cons 40 0)
           (cons 41 0)
           (cons 42 0)
           (cons 91 0)
           (list 10 7.40248 -1.021)
           (cons 40 0)
           (cons 41 0)
           (cons 42 0)
           (cons 91 0)
           (list 10 7.559 -1.073452)
           (cons 40 0)
           (cons 41 0)
           (cons 42 0)
           (cons 91 0)
           (list 10 7.559 -1.247548)
           (cons 40 0)
           (cons 41 0)
           (cons 42 0)
           (cons 91 0)
           (list 10 7.40248 -1.3)
           (cons 40 0)
           (cons 41 0)
           (cons 42 0)
           (cons 91 0)
           (list 10 6.59752 -1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.38016 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.38016 -0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.8 -0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.8 0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.38016 0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.38016 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "Defpoints")
           (cons 100 "AcDbPolyline")
           (cons 90 8)
           (cons 70 1)
           (cons 43 0)
           (cons 38 0)
           (cons 39 0)
           (list 10 0 -1.3)
           (cons 40 0)
           (cons 41 0)
           (cons 42 0)
           (cons 91 0)
           (list 10 7.559 -1.3)
           (cons 40 0)
           (cons 41 0)
           (cons 42 0)
           (cons 91 0)
           (list 10 7.559 -0.5188)
           (cons 40 0)
           (cons 41 0)
           (cons 42 0)
           (cons 91 0)
           (list 10 8.8 -0.5188)
           (cons 40 0)
           (cons 41 0)
           (cons 42 0)
           (cons 91 0)
           (list 10 8.8 0.5188)
           (cons 40 0)
           (cons 41 0)
           (cons 42 0)
           (cons 91 0)
           (list 10 7.559 0.5188)
           (cons 40 0)
           (cons 41 0)
           (cons 42 0)
           (cons 91 0)
           (list 10 7.559 1.3)
           (cons 40 0)
           (cons 41 0)
           (cons 42 0)
           (cons 91 0)
           (list 10 0 1.3)
           (cons 40 0)
           (cons 41 0)
           (cons 42 0)
           (cons 91 0)
          )
         )
         (entmake
          (list
           (cons 0 "TEXT")
           (cons 100 "AcDbEntity")
           (cons 67 0)
           (cons 8 "0")
           (cons 100 "AcDbText")
           (list 10 2.04047619 -0.25 0)
           (cons 40 0.5)
           (cons 1 "1")
           (cons 50 0)
           (cons 41 1)
           (cons 51 0)
           (cons 7 "Standard")
           (cons 71 0)
           (cons 72 4)
           (list 11 2.1 0 0)
           (cons 100 "AcDbText")
           (cons 73 0)
          )
         )
         (entmake
          (list
           (cons 0 "POINT")
           (cons 100 "AcDbEntity")
           (cons 67 0)
           (cons 8 "0")
           (cons 100 "AcDbPoint")
           (list 10 6.68 0 0)
           (cons 50 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 6.68 0 0)
           (cons 40 0.17333333)
          )
         )
         (entmake
          (list
           (cons 0 "ATTDEF")
           (cons 100 "AcDbEntity")
           (cons 67 0)
           (cons 8 "0")
           (cons 100 "AcDbText")
           (list 10 0.4 0.56666667 0)
           (cons 40 0.2)
           (cons 1 "1.100")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.4 0.23333333 0)
           (cons 40 0.2)
           (cons 1 "1.100")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.4 -0.1 0)
           (cons 40 0.2)
           (cons 1 "7.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.4 -0.43333333 0)
           (cons 40 0.2)
           (cons 1 "6.680")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.4 -0.76666667 0)
           (cons 40 0.2)
           (cons 1 "32.983")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "BC_MOTI-LG3-Load"))
        (progn
         (entmake)
         (entmake
          (list
           (cons 0 "BLOCK")
           (cons 2 "BC_MOTI-LG3-Load")
           (cons 70 2)
           (cons 4 "")
           (list 10 0 0 0)
          )
         )
         (entmake
          (list
           (cons 0 "POINT")
           (cons 100 "AcDbEntity")
           (cons 67 0)
           (cons 8 "0")
           (cons 100 "AcDbPoint")
           (list 10 16.7 1.3 0)
           (cons 50 0)
          )
         )
         (entmake
          (list
           (cons 0 "POINT")
           (cons 100 "AcDbEntity")
           (cons 67 0)
           (cons 8 "0")
           (cons 100 "AcDbPoint")
           (list 10 16.7 -1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 62 3)
           (cons 100 "AcDbPoint")
           (list 10 12.85 0 0)
           (cons 50 0)
          )
         )
         (entmake
          (list
           (cons 0 "POINT")
           (cons 100 "AcDbEntity")
           (cons 67 0)
           (cons 8 "0")
           (cons 62 3)
           (cons 100 "AcDbPoint")
           (list 10 2.5 0 0)
           (cons 50 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 2.5 0 0)
           (cons 40 0.1524)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 16.7 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 16.7 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 12.85 0 0)
           (cons 40 0.1524)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 16.7 -1.3)
           (cons 40 0)
           (cons 41 0)
           (cons 42 0)
           (cons 91 0)
           (list 10 16.7 1.3)
           (cons 40 0)
           (cons 41 0)
           (cons 42 0)
           (cons 91 0)
           (list 10 0 1.3)
           (cons 40 0)
           (cons 41 0)
           (cons 42 0)
           (cons 91 0)
          )
         )
         (entmake
          (list
           (cons 0 "TEXT")
           (cons 100 "AcDbEntity")
           (cons 67 0)
           (cons 8 "0")
           (cons 100 "AcDbText")
           (list 10 3.32142857 -0.25 0)
           (cons 40 0.5)
           (cons 1 "4")
           (cons 50 0)
           (cons 41 1)
           (cons 51 0)
           (cons 7 "Standard")
           (cons 71 0)
           (cons 72 4)
           (list 11 3.5 0 0)
           (cons 100 "AcDbText")
           (cons 73 0)
          )
         )
         (entmake
          (list
           (cons 0 "ATTDEF")
           (cons 100 "AcDbEntity")
           (cons 67 0)
           (cons 8 "0")
           (cons 100 "AcDbText")
           (list 10 1.8 -0.1 0)
           (cons 40 0.2)
           (cons 1 "12.850")
           (cons 50 0)
           (cons 41 1)
           (cons 51 0)
           (cons 7 "Standard")
           (cons 71 0)
           (cons 72 0)
           (list 11 0 0 0)
           (cons 100 "AcDbAttributeDefinition")
           (cons 3 "Load Base Point (LB)")
           (cons 2 "LB")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.8 -0.43333333 0)
           (cons 40 0.2)
           (cons 1 "2.500")
           (cons 50 0)
           (cons 41 1)
           (cons 51 0)
           (cons 7 "Standard")
           (cons 71 0)
           (cons 72 0)
           (list 11 0 0 0)
           (cons 100 "AcDbAttributeDefinition")
           (cons 3 "Load Angle Point (LA)")
           (cons 2 "LA")
           (cons 70 9)
           (cons 73 0)
           (cons 74 0)
          )
         )
         (entmake (list (cons 0 "ENDBLK")))
        )
       )
       ((= (strcase BLKNAME) (strcase "BC_MOTI-LG3-Trailer2"))
        (progn
         (entmake)
         (entmake
          (list
           (cons 0 "BLOCK")
           (cons 2 "BC_MOTI-LG3-Trailer2")
           (cons 70 2)
           (cons 4 "")
           (list 10 0 0 0)
          )
         )
         (entmake
          (list
           (cons 0 "POINT")
           (cons 100 "AcDbEntity")
           (cons 67 0)
           (cons 8 "0")
           (cons 100 "AcDbPoint")
           (list 10 5.15 -1.3 0)
           (cons 50 0)
          )
         )
         (entmake
          (list
           (cons 0 "POINT")
           (cons 100 "AcDbEntity")
           (cons 67 0)
           (cons 8 "0")
           (cons 100 "AcDbPoint")
           (list 10 5.15 1.3 0)
           (cons 50 0)
          )
         )
         (entmake
          (list
           (cons 0 "POINT")
           (cons 100 "AcDbEntity")
           (cons 67 0)
           (cons 8 "0")
           (cons 100 "AcDbPoint")
           (list 10 0.5 0 0)
           (cons 50 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 3.72 0 0)
           (cons 40 0.1524)
          )
         )
         (entmake
          (list
           (cons 0 "POINT")
           (cons 100 "AcDbEntity")
           (cons 67 0)
           (cons 8 "0")
           (cons 62 1)
           (cons 6 "Continuous")
           (cons 48 1.524)
           (cons 100 "AcDbPoint")
           (list 10 3.72 0 0)
           (cons 50 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.591 0.570452)
           (cons 40 0)
           (cons 41 0)
           (cons 42 0)
           (cons 91 0)
           (list 10 4.591 0.744548)
           (cons 40 0)
           (cons 41 0)
           (cons 42 0)
           (cons 91 0)
           (list 10 4.74752 0.797)
           (cons 40 0)
           (cons 41 0)
           (cons 42 0)
           (cons 91 0)
           (list 10 5.55248 0.797)
           (cons 40 0)
           (cons 41 0)
           (cons 42 0)
           (cons 91 0)
           (list 10 5.709 0.744548)
           (cons 40 0)
           (cons 41 0)
           (cons 42 0)
           (cons 91 0)
           (list 10 5.709 0.570452)
           (cons 40 0)
           (cons 41 0)
           (cons 42 0)
           (cons 91 0)
           (list 10 5.55248 0.518)
           (cons 40 0)
           (cons 41 0)
           (cons 42 0)
           (cons 91 0)
           (list 10 4.74752 0.518)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.591 -0.744548)
           (cons 40 0)
           (cons 41 0)
           (cons 42 0)
           (cons 91 0)
           (list 10 4.591 -0.570452)
           (cons 40 0)
           (cons 41 0)
           (cons 42 0)
           (cons 91 0)
           (list 10 4.74752 -0.518)
           (cons 40 0)
           (cons 41 0)
           (cons 42 0)
           (cons 91 0)
           (list 10 5.55248 -0.518)
           (cons 40 0)
           (cons 41 0)
           (cons 42 0)
           (cons 91 0)
           (list 10 5.709 -0.570452)
           (cons 40 0)
           (cons 41 0)
           (cons 42 0)
           (cons 91 0)
           (list 10 5.709 -0.744548)
           (cons 40 0)
           (cons 41 0)
           (cons 42 0)
           (cons 91 0)
           (list 10 5.55248 -0.797)
           (cons 40 0)
           (cons 41 0)
           (cons 42 0)
           (cons 91 0)
           (list 10 4.74752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.591 -1.247548)
           (cons 40 0)
           (cons 41 0)
           (cons 42 0)
           (cons 91 0)
           (list 10 4.591 -1.073452)
           (cons 40 0)
           (cons 41 0)
           (cons 42 0)
           (cons 91 0)
           (list 10 4.74752 -1.021)
           (cons 40 0)
           (cons 41 0)
           (cons 42 0)
           (cons 91 0)
           (list 10 5.55248 -1.021)
           (cons 40 0)
           (cons 41 0)
           (cons 42 0)
           (cons 91 0)
           (list 10 5.709 -1.073452)
           (cons 40 0)
           (cons 41 0)
           (cons 42 0)
           (cons 91 0)
           (list 10 5.709 -1.247548)
           (cons 40 0)
           (cons 41 0)
           (cons 42 0)
           (cons 91 0)
           (list 10 5.55248 -1.3)
           (cons 40 0)
           (cons 41 0)
           (cons 42 0)
           (cons 91 0)
           (list 10 4.74752 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.591 1.073452)
           (cons 40 0)
           (cons 41 0)
           (cons 42 0)
           (cons 91 0)
           (list 10 4.591 1.247548)
           (cons 40 0)
           (cons 41 0)
           (cons 42 0)
           (cons 91 0)
           (list 10 4.74752 1.3)
           (cons 40 0)
           (cons 41 0)
           (cons 42 0)
           (cons 91 0)
           (list 10 5.55248 1.3)
           (cons 40 0)
           (cons 41 0)
           (cons 42 0)
           (cons 91 0)
           (list 10 5.709 1.247548)
           (cons 40 0)
           (cons 41 0)
           (cons 42 0)
           (cons 91 0)
           (list 10 5.709 1.073452)
           (cons 40 0)
           (cons 41 0)
           (cons 42 0)
           (cons 91 0)
           (list 10 5.55248 1.021)
           (cons 40 0)
           (cons 41 0)
           (cons 42 0)
           (cons 91 0)
           (list 10 4.74752 1.021)
           (cons 40 0)
           (cons 41 0)
           (cons 42 0)
           (cons 91 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0.5 0 0)
           (cons 40 0.1016)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.57 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.57 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "POLYLINE")
           (cons 100 "AcDbEntity")
           (cons 67 0)
           (cons 8 "Defpoints")
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "Defpoints")
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 4.591 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 4.591 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 5.709 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 5.709 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 7.57 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 7.57 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 5.709 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 5.709 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 4.591 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 4.591 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 0 0.5 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "Defpoints")
          )
         )
         (entmake
          (list
           (cons 0 "TEXT")
           (cons 100 "AcDbEntity")
           (cons 67 0)
           (cons 8 "0")
           (cons 100 "AcDbText")
           (list 10 1.33333333 -0.25 0)
           (cons 40 0.5)
           (cons 1 "3")
           (cons 50 0)
           (cons 41 1)
           (cons 51 0)
           (cons 7 "Standard")
           (cons 71 0)
           (cons 72 4)
           (list 11 1.5 0 0)
           (cons 100 "AcDbText")
           (cons 73 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "0.500")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "0.500")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "5.150")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -1.1 0)
           (cons 40 0.2)
           (cons 1 "3.720")
           (cons 50 0)
           (cons 41 1)
           (cons 51 0)
           (cons 7 "Standard")
           (cons 71 0)
           (cons 72 0)
           (list 11 0 0 0)
           (cons 100 "AcDbAttributeDefinition")
           (cons 3 "Load Base Point (LB)")
           (cons 2 "LB")
           (cons 70 9)
           (cons 73 0)
           (cons 74 0)
          )
         )
         (entmake (list (cons 0 "ENDBLK")))
        )
       )
       ((= (strcase BLKNAME) (strcase "BC_MOTI-LG3-Trailer1"))
        (progn
         (entmake)
         (entmake
          (list
           (cons 0 "BLOCK")
           (cons 2 "BC_MOTI-LG3-Trailer1")
           (cons 70 2)
           (cons 4 "")
           (list 10 0 0 0)
          )
         )
         (entmake
          (list
           (cons 0 "POINT")
           (cons 100 "AcDbEntity")
           (cons 67 0)
           (cons 8 "0")
           (cons 100 "AcDbPoint")
           (list 10 4.49 -1.3 0)
           (cons 50 0)
          )
         )
         (entmake
          (list
           (cons 0 "POINT")
           (cons 100 "AcDbEntity")
           (cons 67 0)
           (cons 8 "0")
           (cons 100 "AcDbPoint")
           (list 10 4.49 1.3 0)
           (cons 50 0)
          )
         )
         (entmake
          (list
           (cons 0 "POINT")
           (cons 100 "AcDbEntity")
           (cons 67 0)
           (cons 8 "0")
           (cons 100 "AcDbPoint")
           (list 10 0.5 0 0)
           (cons 50 0)
          )
         )
         (entmake
          (list
           (cons 0 "POINT")
           (cons 100 "AcDbEntity")
           (cons 67 0)
           (cons 8 "0")
           (cons 100 "AcDbPoint")
           (list 10 4.49 0 0)
           (cons 50 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 4.49 0 0)
           (cons 40 0.17333333)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.931 1.073452)
           (cons 40 0)
           (cons 41 0)
           (cons 42 0)
           (cons 91 0)
           (list 10 3.931 1.247548)
           (cons 40 0)
           (cons 41 0)
           (cons 42 0)
           (cons 91 0)
           (list 10 4.08752 1.3)
           (cons 40 0)
           (cons 41 0)
           (cons 42 0)
           (cons 91 0)
           (list 10 4.89248 1.3)
           (cons 40 0)
           (cons 41 0)
           (cons 42 0)
           (cons 91 0)
           (list 10 5.049 1.247548)
           (cons 40 0)
           (cons 41 0)
           (cons 42 0)
           (cons 91 0)
           (list 10 5.049 1.073452)
           (cons 40 0)
           (cons 41 0)
           (cons 42 0)
           (cons 91 0)
           (list 10 4.89248 1.021)
           (cons 40 0)
           (cons 41 0)
           (cons 42 0)
           (cons 91 0)
           (list 10 4.08752 1.021)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.931 0.570452)
           (cons 40 0)
           (cons 41 0)
           (cons 42 0)
           (cons 91 0)
           (list 10 3.931 0.744548)
           (cons 40 0)
           (cons 41 0)
           (cons 42 0)
           (cons 91 0)
           (list 10 4.08752 0.797)
           (cons 40 0)
           (cons 41 0)
           (cons 42 0)
           (cons 91 0)
           (list 10 4.89248 0.797)
           (cons 40 0)
           (cons 41 0)
           (cons 42 0)
           (cons 91 0)
           (list 10 5.049 0.744548)
           (cons 40 0)
           (cons 41 0)
           (cons 42 0)
           (cons 91 0)
           (list 10 5.049 0.570452)
           (cons 40 0)
           (cons 41 0)
           (cons 42 0)
           (cons 91 0)
           (list 10 4.89248 0.518)
           (cons 40 0)
           (cons 41 0)
           (cons 42 0)
           (cons 91 0)
           (list 10 4.08752 0.518)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.931 -0.744548)
           (cons 40 0)
           (cons 41 0)
           (cons 42 0)
           (cons 91 0)
           (list 10 3.931 -0.570452)
           (cons 40 0)
           (cons 41 0)
           (cons 42 0)
           (cons 91 0)
           (list 10 4.08752 -0.518)
           (cons 40 0)
           (cons 41 0)
           (cons 42 0)
           (cons 91 0)
           (list 10 4.89248 -0.518)
           (cons 40 0)
           (cons 41 0)
           (cons 42 0)
           (cons 91 0)
           (list 10 5.049 -0.570452)
           (cons 40 0)
           (cons 41 0)
           (cons 42 0)
           (cons 91 0)
           (list 10 5.049 -0.744548)
           (cons 40 0)
           (cons 41 0)
           (cons 42 0)
           (cons 91 0)
           (list 10 4.89248 -0.797)
           (cons 40 0)
           (cons 41 0)
           (cons 42 0)
           (cons 91 0)
           (list 10 4.08752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.931 -1.247548)
           (cons 40 0)
           (cons 41 0)
           (cons 42 0)
           (cons 91 0)
           (list 10 3.931 -1.073452)
           (cons 40 0)
           (cons 41 0)
           (cons 42 0)
           (cons 91 0)
           (list 10 4.08752 -1.021)
           (cons 40 0)
           (cons 41 0)
           (cons 42 0)
           (cons 91 0)
           (list 10 4.89248 -1.021)
           (cons 40 0)
           (cons 41 0)
           (cons 42 0)
           (cons 91 0)
           (list 10 5.049 -1.073452)
           (cons 40 0)
           (cons 41 0)
           (cons 42 0)
           (cons 91 0)
           (list 10 5.049 -1.247548)
           (cons 40 0)
           (cons 41 0)
           (cons 42 0)
           (cons 91 0)
           (list 10 4.89248 -1.3)
           (cons 40 0)
           (cons 41 0)
           (cons 42 0)
           (cons 91 0)
           (list 10 4.08752 -1.3)
           (cons 40 0)
           (cons 41 0)
           (cons 42 0)
           (cons 91 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0.5 0 0)
           (cons 40 0.104)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.99 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.99 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "POLYLINE")
           (cons 100 "AcDbEntity")
           (cons 67 0)
           (cons 8 "Defpoints")
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "Defpoints")
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 3.931 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 3.931 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 5.049 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 5.049 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 4.99 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 4.99 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 5.049 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 5.049 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 3.931 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 3.931 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 0 0.5 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "Defpoints")
          )
         )
         (entmake
          (list
           (cons 0 "TEXT")
           (cons 100 "AcDbEntity")
           (cons 67 0)
           (cons 8 "0")
           (cons 100 "AcDbText")
           (list 10 1.33333333 -0.25 0)
           (cons 40 0.5)
           (cons 1 "2")
           (cons 50 0)
           (cons 41 1)
           (cons 51 0)
           (cons 7 "Standard")
           (cons 71 0)
           (cons 72 4)
           (list 11 1.5 0 0)
           (cons 100 "AcDbText")
           (cons 73 0)
          )
         )
         (entmake
          (list
           (cons 0 "ATTDEF")
           (cons 100 "AcDbEntity")
           (cons 67 0)
           (cons 8 "0")
           (cons 100 "AcDbText")
           (list 10 -0.3 0.56666667 0)
           (cons 40 0.2)
           (cons 1 "0.500")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 0.23333333 0)
           (cons 40 0.2)
           (cons 1 "0.500")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.1 0)
           (cons 40 0.2)
           (cons 1 "4.490")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.43333333 0)
           (cons 40 0.2)
           (cons 1 "4.490")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "BC_MOTI-LG3-Truck"))
        (progn
         (entmake)
         (entmake
          (list
           (cons 0 "BLOCK")
           (cons 2 "BC_MOTI-LG3-Truck")
           (cons 70 2)
           (cons 4 "")
           (list 10 0 0 0)
          )
         )
         (entmake
          (list
           (cons 0 "POINT")
           (cons 100 "AcDbEntity")
           (cons 67 0)
           (cons 8 "0")
           (cons 62 1)
           (cons 100 "AcDbPoint")
           (list 10 7.52 0 0)
           (cons 50 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 7.52 0 0)
           (cons 40 0.1524)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 7.9 -1.3 0)
           (cons 50 0)
          )
         )
         (entmake
          (list
           (cons 0 "POINT")
           (cons 100 "AcDbEntity")
           (cons 67 0)
           (cons 8 "0")
           (cons 100 "AcDbPoint")
           (list 10 7.9 1.3 0)
           (cons 50 0)
          )
         )
         (entmake
          (list
           (cons 0 "POINT")
           (cons 100 "AcDbEntity")
           (cons 67 0)
           (cons 8 "0")
           (cons 100 "AcDbPoint")
           (list 10 1.1 -1.3 0)
           (cons 50 0)
          )
         )
         (entmake
          (list
           (cons 0 "POINT")
           (cons 100 "AcDbEntity")
           (cons 67 0)
           (cons 8 "0")
           (cons 100 "AcDbPoint")
           (list 10 1.1 1.3 0)
           (cons 50 0)
          )
         )
         (entmake
          (list
           (cons 0 "POINT")
           (cons 100 "AcDbEntity")
           (cons 67 0)
           (cons 8 "0")
           (cons 100 "AcDbPoint")
           (list 10 1.1 0 0)
           (cons 50 0)
          )
         )
         (entmake
          (list
           (cons 0 "INSERT")
           (cons 100 "AcDbEntity")
           (cons 67 0)
           (cons 8 "0")
           (cons 100 "AcDbBlockReference")
           (cons 2 "WheelLeftM1")
           (list 10 1.1 -1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM1")
           (list 10 1.1 1.0206 0)
           (cons 41 1)
           (cons 42 1)
           (cons 43 1)
           (cons 50 0)
           (cons 70 0)
           (cons 71 0)
           (cons 44 0)
           (cons 45 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.341 1.073452)
           (cons 40 0)
           (cons 41 0)
           (cons 42 0)
           (cons 91 0)
           (list 10 7.341 1.247548)
           (cons 40 0)
           (cons 41 0)
           (cons 42 0)
           (cons 91 0)
           (list 10 7.49752 1.3)
           (cons 40 0)
           (cons 41 0)
           (cons 42 0)
           (cons 91 0)
           (list 10 8.30248 1.3)
           (cons 40 0)
           (cons 41 0)
           (cons 42 0)
           (cons 91 0)
           (list 10 8.459 1.247548)
           (cons 40 0)
           (cons 41 0)
           (cons 42 0)
           (cons 91 0)
           (list 10 8.459 1.073452)
           (cons 40 0)
           (cons 41 0)
           (cons 42 0)
           (cons 91 0)
           (list 10 8.30248 1.021)
           (cons 40 0)
           (cons 41 0)
           (cons 42 0)
           (cons 91 0)
           (list 10 7.49752 1.021)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.341 0.570452)
           (cons 40 0)
           (cons 41 0)
           (cons 42 0)
           (cons 91 0)
           (list 10 7.341 0.744548)
           (cons 40 0)
           (cons 41 0)
           (cons 42 0)
           (cons 91 0)
           (list 10 7.49752 0.797)
           (cons 40 0)
           (cons 41 0)
           (cons 42 0)
           (cons 91 0)
           (list 10 8.30248 0.797)
           (cons 40 0)
           (cons 41 0)
           (cons 42 0)
           (cons 91 0)
           (list 10 8.459 0.744548)
           (cons 40 0)
           (cons 41 0)
           (cons 42 0)
           (cons 91 0)
           (list 10 8.459 0.570452)
           (cons 40 0)
           (cons 41 0)
           (cons 42 0)
           (cons 91 0)
           (list 10 8.30248 0.518)
           (cons 40 0)
           (cons 41 0)
           (cons 42 0)
           (cons 91 0)
           (list 10 7.49752 0.518)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.341 -0.744548)
           (cons 40 0)
           (cons 41 0)
           (cons 42 0)
           (cons 91 0)
           (list 10 7.341 -0.570452)
           (cons 40 0)
           (cons 41 0)
           (cons 42 0)
           (cons 91 0)
           (list 10 7.49752 -0.518)
           (cons 40 0)
           (cons 41 0)
           (cons 42 0)
           (cons 91 0)
           (list 10 8.30248 -0.518)
           (cons 40 0)
           (cons 41 0)
           (cons 42 0)
           (cons 91 0)
           (list 10 8.459 -0.570452)
           (cons 40 0)
           (cons 41 0)
           (cons 42 0)
           (cons 91 0)
           (list 10 8.459 -0.744548)
           (cons 40 0)
           (cons 41 0)
           (cons 42 0)
           (cons 91 0)
           (list 10 8.30248 -0.797)
           (cons 40 0)
           (cons 41 0)
           (cons 42 0)
           (cons 91 0)
           (list 10 7.49752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.341 -1.247548)
           (cons 40 0)
           (cons 41 0)
           (cons 42 0)
           (cons 91 0)
           (list 10 7.341 -1.073452)
           (cons 40 0)
           (cons 41 0)
           (cons 42 0)
           (cons 91 0)
           (list 10 7.49752 -1.021)
           (cons 40 0)
           (cons 41 0)
           (cons 42 0)
           (cons 91 0)
           (list 10 8.30248 -1.021)
           (cons 40 0)
           (cons 41 0)
           (cons 42 0)
           (cons 91 0)
           (list 10 8.459 -1.073452)
           (cons 40 0)
           (cons 41 0)
           (cons 42 0)
           (cons 91 0)
           (list 10 8.459 -1.247548)
           (cons 40 0)
           (cons 41 0)
           (cons 42 0)
           (cons 91 0)
           (list 10 8.30248 -1.3)
           (cons 40 0)
           (cons 41 0)
           (cons 42 0)
           (cons 91 0)
           (list 10 7.49752 -1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.38016 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.38016 -0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 11.16 -0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 11.16 0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.38016 0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.38016 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "Defpoints")
           (cons 100 "AcDbPolyline")
           (cons 90 8)
           (cons 70 1)
           (cons 43 0)
           (cons 38 0)
           (cons 39 0)
           (list 10 0 -1.3)
           (cons 40 0)
           (cons 41 0)
           (cons 42 0)
           (cons 91 0)
           (list 10 8.459 -1.3)
           (cons 40 0)
           (cons 41 0)
           (cons 42 0)
           (cons 91 0)
           (list 10 8.459 -0.5188)
           (cons 40 0)
           (cons 41 0)
           (cons 42 0)
           (cons 91 0)
           (list 10 11.16 -0.5188)
           (cons 40 0)
           (cons 41 0)
           (cons 42 0)
           (cons 91 0)
           (list 10 11.16 0.5188)
           (cons 40 0)
           (cons 41 0)
           (cons 42 0)
           (cons 91 0)
           (list 10 8.459 0.5188)
           (cons 40 0)
           (cons 41 0)
           (cons 42 0)
           (cons 91 0)
           (list 10 8.459 1.3)
           (cons 40 0)
           (cons 41 0)
           (cons 42 0)
           (cons 91 0)
           (list 10 0 1.3)
           (cons 40 0)
           (cons 41 0)
           (cons 42 0)
           (cons 91 0)
          )
         )
         (entmake
          (list
           (cons 0 "TEXT")
           (cons 100 "AcDbEntity")
           (cons 67 0)
           (cons 8 "0")
           (cons 100 "AcDbText")
           (list 10 2.04047619 -0.25 0)
           (cons 40 0.5)
           (cons 1 "1")
           (cons 50 0)
           (cons 41 1)
           (cons 51 0)
           (cons 7 "Standard")
           (cons 71 0)
           (cons 72 4)
           (list 11 2.1 0 0)
           (cons 100 "AcDbText")
           (cons 73 0)
          )
         )
         (entmake
          (list
           (cons 0 "POINT")
           (cons 100 "AcDbEntity")
           (cons 67 0)
           (cons 8 "0")
           (cons 100 "AcDbPoint")
           (list 10 10.66 0 0)
           (cons 50 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 10.66 0 0)
           (cons 40 0.17333333)
          )
         )
         (entmake
          (list
           (cons 0 "ATTDEF")
           (cons 100 "AcDbEntity")
           (cons 67 0)
           (cons 8 "0")
           (cons 100 "AcDbText")
           (list 10 0.4 0.56666667 0)
           (cons 40 0.2)
           (cons 1 "1.100")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.4 0.23333333 0)
           (cons 40 0.2)
           (cons 1 "1.100")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.4 -0.1 0)
           (cons 40 0.2)
           (cons 1 "7.900")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.4 -0.43333333 0)
           (cons 40 0.2)
           (cons 1 "10.660")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.4 -0.76666667 0)
           (cons 40 0.2)
           (cons 1 "32.983")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.4 -1.1 0)
           (cons 40 0.2)
           (cons 1 "7.52")
           (cons 50 0)
           (cons 41 1)
           (cons 51 0)
           (cons 7 "Standard")
           (cons 71 0)
           (cons 72 0)
           (list 11 0 0 0)
           (cons 100 "AcDbAttributeDefinition")
           (cons 3 "Load Angle Point (LA)")
           (cons 2 "LA")
           (cons 70 9)
           (cons 73 0)
           (cons 74 0)
          )
         )
         (entmake (list (cons 0 "ENDBLK")))
        )
       )
       ((= (strcase BLKNAME) (strcase "AASHTO-2011-WB-67-TRAILER"))
        (progn
         (entmake)
         (entmake
          (list
           (cons 0 "BLOCK")
           (cons 2 "AASHTO-2011-WB-67-TRAILER")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 53 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 53 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 3 0 0)
           (cons 40 0.34)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 44.84868766 -2.42766667)
           (cons 40 0)
           (cons 41 0)
           (cons 42 0)
           (cons 91 0)
           (list 10 44.84868766 -1.85566667)
           (cons 40 0)
           (cons 41 0)
           (cons 42 0)
           (cons 91 0)
           (list 10 45.31068766 -1.68333333)
           (cons 40 0)
           (cons 41 0)
           (cons 42 0)
           (cons 91 0)
           (list 10 47.68668766 -1.68333333)
           (cons 40 0)
           (cons 41 0)
           (cons 42 0)
           (cons 91 0)
           (list 10 48.14868766 -1.85566667)
           (cons 40 0)
           (cons 41 0)
           (cons 42 0)
           (cons 91 0)
           (list 10 48.14868766 -2.42766667)
           (cons 40 0)
           (cons 41 0)
           (cons 42 0)
           (cons 91 0)
           (list 10 47.68668766 -2.6)
           (cons 40 0)
           (cons 41 0)
           (cons 42 0)
           (cons 91 0)
           (list 10 45.31068766 -2.6)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 44.84868766 -4.07766667)
           (cons 40 0)
           (cons 41 0)
           (cons 42 0)
           (cons 91 0)
           (list 10 44.84868766 -3.50566667)
           (cons 40 0)
           (cons 41 0)
           (cons 42 0)
           (cons 91 0)
           (list 10 45.31068766 -3.33333333)
           (cons 40 0)
           (cons 41 0)
           (cons 42 0)
           (cons 91 0)
           (list 10 47.68668766 -3.33333333)
           (cons 40 0)
           (cons 41 0)
           (cons 42 0)
           (cons 91 0)
           (list 10 48.14868766 -3.50566667)
           (cons 40 0)
           (cons 41 0)
           (cons 42 0)
           (cons 91 0)
           (list 10 48.14868766 -4.07766667)
           (cons 40 0)
           (cons 41 0)
           (cons 42 0)
           (cons 91 0)
           (list 10 47.68668766 -4.25)
           (cons 40 0)
           (cons 41 0)
           (cons 42 0)
           (cons 91 0)
           (list 10 45.31068766 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 44.84868766 1.85566667)
           (cons 40 0)
           (cons 41 0)
           (cons 42 0)
           (cons 91 0)
           (list 10 44.84868766 2.42766667)
           (cons 40 0)
           (cons 41 0)
           (cons 42 0)
           (cons 91 0)
           (list 10 45.31068766 2.6)
           (cons 40 0)
           (cons 41 0)
           (cons 42 0)
           (cons 91 0)
           (list 10 47.68668766 2.6)
           (cons 40 0)
           (cons 41 0)
           (cons 42 0)
           (cons 91 0)
           (list 10 48.14868766 2.42766667)
           (cons 40 0)
           (cons 41 0)
           (cons 42 0)
           (cons 91 0)
           (list 10 48.14868766 1.85566667)
           (cons 40 0)
           (cons 41 0)
           (cons 42 0)
           (cons 91 0)
           (list 10 47.68668766 1.68333333)
           (cons 40 0)
           (cons 41 0)
           (cons 42 0)
           (cons 91 0)
           (list 10 45.31068766 1.68333333)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 44.84868766 3.50566667)
           (cons 40 0)
           (cons 41 0)
           (cons 42 0)
           (cons 91 0)
           (list 10 44.84868766 4.07766667)
           (cons 40 0)
           (cons 41 0)
           (cons 42 0)
           (cons 91 0)
           (list 10 45.31068766 4.25)
           (cons 40 0)
           (cons 41 0)
           (cons 42 0)
           (cons 91 0)
           (list 10 47.68668766 4.25)
           (cons 40 0)
           (cons 41 0)
           (cons 42 0)
           (cons 91 0)
           (list 10 48.14868766 4.07766667)
           (cons 40 0)
           (cons 41 0)
           (cons 42 0)
           (cons 91 0)
           (list 10 48.14868766 3.50566667)
           (cons 40 0)
           (cons 41 0)
           (cons 42 0)
           (cons 91 0)
           (list 10 47.68668766 3.33333333)
           (cons 40 0)
           (cons 41 0)
           (cons 42 0)
           (cons 91 0)
           (list 10 45.31068766 3.33333333)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 48.85131234 -2.42766667)
           (cons 40 0)
           (cons 41 0)
           (cons 42 0)
           (cons 91 0)
           (list 10 48.85131234 -1.85566667)
           (cons 40 0)
           (cons 41 0)
           (cons 42 0)
           (cons 91 0)
           (list 10 49.31331234 -1.68333333)
           (cons 40 0)
           (cons 41 0)
           (cons 42 0)
           (cons 91 0)
           (list 10 51.68931234 -1.68333333)
           (cons 40 0)
           (cons 41 0)
           (cons 42 0)
           (cons 91 0)
           (list 10 52.15131234 -1.85566667)
           (cons 40 0)
           (cons 41 0)
           (cons 42 0)
           (cons 91 0)
           (list 10 52.15131234 -2.42766667)
           (cons 40 0)
           (cons 41 0)
           (cons 42 0)
           (cons 91 0)
           (list 10 51.68931234 -2.6)
           (cons 40 0)
           (cons 41 0)
           (cons 42 0)
           (cons 91 0)
           (list 10 49.31331234 -2.6)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 48.85131234 -4.07766667)
           (cons 40 0)
           (cons 41 0)
           (cons 42 0)
           (cons 91 0)
           (list 10 48.85131234 -3.50566667)
           (cons 40 0)
           (cons 41 0)
           (cons 42 0)
           (cons 91 0)
           (list 10 49.31331234 -3.33333333)
           (cons 40 0)
           (cons 41 0)
           (cons 42 0)
           (cons 91 0)
           (list 10 51.68931234 -3.33333333)
           (cons 40 0)
           (cons 41 0)
           (cons 42 0)
           (cons 91 0)
           (list 10 52.15131234 -3.50566667)
           (cons 40 0)
           (cons 41 0)
           (cons 42 0)
           (cons 91 0)
           (list 10 52.15131234 -4.07766667)
           (cons 40 0)
           (cons 41 0)
           (cons 42 0)
           (cons 91 0)
           (list 10 51.68931234 -4.25)
           (cons 40 0)
           (cons 41 0)
           (cons 42 0)
           (cons 91 0)
           (list 10 49.31331234 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 48.85131234 1.85566667)
           (cons 40 0)
           (cons 41 0)
           (cons 42 0)
           (cons 91 0)
           (list 10 48.85131234 2.42766667)
           (cons 40 0)
           (cons 41 0)
           (cons 42 0)
           (cons 91 0)
           (list 10 49.31331234 2.6)
           (cons 40 0)
           (cons 41 0)
           (cons 42 0)
           (cons 91 0)
           (list 10 51.68931234 2.6)
           (cons 40 0)
           (cons 41 0)
           (cons 42 0)
           (cons 91 0)
           (list 10 52.15131234 2.42766667)
           (cons 40 0)
           (cons 41 0)
           (cons 42 0)
           (cons 91 0)
           (list 10 52.15131234 1.85566667)
           (cons 40 0)
           (cons 41 0)
           (cons 42 0)
           (cons 91 0)
           (list 10 51.68931234 1.68333333)
           (cons 40 0)
           (cons 41 0)
           (cons 42 0)
           (cons 91 0)
           (list 10 49.31331234 1.68333333)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 48.85131234 3.50566667)
           (cons 40 0)
           (cons 41 0)
           (cons 42 0)
           (cons 91 0)
           (list 10 48.85131234 4.07766667)
           (cons 40 0)
           (cons 41 0)
           (cons 42 0)
           (cons 91 0)
           (list 10 49.31331234 4.25)
           (cons 40 0)
           (cons 41 0)
           (cons 42 0)
           (cons 91 0)
           (list 10 51.68931234 4.25)
           (cons 40 0)
           (cons 41 0)
           (cons 42 0)
           (cons 91 0)
           (list 10 52.15131234 4.07766667)
           (cons 40 0)
           (cons 41 0)
           (cons 42 0)
           (cons 91 0)
           (list 10 52.15131234 3.50566667)
           (cons 40 0)
           (cons 41 0)
           (cons 42 0)
           (cons 91 0)
           (list 10 51.68931234 3.33333333)
           (cons 40 0)
           (cons 41 0)
           (cons 42 0)
           (cons 91 0)
           (list 10 49.31331234 3.33333333)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4.25 0)
           (cons 50 0)
          )
         )
         (entmake
          (list
           (cons 0 "POINT")
           (cons 100 "AcDbEntity")
           (cons 67 0)
           (cons 8 "0")
           (cons 100 "AcDbPoint")
           (list 10 0 4.25 0)
           (cons 50 0)
          )
         )
         (entmake
          (list
           (cons 0 "POINT")
           (cons 100 "AcDbEntity")
           (cons 67 0)
           (cons 8 "0")
           (cons 100 "AcDbPoint")
           (list 10 53 -4.25 0)
           (cons 50 0)
          )
         )
         (entmake
          (list
           (cons 0 "POINT")
           (cons 100 "AcDbEntity")
           (cons 67 0)
           (cons 8 "0")
           (cons 100 "AcDbPoint")
           (list 10 53 4.25 0)
           (cons 50 0)
          )
         )
         (entmake
          (list
           (cons 0 "POINT")
           (cons 100 "AcDbEntity")
           (cons 67 0)
           (cons 8 "0")
           (cons 100 "AcDbPoint")
           (list 10 48.5 -4.25 0)
           (cons 50 0)
          )
         )
         (entmake
          (list
           (cons 0 "POINT")
           (cons 100 "AcDbEntity")
           (cons 67 0)
           (cons 8 "0")
           (cons 100 "AcDbPoint")
           (list 10 48.5 4.25 0)
           (cons 50 0)
          )
         )
         (entmake
          (list
           (cons 0 "POINT")
           (cons 100 "AcDbEntity")
           (cons 67 0)
           (cons 8 "0")
           (cons 100 "AcDbPoint")
           (list 10 3 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4.25)
           (cons 40 0)
           (cons 41 0)
           (cons 42 0)
           (cons 91 0)
           (list 10 53 -4.25)
           (cons 40 0)
           (cons 41 0)
           (cons 42 0)
           (cons 91 0)
           (list 10 53 4.25)
           (cons 40 0)
           (cons 41 0)
           (cons 42 0)
           (cons 91 0)
           (list 10 0 4.25)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.70341207 1.85914261 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 0.76552931 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -0.32808399 0)
           (cons 40 0.65616798)
           (cons 1 "48.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-67-TRUCK"))
        (progn
         (entmake)
         (entmake
          (list
           (cons 0 "BLOCK")
           (cons 2 "AASHTO-2011-WB-67-TRUCK")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15 -1.43333333 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 25.6 -1.43333333 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 25.6 1.43333333 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15 1.43333333 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 23.5 0 0)
           (cons 40 1.14285714)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 24.30812204 -0.80812204 0)
           (list 11 24.30812204 0.80812204 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 19.56666667 -2.17766667)
           (cons 40 0)
           (cons 41 0)
           (cons 42 0)
           (cons 91 0)
           (list 10 19.56666667 -1.60566667)
           (cons 40 0)
           (cons 41 0)
           (cons 42 0)
           (cons 91 0)
           (list 10 20.08 -1.43333333)
           (cons 40 0)
           (cons 41 0)
           (cons 42 0)
           (cons 91 0)
           (list 10 22.72 -1.43333333)
           (cons 40 0)
           (cons 41 0)
           (cons 42 0)
           (cons 91 0)
           (list 10 23.23333333 -1.60566667)
           (cons 40 0)
           (cons 41 0)
           (cons 42 0)
           (cons 91 0)
           (list 10 23.23333333 -2.17766667)
           (cons 40 0)
           (cons 41 0)
           (cons 42 0)
           (cons 91 0)
           (list 10 22.72 -2.35)
           (cons 40 0)
           (cons 41 0)
           (cons 42 0)
           (cons 91 0)
           (list 10 20.08 -2.35)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 19.56666667 -3.82766667)
           (cons 40 0)
           (cons 41 0)
           (cons 42 0)
           (cons 91 0)
           (list 10 19.56666667 -3.25566667)
           (cons 40 0)
           (cons 41 0)
           (cons 42 0)
           (cons 91 0)
           (list 10 20.08 -3.08333333)
           (cons 40 0)
           (cons 41 0)
           (cons 42 0)
           (cons 91 0)
           (list 10 22.72 -3.08333333)
           (cons 40 0)
           (cons 41 0)
           (cons 42 0)
           (cons 91 0)
           (list 10 23.23333333 -3.25566667)
           (cons 40 0)
           (cons 41 0)
           (cons 42 0)
           (cons 91 0)
           (list 10 23.23333333 -3.82766667)
           (cons 40 0)
           (cons 41 0)
           (cons 42 0)
           (cons 91 0)
           (list 10 22.72 -4)
           (cons 40 0)
           (cons 41 0)
           (cons 42 0)
           (cons 91 0)
           (list 10 20.08 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 19.56666667 1.60566667)
           (cons 40 0)
           (cons 41 0)
           (cons 42 0)
           (cons 91 0)
           (list 10 19.56666667 2.17766667)
           (cons 40 0)
           (cons 41 0)
           (cons 42 0)
           (cons 91 0)
           (list 10 20.08 2.35)
           (cons 40 0)
           (cons 41 0)
           (cons 42 0)
           (cons 91 0)
           (list 10 22.72 2.35)
           (cons 40 0)
           (cons 41 0)
           (cons 42 0)
           (cons 91 0)
           (list 10 23.23333333 2.17766667)
           (cons 40 0)
           (cons 41 0)
           (cons 42 0)
           (cons 91 0)
           (list 10 23.23333333 1.60566667)
           (cons 40 0)
           (cons 41 0)
           (cons 42 0)
           (cons 91 0)
           (list 10 22.72 1.43333333)
           (cons 40 0)
           (cons 41 0)
           (cons 42 0)
           (cons 91 0)
           (list 10 20.08 1.43333333)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 19.56666667 3.25566667)
           (cons 40 0)
           (cons 41 0)
           (cons 42 0)
           (cons 91 0)
           (list 10 19.56666667 3.82766667)
           (cons 40 0)
           (cons 41 0)
           (cons 42 0)
           (cons 91 0)
           (list 10 20.08 4)
           (cons 40 0)
           (cons 41 0)
           (cons 42 0)
           (cons 91 0)
           (list 10 22.72 4)
           (cons 40 0)
           (cons 41 0)
           (cons 42 0)
           (cons 91 0)
           (list 10 23.23333333 3.82766667)
           (cons 40 0)
           (cons 41 0)
           (cons 42 0)
           (cons 91 0)
           (list 10 23.23333333 3.25566667)
           (cons 40 0)
           (cons 41 0)
           (cons 42 0)
           (cons 91 0)
           (list 10 22.72 3.08333333)
           (cons 40 0)
           (cons 41 0)
           (cons 42 0)
           (cons 91 0)
           (list 10 20.08 3.08333333)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.76666667 -2.17766667)
           (cons 40 0)
           (cons 41 0)
           (cons 42 0)
           (cons 91 0)
           (list 10 23.76666667 -1.60566667)
           (cons 40 0)
           (cons 41 0)
           (cons 42 0)
           (cons 91 0)
           (list 10 24.28 -1.43333333)
           (cons 40 0)
           (cons 41 0)
           (cons 42 0)
           (cons 91 0)
           (list 10 26.92 -1.43333333)
           (cons 40 0)
           (cons 41 0)
           (cons 42 0)
           (cons 91 0)
           (list 10 27.43333333 -1.60566667)
           (cons 40 0)
           (cons 41 0)
           (cons 42 0)
           (cons 91 0)
           (list 10 27.43333333 -2.17766667)
           (cons 40 0)
           (cons 41 0)
           (cons 42 0)
           (cons 91 0)
           (list 10 26.92 -2.35)
           (cons 40 0)
           (cons 41 0)
           (cons 42 0)
           (cons 91 0)
           (list 10 24.28 -2.35)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.76666667 -3.82766667)
           (cons 40 0)
           (cons 41 0)
           (cons 42 0)
           (cons 91 0)
           (list 10 23.76666667 -3.25566667)
           (cons 40 0)
           (cons 41 0)
           (cons 42 0)
           (cons 91 0)
           (list 10 24.28 -3.08333333)
           (cons 40 0)
           (cons 41 0)
           (cons 42 0)
           (cons 91 0)
           (list 10 26.92 -3.08333333)
           (cons 40 0)
           (cons 41 0)
           (cons 42 0)
           (cons 91 0)
           (list 10 27.43333333 -3.25566667)
           (cons 40 0)
           (cons 41 0)
           (cons 42 0)
           (cons 91 0)
           (list 10 27.43333333 -3.82766667)
           (cons 40 0)
           (cons 41 0)
           (cons 42 0)
           (cons 91 0)
           (list 10 26.92 -4)
           (cons 40 0)
           (cons 41 0)
           (cons 42 0)
           (cons 91 0)
           (list 10 24.28 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.76666667 1.60566667)
           (cons 40 0)
           (cons 41 0)
           (cons 42 0)
           (cons 91 0)
           (list 10 23.76666667 2.17766667)
           (cons 40 0)
           (cons 41 0)
           (cons 42 0)
           (cons 91 0)
           (list 10 24.28 2.35)
           (cons 40 0)
           (cons 41 0)
           (cons 42 0)
           (cons 91 0)
           (list 10 26.92 2.35)
           (cons 40 0)
           (cons 41 0)
           (cons 42 0)
           (cons 91 0)
           (list 10 27.43333333 2.17766667)
           (cons 40 0)
           (cons 41 0)
           (cons 42 0)
           (cons 91 0)
           (list 10 27.43333333 1.60566667)
           (cons 40 0)
           (cons 41 0)
           (cons 42 0)
           (cons 91 0)
           (list 10 26.92 1.43333333)
           (cons 40 0)
           (cons 41 0)
           (cons 42 0)
           (cons 91 0)
           (list 10 24.28 1.43333333)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.76666667 3.25566667)
           (cons 40 0)
           (cons 41 0)
           (cons 42 0)
           (cons 91 0)
           (list 10 23.76666667 3.82766667)
           (cons 40 0)
           (cons 41 0)
           (cons 42 0)
           (cons 91 0)
           (list 10 24.28 4)
           (cons 40 0)
           (cons 41 0)
           (cons 42 0)
           (cons 91 0)
           (list 10 26.92 4)
           (cons 40 0)
           (cons 41 0)
           (cons 42 0)
           (cons 91 0)
           (list 10 27.43333333 3.82766667)
           (cons 40 0)
           (cons 41 0)
           (cons 42 0)
           (cons 91 0)
           (list 10 27.43333333 3.25566667)
           (cons 40 0)
           (cons 41 0)
           (cons 42 0)
           (cons 91 0)
           (list 10 26.92 3.08333333)
           (cons 40 0)
           (cons 41 0)
           (cons 42 0)
           (cons 91 0)
           (list 10 24.28 3.08333333)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4 0)
           (cons 50 0)
          )
         )
         (entmake
          (list
           (cons 0 "POINT")
           (cons 100 "AcDbEntity")
           (cons 67 0)
           (cons 8 "0")
           (cons 100 "AcDbPoint")
           (list 10 0 4 0)
           (cons 50 0)
          )
         )
         (entmake
          (list
           (cons 0 "POINT")
           (cons 100 "AcDbEntity")
           (cons 67 0)
           (cons 8 "0")
           (cons 100 "AcDbPoint")
           (list 10 4 4 0)
           (cons 50 0)
          )
         )
         (entmake
          (list
           (cons 0 "POINT")
           (cons 100 "AcDbEntity")
           (cons 67 0)
           (cons 8 "0")
           (cons 100 "AcDbPoint")
           (list 10 4 0 0)
           (cons 50 0)
          )
         )
         (entmake
          (list
           (cons 0 "POINT")
           (cons 100 "AcDbEntity")
           (cons 67 0)
           (cons 8 "0")
           (cons 100 "AcDbPoint")
           (list 10 23.5 4 0)
           (cons 50 0)
          )
         )
         (entmake
          (list
           (cons 0 "POINT")
           (cons 100 "AcDbEntity")
           (cons 67 0)
           (cons 8 "0")
           (cons 100 "AcDbPoint")
           (list 10 23.5 -4 0)
           (cons 50 0)
          )
         )
         (entmake
          (list
           (cons 0 "POINT")
           (cons 100 "AcDbEntity")
           (cons 67 0)
           (cons 8 "0")
           (cons 100 "AcDbPoint")
           (list 10 23.5 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4)
           (cons 40 0)
           (cons 41 0)
           (cons 42 0)
           (cons 91 0)
           (list 10 25.6 -4)
           (cons 40 0)
           (cons 41 0)
           (cons 42 0)
           (cons 91 0)
           (list 10 25.6 4)
           (cons 40 0)
           (cons 41 0)
           (cons 42 0)
           (cons 91 0)
           (list 10 0 4)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelLeft1")
           (list 10 4 -3.08333333 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRight1")
           (list 10 4 3.08333333 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 1.70341207 1.85914261 0)
           (cons 40 0.65616798)
           (cons 1 "4.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 0.76552931 0)
           (cons 40 0.65616798)
           (cons 1 "4.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -0.32808399 0)
           (cons 40 0.65616798)
           (cons 1 "23.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -1.42169729 0)
           (cons 40 0.65616798)
           (cons 1 "23.500")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -2.51531059 0)
           (cons 40 0.65616798)
           (cons 1 "25.8")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-109D-TRAILER"))
        (progn
         (entmake)
         (entmake
          (list
           (cons 0 "BLOCK")
           (cons 2 "AASHTO-2011-WB-109D-TRAILER")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4.25)
           (cons 40 0)
           (cons 41 0)
           (cons 42 0)
           (cons 91 0)
           (list 10 48 -4.25)
           (cons 40 0)
           (cons 41 0)
           (cons 42 0)
           (cons 91 0)
           (list 10 48 4.25)
           (cons 40 0)
           (cons 41 0)
           (cons 42 0)
           (cons 91 0)
           (list 10 0 4.25)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 48 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 48 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 48 0 0)
           (list 11 48 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 48 0 0)
           (cons 40 0.33333333)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 3 0 0)
           (cons 40 0.34)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 39.832021 -2.59333333)
           (cons 40 0)
           (cons 41 0)
           (cons 42 0)
           (cons 91 0)
           (list 10 39.832021 -2.07333333)
           (cons 40 0)
           (cons 41 0)
           (cons 42 0)
           (cons 91 0)
           (list 10 40.29868766 -1.91666667)
           (cons 40 0)
           (cons 41 0)
           (cons 42 0)
           (cons 91 0)
           (list 10 42.69868766 -1.91666667)
           (cons 40 0)
           (cons 41 0)
           (cons 42 0)
           (cons 91 0)
           (list 10 43.16535433 -2.07333333)
           (cons 40 0)
           (cons 41 0)
           (cons 42 0)
           (cons 91 0)
           (list 10 43.16535433 -2.59333333)
           (cons 40 0)
           (cons 41 0)
           (cons 42 0)
           (cons 91 0)
           (list 10 42.69868766 -2.75)
           (cons 40 0)
           (cons 41 0)
           (cons 42 0)
           (cons 91 0)
           (list 10 40.29868766 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 39.832021 -4.09333333)
           (cons 40 0)
           (cons 41 0)
           (cons 42 0)
           (cons 91 0)
           (list 10 39.832021 -3.57333333)
           (cons 40 0)
           (cons 41 0)
           (cons 42 0)
           (cons 91 0)
           (list 10 40.29868766 -3.41666667)
           (cons 40 0)
           (cons 41 0)
           (cons 42 0)
           (cons 91 0)
           (list 10 42.69868766 -3.41666667)
           (cons 40 0)
           (cons 41 0)
           (cons 42 0)
           (cons 91 0)
           (list 10 43.16535433 -3.57333333)
           (cons 40 0)
           (cons 41 0)
           (cons 42 0)
           (cons 91 0)
           (list 10 43.16535433 -4.09333333)
           (cons 40 0)
           (cons 41 0)
           (cons 42 0)
           (cons 91 0)
           (list 10 42.69868766 -4.25)
           (cons 40 0)
           (cons 41 0)
           (cons 42 0)
           (cons 91 0)
           (list 10 40.29868766 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 39.832021 2.07333333)
           (cons 40 0)
           (cons 41 0)
           (cons 42 0)
           (cons 91 0)
           (list 10 39.832021 2.59333333)
           (cons 40 0)
           (cons 41 0)
           (cons 42 0)
           (cons 91 0)
           (list 10 40.29868766 2.75)
           (cons 40 0)
           (cons 41 0)
           (cons 42 0)
           (cons 91 0)
           (list 10 42.69868766 2.75)
           (cons 40 0)
           (cons 41 0)
           (cons 42 0)
           (cons 91 0)
           (list 10 43.16535433 2.59333333)
           (cons 40 0)
           (cons 41 0)
           (cons 42 0)
           (cons 91 0)
           (list 10 43.16535433 2.07333333)
           (cons 40 0)
           (cons 41 0)
           (cons 42 0)
           (cons 91 0)
           (list 10 42.69868766 1.91666667)
           (cons 40 0)
           (cons 41 0)
           (cons 42 0)
           (cons 91 0)
           (list 10 40.29868766 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 39.832021 3.57333333)
           (cons 40 0)
           (cons 41 0)
           (cons 42 0)
           (cons 91 0)
           (list 10 39.832021 4.09333333)
           (cons 40 0)
           (cons 41 0)
           (cons 42 0)
           (cons 91 0)
           (list 10 40.29868766 4.25)
           (cons 40 0)
           (cons 41 0)
           (cons 42 0)
           (cons 91 0)
           (list 10 42.69868766 4.25)
           (cons 40 0)
           (cons 41 0)
           (cons 42 0)
           (cons 91 0)
           (list 10 43.16535433 4.09333333)
           (cons 40 0)
           (cons 41 0)
           (cons 42 0)
           (cons 91 0)
           (list 10 43.16535433 3.57333333)
           (cons 40 0)
           (cons 41 0)
           (cons 42 0)
           (cons 91 0)
           (list 10 42.69868766 3.41666667)
           (cons 40 0)
           (cons 41 0)
           (cons 42 0)
           (cons 91 0)
           (list 10 40.29868766 3.41666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 43.83464567 -2.59333333)
           (cons 40 0)
           (cons 41 0)
           (cons 42 0)
           (cons 91 0)
           (list 10 43.83464567 -2.07333333)
           (cons 40 0)
           (cons 41 0)
           (cons 42 0)
           (cons 91 0)
           (list 10 44.30131234 -1.91666667)
           (cons 40 0)
           (cons 41 0)
           (cons 42 0)
           (cons 91 0)
           (list 10 46.70131234 -1.91666667)
           (cons 40 0)
           (cons 41 0)
           (cons 42 0)
           (cons 91 0)
           (list 10 47.167979 -2.07333333)
           (cons 40 0)
           (cons 41 0)
           (cons 42 0)
           (cons 91 0)
           (list 10 47.167979 -2.59333333)
           (cons 40 0)
           (cons 41 0)
           (cons 42 0)
           (cons 91 0)
           (list 10 46.70131234 -2.75)
           (cons 40 0)
           (cons 41 0)
           (cons 42 0)
           (cons 91 0)
           (list 10 44.30131234 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 43.83464567 -4.09333333)
           (cons 40 0)
           (cons 41 0)
           (cons 42 0)
           (cons 91 0)
           (list 10 43.83464567 -3.57333333)
           (cons 40 0)
           (cons 41 0)
           (cons 42 0)
           (cons 91 0)
           (list 10 44.30131234 -3.41666667)
           (cons 40 0)
           (cons 41 0)
           (cons 42 0)
           (cons 91 0)
           (list 10 46.70131234 -3.41666667)
           (cons 40 0)
           (cons 41 0)
           (cons 42 0)
           (cons 91 0)
           (list 10 47.167979 -3.57333333)
           (cons 40 0)
           (cons 41 0)
           (cons 42 0)
           (cons 91 0)
           (list 10 47.167979 -4.09333333)
           (cons 40 0)
           (cons 41 0)
           (cons 42 0)
           (cons 91 0)
           (list 10 46.70131234 -4.25)
           (cons 40 0)
           (cons 41 0)
           (cons 42 0)
           (cons 91 0)
           (list 10 44.30131234 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 43.83464567 2.07333333)
           (cons 40 0)
           (cons 41 0)
           (cons 42 0)
           (cons 91 0)
           (list 10 43.83464567 2.59333333)
           (cons 40 0)
           (cons 41 0)
           (cons 42 0)
           (cons 91 0)
           (list 10 44.30131234 2.75)
           (cons 40 0)
           (cons 41 0)
           (cons 42 0)
           (cons 91 0)
           (list 10 46.70131234 2.75)
           (cons 40 0)
           (cons 41 0)
           (cons 42 0)
           (cons 91 0)
           (list 10 47.167979 2.59333333)
           (cons 40 0)
           (cons 41 0)
           (cons 42 0)
           (cons 91 0)
           (list 10 47.167979 2.07333333)
           (cons 40 0)
           (cons 41 0)
           (cons 42 0)
           (cons 91 0)
           (list 10 46.70131234 1.91666667)
           (cons 40 0)
           (cons 41 0)
           (cons 42 0)
           (cons 91 0)
           (list 10 44.30131234 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 43.83464567 3.57333333)
           (cons 40 0)
           (cons 41 0)
           (cons 42 0)
           (cons 91 0)
           (list 10 43.83464567 4.09333333)
           (cons 40 0)
           (cons 41 0)
           (cons 42 0)
           (cons 91 0)
           (list 10 44.30131234 4.25)
           (cons 40 0)
           (cons 41 0)
           (cons 42 0)
           (cons 91 0)
           (list 10 46.70131234 4.25)
           (cons 40 0)
           (cons 41 0)
           (cons 42 0)
           (cons 91 0)
           (list 10 47.167979 4.09333333)
           (cons 40 0)
           (cons 41 0)
           (cons 42 0)
           (cons 91 0)
           (list 10 47.167979 3.57333333)
           (cons 40 0)
           (cons 41 0)
           (cons 42 0)
           (cons 91 0)
           (list 10 46.70131234 3.41666667)
           (cons 40 0)
           (cons 41 0)
           (cons 42 0)
           (cons 91 0)
           (list 10 44.30131234 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4.25 0)
           (cons 50 0)
          )
         )
         (entmake
          (list
           (cons 0 "POINT")
           (cons 100 "AcDbEntity")
           (cons 67 0)
           (cons 8 "0")
           (cons 100 "AcDbPoint")
           (list 10 48 -4.25 0)
           (cons 50 0)
          )
         )
         (entmake
          (list
           (cons 0 "POINT")
           (cons 100 "AcDbEntity")
           (cons 67 0)
           (cons 8 "0")
           (cons 100 "AcDbPoint")
           (list 10 0 4.25 0)
           (cons 50 0)
          )
         )
         (entmake
          (list
           (cons 0 "POINT")
           (cons 100 "AcDbEntity")
           (cons 67 0)
           (cons 8 "0")
           (cons 100 "AcDbPoint")
           (list 10 48 4.25 0)
           (cons 50 0)
          )
         )
         (entmake
          (list
           (cons 0 "POINT")
           (cons 100 "AcDbEntity")
           (cons 67 0)
           (cons 8 "0")
           (cons 100 "AcDbPoint")
           (list 10 3 0 0)
           (cons 50 0)
          )
         )
         (entmake
          (list
           (cons 0 "POINT")
           (cons 100 "AcDbEntity")
           (cons 67 0)
           (cons 8 "0")
           (cons 100 "AcDbPoint")
           (list 10 48 0 0)
           (cons 50 0)
          )
         )
         (entmake
          (list
           (cons 0 "POINT")
           (cons 100 "AcDbEntity")
           (cons 67 0)
           (cons 8 "0")
           (cons 100 "AcDbPoint")
           (list 10 43.5 4.25 0)
           (cons 50 0)
          )
         )
         (entmake
          (list
           (cons 0 "POINT")
           (cons 100 "AcDbEntity")
           (cons 67 0)
           (cons 8 "0")
           (cons 100 "AcDbPoint")
           (list 10 43.5 -4.25 0)
           (cons 50 0)
          )
         )
         (entmake
          (list
           (cons 0 "ATTDEF")
           (cons 100 "AcDbEntity")
           (cons 67 0)
           (cons 8 "0")
           (cons 100 "AcDbText")
           (list 10 0.70341207 1.85914261 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 0.76552931 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -0.32808399 0)
           (cons 40 0.65616798)
           (cons 1 "43.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -1.42169729 0)
           (cons 40 0.65616798)
           (cons 1 "48.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-109D-PUP"))
        (progn
         (entmake)
         (entmake
          (list
           (cons 0 "BLOCK")
           (cons 2 "AASHTO-2011-WB-109D-PUP")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 3)
           (cons 70 1)
           (cons 43 0)
           (cons 38 0)
           (cons 39 0)
           (list 10 0 0)
           (cons 40 0)
           (cons 41 0)
           (cons 42 0)
           (cons 91 0)
           (list 10 10 4.25)
           (cons 40 0)
           (cons 41 0)
           (cons 42 0)
           (cons 91 0)
           (list 10 10 -4.25)
           (cons 40 0)
           (cons 41 0)
           (cons 42 0)
           (cons 91 0)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 10 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.56666667)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.332021 -2.59333333)
           (cons 40 0)
           (cons 41 0)
           (cons 42 0)
           (cons 91 0)
           (list 10 6.332021 -2.07333333)
           (cons 40 0)
           (cons 41 0)
           (cons 42 0)
           (cons 91 0)
           (list 10 6.79868766 -1.91666667)
           (cons 40 0)
           (cons 41 0)
           (cons 42 0)
           (cons 91 0)
           (list 10 9.19868766 -1.91666667)
           (cons 40 0)
           (cons 41 0)
           (cons 42 0)
           (cons 91 0)
           (list 10 9.66535433 -2.07333333)
           (cons 40 0)
           (cons 41 0)
           (cons 42 0)
           (cons 91 0)
           (list 10 9.66535433 -2.59333333)
           (cons 40 0)
           (cons 41 0)
           (cons 42 0)
           (cons 91 0)
           (list 10 9.19868766 -2.75)
           (cons 40 0)
           (cons 41 0)
           (cons 42 0)
           (cons 91 0)
           (list 10 6.79868766 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.332021 -4.09333333)
           (cons 40 0)
           (cons 41 0)
           (cons 42 0)
           (cons 91 0)
           (list 10 6.332021 -3.57333333)
           (cons 40 0)
           (cons 41 0)
           (cons 42 0)
           (cons 91 0)
           (list 10 6.79868766 -3.41666667)
           (cons 40 0)
           (cons 41 0)
           (cons 42 0)
           (cons 91 0)
           (list 10 9.19868766 -3.41666667)
           (cons 40 0)
           (cons 41 0)
           (cons 42 0)
           (cons 91 0)
           (list 10 9.66535433 -3.57333333)
           (cons 40 0)
           (cons 41 0)
           (cons 42 0)
           (cons 91 0)
           (list 10 9.66535433 -4.09333333)
           (cons 40 0)
           (cons 41 0)
           (cons 42 0)
           (cons 91 0)
           (list 10 9.19868766 -4.25)
           (cons 40 0)
           (cons 41 0)
           (cons 42 0)
           (cons 91 0)
           (list 10 6.79868766 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.332021 2.07333333)
           (cons 40 0)
           (cons 41 0)
           (cons 42 0)
           (cons 91 0)
           (list 10 6.332021 2.59333333)
           (cons 40 0)
           (cons 41 0)
           (cons 42 0)
           (cons 91 0)
           (list 10 6.79868766 2.75)
           (cons 40 0)
           (cons 41 0)
           (cons 42 0)
           (cons 91 0)
           (list 10 9.19868766 2.75)
           (cons 40 0)
           (cons 41 0)
           (cons 42 0)
           (cons 91 0)
           (list 10 9.66535433 2.59333333)
           (cons 40 0)
           (cons 41 0)
           (cons 42 0)
           (cons 91 0)
           (list 10 9.66535433 2.07333333)
           (cons 40 0)
           (cons 41 0)
           (cons 42 0)
           (cons 91 0)
           (list 10 9.19868766 1.91666667)
           (cons 40 0)
           (cons 41 0)
           (cons 42 0)
           (cons 91 0)
           (list 10 6.79868766 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.332021 3.57333333)
           (cons 40 0)
           (cons 41 0)
           (cons 42 0)
           (cons 91 0)
           (list 10 6.332021 4.09333333)
           (cons 40 0)
           (cons 41 0)
           (cons 42 0)
           (cons 91 0)
           (list 10 6.79868766 4.25)
           (cons 40 0)
           (cons 41 0)
           (cons 42 0)
           (cons 91 0)
           (list 10 9.19868766 4.25)
           (cons 40 0)
           (cons 41 0)
           (cons 42 0)
           (cons 91 0)
           (list 10 9.66535433 4.09333333)
           (cons 40 0)
           (cons 41 0)
           (cons 42 0)
           (cons 91 0)
           (list 10 9.66535433 3.57333333)
           (cons 40 0)
           (cons 41 0)
           (cons 42 0)
           (cons 91 0)
           (list 10 9.19868766 3.41666667)
           (cons 40 0)
           (cons 41 0)
           (cons 42 0)
           (cons 91 0)
           (list 10 6.79868766 3.41666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.33464567 -2.59333333)
           (cons 40 0)
           (cons 41 0)
           (cons 42 0)
           (cons 91 0)
           (list 10 10.33464567 -2.07333333)
           (cons 40 0)
           (cons 41 0)
           (cons 42 0)
           (cons 91 0)
           (list 10 10.80131234 -1.91666667)
           (cons 40 0)
           (cons 41 0)
           (cons 42 0)
           (cons 91 0)
           (list 10 13.20131234 -1.91666667)
           (cons 40 0)
           (cons 41 0)
           (cons 42 0)
           (cons 91 0)
           (list 10 13.667979 -2.07333333)
           (cons 40 0)
           (cons 41 0)
           (cons 42 0)
           (cons 91 0)
           (list 10 13.667979 -2.59333333)
           (cons 40 0)
           (cons 41 0)
           (cons 42 0)
           (cons 91 0)
           (list 10 13.20131234 -2.75)
           (cons 40 0)
           (cons 41 0)
           (cons 42 0)
           (cons 91 0)
           (list 10 10.80131234 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.33464567 -4.09333333)
           (cons 40 0)
           (cons 41 0)
           (cons 42 0)
           (cons 91 0)
           (list 10 10.33464567 -3.57333333)
           (cons 40 0)
           (cons 41 0)
           (cons 42 0)
           (cons 91 0)
           (list 10 10.80131234 -3.41666667)
           (cons 40 0)
           (cons 41 0)
           (cons 42 0)
           (cons 91 0)
           (list 10 13.20131234 -3.41666667)
           (cons 40 0)
           (cons 41 0)
           (cons 42 0)
           (cons 91 0)
           (list 10 13.667979 -3.57333333)
           (cons 40 0)
           (cons 41 0)
           (cons 42 0)
           (cons 91 0)
           (list 10 13.667979 -4.09333333)
           (cons 40 0)
           (cons 41 0)
           (cons 42 0)
           (cons 91 0)
           (list 10 13.20131234 -4.25)
           (cons 40 0)
           (cons 41 0)
           (cons 42 0)
           (cons 91 0)
           (list 10 10.80131234 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.33464567 2.07333333)
           (cons 40 0)
           (cons 41 0)
           (cons 42 0)
           (cons 91 0)
           (list 10 10.33464567 2.59333333)
           (cons 40 0)
           (cons 41 0)
           (cons 42 0)
           (cons 91 0)
           (list 10 10.80131234 2.75)
           (cons 40 0)
           (cons 41 0)
           (cons 42 0)
           (cons 91 0)
           (list 10 13.20131234 2.75)
           (cons 40 0)
           (cons 41 0)
           (cons 42 0)
           (cons 91 0)
           (list 10 13.667979 2.59333333)
           (cons 40 0)
           (cons 41 0)
           (cons 42 0)
           (cons 91 0)
           (list 10 13.667979 2.07333333)
           (cons 40 0)
           (cons 41 0)
           (cons 42 0)
           (cons 91 0)
           (list 10 13.20131234 1.91666667)
           (cons 40 0)
           (cons 41 0)
           (cons 42 0)
           (cons 91 0)
           (list 10 10.80131234 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.33464567 3.57333333)
           (cons 40 0)
           (cons 41 0)
           (cons 42 0)
           (cons 91 0)
           (list 10 10.33464567 4.09333333)
           (cons 40 0)
           (cons 41 0)
           (cons 42 0)
           (cons 91 0)
           (list 10 10.80131234 4.25)
           (cons 40 0)
           (cons 41 0)
           (cons 42 0)
           (cons 91 0)
           (list 10 13.20131234 4.25)
           (cons 40 0)
           (cons 41 0)
           (cons 42 0)
           (cons 91 0)
           (list 10 13.667979 4.09333333)
           (cons 40 0)
           (cons 41 0)
           (cons 42 0)
           (cons 91 0)
           (list 10 13.667979 3.57333333)
           (cons 40 0)
           (cons 41 0)
           (cons 42 0)
           (cons 91 0)
           (list 10 13.20131234 3.41666667)
           (cons 40 0)
           (cons 41 0)
           (cons 42 0)
           (cons 91 0)
           (list 10 10.80131234 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 10 0 0)
           (cons 50 0)
          )
         )
         (entmake
          (list
           (cons 0 "POINT")
           (cons 100 "AcDbEntity")
           (cons 67 0)
           (cons 8 "0")
           (cons 100 "AcDbPoint")
           (list 10 10 4.25 0)
           (cons 50 0)
          )
         )
         (entmake
          (list
           (cons 0 "POINT")
           (cons 100 "AcDbEntity")
           (cons 67 0)
           (cons 8 "0")
           (cons 100 "AcDbPoint")
           (list 10 10 -4.25 0)
           (cons 50 0)
          )
         )
         (entmake
          (list
           (cons 0 "ATTDEF")
           (cons 100 "AcDbEntity")
           (cons 67 0)
           (cons 8 "0")
           (cons 100 "AcDbText")
           (list 10 -2.29658793 1.85914261 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 0.76552931 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -0.32808399 0)
           (cons 40 0.65616798)
           (cons 1 "10.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -1.42169729 0)
           (cons 40 0.65616798)
           (cons 1 "10.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-109D-TRAILER"))
        (progn
         (entmake)
         (entmake
          (list
           (cons 0 "BLOCK")
           (cons 2 "AASHTO-2011-WB-109D-TRAILER")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4.25)
           (cons 40 0)
           (cons 41 0)
           (cons 42 0)
           (cons 91 0)
           (list 10 48 -4.25)
           (cons 40 0)
           (cons 41 0)
           (cons 42 0)
           (cons 91 0)
           (list 10 48 4.25)
           (cons 40 0)
           (cons 41 0)
           (cons 42 0)
           (cons 91 0)
           (list 10 0 4.25)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 48 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 48 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 48 0 0)
           (list 11 48 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 48 0 0)
           (cons 40 0.33333333)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 3 0 0)
           (cons 40 0.34)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 39.832021 -2.59333333)
           (cons 40 0)
           (cons 41 0)
           (cons 42 0)
           (cons 91 0)
           (list 10 39.832021 -2.07333333)
           (cons 40 0)
           (cons 41 0)
           (cons 42 0)
           (cons 91 0)
           (list 10 40.29868766 -1.91666667)
           (cons 40 0)
           (cons 41 0)
           (cons 42 0)
           (cons 91 0)
           (list 10 42.69868766 -1.91666667)
           (cons 40 0)
           (cons 41 0)
           (cons 42 0)
           (cons 91 0)
           (list 10 43.16535433 -2.07333333)
           (cons 40 0)
           (cons 41 0)
           (cons 42 0)
           (cons 91 0)
           (list 10 43.16535433 -2.59333333)
           (cons 40 0)
           (cons 41 0)
           (cons 42 0)
           (cons 91 0)
           (list 10 42.69868766 -2.75)
           (cons 40 0)
           (cons 41 0)
           (cons 42 0)
           (cons 91 0)
           (list 10 40.29868766 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 39.832021 -4.09333333)
           (cons 40 0)
           (cons 41 0)
           (cons 42 0)
           (cons 91 0)
           (list 10 39.832021 -3.57333333)
           (cons 40 0)
           (cons 41 0)
           (cons 42 0)
           (cons 91 0)
           (list 10 40.29868766 -3.41666667)
           (cons 40 0)
           (cons 41 0)
           (cons 42 0)
           (cons 91 0)
           (list 10 42.69868766 -3.41666667)
           (cons 40 0)
           (cons 41 0)
           (cons 42 0)
           (cons 91 0)
           (list 10 43.16535433 -3.57333333)
           (cons 40 0)
           (cons 41 0)
           (cons 42 0)
           (cons 91 0)
           (list 10 43.16535433 -4.09333333)
           (cons 40 0)
           (cons 41 0)
           (cons 42 0)
           (cons 91 0)
           (list 10 42.69868766 -4.25)
           (cons 40 0)
           (cons 41 0)
           (cons 42 0)
           (cons 91 0)
           (list 10 40.29868766 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 39.832021 2.07333333)
           (cons 40 0)
           (cons 41 0)
           (cons 42 0)
           (cons 91 0)
           (list 10 39.832021 2.59333333)
           (cons 40 0)
           (cons 41 0)
           (cons 42 0)
           (cons 91 0)
           (list 10 40.29868766 2.75)
           (cons 40 0)
           (cons 41 0)
           (cons 42 0)
           (cons 91 0)
           (list 10 42.69868766 2.75)
           (cons 40 0)
           (cons 41 0)
           (cons 42 0)
           (cons 91 0)
           (list 10 43.16535433 2.59333333)
           (cons 40 0)
           (cons 41 0)
           (cons 42 0)
           (cons 91 0)
           (list 10 43.16535433 2.07333333)
           (cons 40 0)
           (cons 41 0)
           (cons 42 0)
           (cons 91 0)
           (list 10 42.69868766 1.91666667)
           (cons 40 0)
           (cons 41 0)
           (cons 42 0)
           (cons 91 0)
           (list 10 40.29868766 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 39.832021 3.57333333)
           (cons 40 0)
           (cons 41 0)
           (cons 42 0)
           (cons 91 0)
           (list 10 39.832021 4.09333333)
           (cons 40 0)
           (cons 41 0)
           (cons 42 0)
           (cons 91 0)
           (list 10 40.29868766 4.25)
           (cons 40 0)
           (cons 41 0)
           (cons 42 0)
           (cons 91 0)
           (list 10 42.69868766 4.25)
           (cons 40 0)
           (cons 41 0)
           (cons 42 0)
           (cons 91 0)
           (list 10 43.16535433 4.09333333)
           (cons 40 0)
           (cons 41 0)
           (cons 42 0)
           (cons 91 0)
           (list 10 43.16535433 3.57333333)
           (cons 40 0)
           (cons 41 0)
           (cons 42 0)
           (cons 91 0)
           (list 10 42.69868766 3.41666667)
           (cons 40 0)
           (cons 41 0)
           (cons 42 0)
           (cons 91 0)
           (list 10 40.29868766 3.41666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 43.83464567 -2.59333333)
           (cons 40 0)
           (cons 41 0)
           (cons 42 0)
           (cons 91 0)
           (list 10 43.83464567 -2.07333333)
           (cons 40 0)
           (cons 41 0)
           (cons 42 0)
           (cons 91 0)
           (list 10 44.30131234 -1.91666667)
           (cons 40 0)
           (cons 41 0)
           (cons 42 0)
           (cons 91 0)
           (list 10 46.70131234 -1.91666667)
           (cons 40 0)
           (cons 41 0)
           (cons 42 0)
           (cons 91 0)
           (list 10 47.167979 -2.07333333)
           (cons 40 0)
           (cons 41 0)
           (cons 42 0)
           (cons 91 0)
           (list 10 47.167979 -2.59333333)
           (cons 40 0)
           (cons 41 0)
           (cons 42 0)
           (cons 91 0)
           (list 10 46.70131234 -2.75)
           (cons 40 0)
           (cons 41 0)
           (cons 42 0)
           (cons 91 0)
           (list 10 44.30131234 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 43.83464567 -4.09333333)
           (cons 40 0)
           (cons 41 0)
           (cons 42 0)
           (cons 91 0)
           (list 10 43.83464567 -3.57333333)
           (cons 40 0)
           (cons 41 0)
           (cons 42 0)
           (cons 91 0)
           (list 10 44.30131234 -3.41666667)
           (cons 40 0)
           (cons 41 0)
           (cons 42 0)
           (cons 91 0)
           (list 10 46.70131234 -3.41666667)
           (cons 40 0)
           (cons 41 0)
           (cons 42 0)
           (cons 91 0)
           (list 10 47.167979 -3.57333333)
           (cons 40 0)
           (cons 41 0)
           (cons 42 0)
           (cons 91 0)
           (list 10 47.167979 -4.09333333)
           (cons 40 0)
           (cons 41 0)
           (cons 42 0)
           (cons 91 0)
           (list 10 46.70131234 -4.25)
           (cons 40 0)
           (cons 41 0)
           (cons 42 0)
           (cons 91 0)
           (list 10 44.30131234 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 43.83464567 2.07333333)
           (cons 40 0)
           (cons 41 0)
           (cons 42 0)
           (cons 91 0)
           (list 10 43.83464567 2.59333333)
           (cons 40 0)
           (cons 41 0)
           (cons 42 0)
           (cons 91 0)
           (list 10 44.30131234 2.75)
           (cons 40 0)
           (cons 41 0)
           (cons 42 0)
           (cons 91 0)
           (list 10 46.70131234 2.75)
           (cons 40 0)
           (cons 41 0)
           (cons 42 0)
           (cons 91 0)
           (list 10 47.167979 2.59333333)
           (cons 40 0)
           (cons 41 0)
           (cons 42 0)
           (cons 91 0)
           (list 10 47.167979 2.07333333)
           (cons 40 0)
           (cons 41 0)
           (cons 42 0)
           (cons 91 0)
           (list 10 46.70131234 1.91666667)
           (cons 40 0)
           (cons 41 0)
           (cons 42 0)
           (cons 91 0)
           (list 10 44.30131234 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 43.83464567 3.57333333)
           (cons 40 0)
           (cons 41 0)
           (cons 42 0)
           (cons 91 0)
           (list 10 43.83464567 4.09333333)
           (cons 40 0)
           (cons 41 0)
           (cons 42 0)
           (cons 91 0)
           (list 10 44.30131234 4.25)
           (cons 40 0)
           (cons 41 0)
           (cons 42 0)
           (cons 91 0)
           (list 10 46.70131234 4.25)
           (cons 40 0)
           (cons 41 0)
           (cons 42 0)
           (cons 91 0)
           (list 10 47.167979 4.09333333)
           (cons 40 0)
           (cons 41 0)
           (cons 42 0)
           (cons 91 0)
           (list 10 47.167979 3.57333333)
           (cons 40 0)
           (cons 41 0)
           (cons 42 0)
           (cons 91 0)
           (list 10 46.70131234 3.41666667)
           (cons 40 0)
           (cons 41 0)
           (cons 42 0)
           (cons 91 0)
           (list 10 44.30131234 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4.25 0)
           (cons 50 0)
          )
         )
         (entmake
          (list
           (cons 0 "POINT")
           (cons 100 "AcDbEntity")
           (cons 67 0)
           (cons 8 "0")
           (cons 100 "AcDbPoint")
           (list 10 48 -4.25 0)
           (cons 50 0)
          )
         )
         (entmake
          (list
           (cons 0 "POINT")
           (cons 100 "AcDbEntity")
           (cons 67 0)
           (cons 8 "0")
           (cons 100 "AcDbPoint")
           (list 10 0 4.25 0)
           (cons 50 0)
          )
         )
         (entmake
          (list
           (cons 0 "POINT")
           (cons 100 "AcDbEntity")
           (cons 67 0)
           (cons 8 "0")
           (cons 100 "AcDbPoint")
           (list 10 48 4.25 0)
           (cons 50 0)
          )
         )
         (entmake
          (list
           (cons 0 "POINT")
           (cons 100 "AcDbEntity")
           (cons 67 0)
           (cons 8 "0")
           (cons 100 "AcDbPoint")
           (list 10 3 0 0)
           (cons 50 0)
          )
         )
         (entmake
          (list
           (cons 0 "POINT")
           (cons 100 "AcDbEntity")
           (cons 67 0)
           (cons 8 "0")
           (cons 100 "AcDbPoint")
           (list 10 48 0 0)
           (cons 50 0)
          )
         )
         (entmake
          (list
           (cons 0 "POINT")
           (cons 100 "AcDbEntity")
           (cons 67 0)
           (cons 8 "0")
           (cons 100 "AcDbPoint")
           (list 10 43.5 4.25 0)
           (cons 50 0)
          )
         )
         (entmake
          (list
           (cons 0 "POINT")
           (cons 100 "AcDbEntity")
           (cons 67 0)
           (cons 8 "0")
           (cons 100 "AcDbPoint")
           (list 10 43.5 -4.25 0)
           (cons 50 0)
          )
         )
         (entmake
          (list
           (cons 0 "ATTDEF")
           (cons 100 "AcDbEntity")
           (cons 67 0)
           (cons 8 "0")
           (cons 100 "AcDbText")
           (list 10 0.70341207 1.85914261 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 0.76552931 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -0.32808399 0)
           (cons 40 0.65616798)
           (cons 1 "43.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -1.42169729 0)
           (cons 40 0.65616798)
           (cons 1 "48.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-109D-TRUCK"))
        (progn
         (entmake)
         (entmake
          (list
           (cons 0 "BLOCK")
           (cons 2 "AASHTO-2011-WB-109D-TRUCK")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4)
           (cons 40 0)
           (cons 41 0)
           (cons 42 0)
           (cons 91 0)
           (list 10 16.6 -4)
           (cons 40 0)
           (cons 41 0)
           (cons 42 0)
           (cons 91 0)
           (list 10 16.6 4)
           (cons 40 0)
           (cons 41 0)
           (cons 42 0)
           (cons 91 0)
           (list 10 0 4)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.5 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.5 -1.66666667 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 16.6 -1.66666667 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 16.6 1.66666667 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.5 1.66666667 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.5 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 14 0 0)
           (cons 40 1.14285714)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 14.80812204 -0.80812204 0)
           (list 11 14.80812204 0.80812204 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.73333333 -2.34333333)
           (cons 40 0)
           (cons 41 0)
           (cons 42 0)
           (cons 91 0)
           (list 10 10.73333333 -1.82333333)
           (cons 40 0)
           (cons 41 0)
           (cons 42 0)
           (cons 91 0)
           (list 10 11.2 -1.66666667)
           (cons 40 0)
           (cons 41 0)
           (cons 42 0)
           (cons 91 0)
           (list 10 13.6 -1.66666667)
           (cons 40 0)
           (cons 41 0)
           (cons 42 0)
           (cons 91 0)
           (list 10 14.06666667 -1.82333333)
           (cons 40 0)
           (cons 41 0)
           (cons 42 0)
           (cons 91 0)
           (list 10 14.06666667 -2.34333333)
           (cons 40 0)
           (cons 41 0)
           (cons 42 0)
           (cons 91 0)
           (list 10 13.6 -2.5)
           (cons 40 0)
           (cons 41 0)
           (cons 42 0)
           (cons 91 0)
           (list 10 11.2 -2.5)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.73333333 -3.84333333)
           (cons 40 0)
           (cons 41 0)
           (cons 42 0)
           (cons 91 0)
           (list 10 10.73333333 -3.32333333)
           (cons 40 0)
           (cons 41 0)
           (cons 42 0)
           (cons 91 0)
           (list 10 11.2 -3.16666667)
           (cons 40 0)
           (cons 41 0)
           (cons 42 0)
           (cons 91 0)
           (list 10 13.6 -3.16666667)
           (cons 40 0)
           (cons 41 0)
           (cons 42 0)
           (cons 91 0)
           (list 10 14.06666667 -3.32333333)
           (cons 40 0)
           (cons 41 0)
           (cons 42 0)
           (cons 91 0)
           (list 10 14.06666667 -3.84333333)
           (cons 40 0)
           (cons 41 0)
           (cons 42 0)
           (cons 91 0)
           (list 10 13.6 -4)
           (cons 40 0)
           (cons 41 0)
           (cons 42 0)
           (cons 91 0)
           (list 10 11.2 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.73333333 1.82333333)
           (cons 40 0)
           (cons 41 0)
           (cons 42 0)
           (cons 91 0)
           (list 10 10.73333333 2.34333333)
           (cons 40 0)
           (cons 41 0)
           (cons 42 0)
           (cons 91 0)
           (list 10 11.2 2.5)
           (cons 40 0)
           (cons 41 0)
           (cons 42 0)
           (cons 91 0)
           (list 10 13.6 2.5)
           (cons 40 0)
           (cons 41 0)
           (cons 42 0)
           (cons 91 0)
           (list 10 14.06666667 2.34333333)
           (cons 40 0)
           (cons 41 0)
           (cons 42 0)
           (cons 91 0)
           (list 10 14.06666667 1.82333333)
           (cons 40 0)
           (cons 41 0)
           (cons 42 0)
           (cons 91 0)
           (list 10 13.6 1.66666667)
           (cons 40 0)
           (cons 41 0)
           (cons 42 0)
           (cons 91 0)
           (list 10 11.2 1.66666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.73333333 3.32333333)
           (cons 40 0)
           (cons 41 0)
           (cons 42 0)
           (cons 91 0)
           (list 10 10.73333333 3.84333333)
           (cons 40 0)
           (cons 41 0)
           (cons 42 0)
           (cons 91 0)
           (list 10 11.2 4)
           (cons 40 0)
           (cons 41 0)
           (cons 42 0)
           (cons 91 0)
           (list 10 13.6 4)
           (cons 40 0)
           (cons 41 0)
           (cons 42 0)
           (cons 91 0)
           (list 10 14.06666667 3.84333333)
           (cons 40 0)
           (cons 41 0)
           (cons 42 0)
           (cons 91 0)
           (list 10 14.06666667 3.32333333)
           (cons 40 0)
           (cons 41 0)
           (cons 42 0)
           (cons 91 0)
           (list 10 13.6 3.16666667)
           (cons 40 0)
           (cons 41 0)
           (cons 42 0)
           (cons 91 0)
           (list 10 11.2 3.16666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.93333333 -2.34333333)
           (cons 40 0)
           (cons 41 0)
           (cons 42 0)
           (cons 91 0)
           (list 10 14.93333333 -1.82333333)
           (cons 40 0)
           (cons 41 0)
           (cons 42 0)
           (cons 91 0)
           (list 10 15.4 -1.66666667)
           (cons 40 0)
           (cons 41 0)
           (cons 42 0)
           (cons 91 0)
           (list 10 17.8 -1.66666667)
           (cons 40 0)
           (cons 41 0)
           (cons 42 0)
           (cons 91 0)
           (list 10 18.26666667 -1.82333333)
           (cons 40 0)
           (cons 41 0)
           (cons 42 0)
           (cons 91 0)
           (list 10 18.26666667 -2.34333333)
           (cons 40 0)
           (cons 41 0)
           (cons 42 0)
           (cons 91 0)
           (list 10 17.8 -2.5)
           (cons 40 0)
           (cons 41 0)
           (cons 42 0)
           (cons 91 0)
           (list 10 15.4 -2.5)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.93333333 -3.84333333)
           (cons 40 0)
           (cons 41 0)
           (cons 42 0)
           (cons 91 0)
           (list 10 14.93333333 -3.32333333)
           (cons 40 0)
           (cons 41 0)
           (cons 42 0)
           (cons 91 0)
           (list 10 15.4 -3.16666667)
           (cons 40 0)
           (cons 41 0)
           (cons 42 0)
           (cons 91 0)
           (list 10 17.8 -3.16666667)
           (cons 40 0)
           (cons 41 0)
           (cons 42 0)
           (cons 91 0)
           (list 10 18.26666667 -3.32333333)
           (cons 40 0)
           (cons 41 0)
           (cons 42 0)
           (cons 91 0)
           (list 10 18.26666667 -3.84333333)
           (cons 40 0)
           (cons 41 0)
           (cons 42 0)
           (cons 91 0)
           (list 10 17.8 -4)
           (cons 40 0)
           (cons 41 0)
           (cons 42 0)
           (cons 91 0)
           (list 10 15.4 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.93333333 1.82333333)
           (cons 40 0)
           (cons 41 0)
           (cons 42 0)
           (cons 91 0)
           (list 10 14.93333333 2.34333333)
           (cons 40 0)
           (cons 41 0)
           (cons 42 0)
           (cons 91 0)
           (list 10 15.4 2.5)
           (cons 40 0)
           (cons 41 0)
           (cons 42 0)
           (cons 91 0)
           (list 10 17.8 2.5)
           (cons 40 0)
           (cons 41 0)
           (cons 42 0)
           (cons 91 0)
           (list 10 18.26666667 2.34333333)
           (cons 40 0)
           (cons 41 0)
           (cons 42 0)
           (cons 91 0)
           (list 10 18.26666667 1.82333333)
           (cons 40 0)
           (cons 41 0)
           (cons 42 0)
           (cons 91 0)
           (list 10 17.8 1.66666667)
           (cons 40 0)
           (cons 41 0)
           (cons 42 0)
           (cons 91 0)
           (list 10 15.4 1.66666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.93333333 3.32333333)
           (cons 40 0)
           (cons 41 0)
           (cons 42 0)
           (cons 91 0)
           (list 10 14.93333333 3.84333333)
           (cons 40 0)
           (cons 41 0)
           (cons 42 0)
           (cons 91 0)
           (list 10 15.4 4)
           (cons 40 0)
           (cons 41 0)
           (cons 42 0)
           (cons 91 0)
           (list 10 17.8 4)
           (cons 40 0)
           (cons 41 0)
           (cons 42 0)
           (cons 91 0)
           (list 10 18.26666667 3.84333333)
           (cons 40 0)
           (cons 41 0)
           (cons 42 0)
           (cons 91 0)
           (list 10 18.26666667 3.32333333)
           (cons 40 0)
           (cons 41 0)
           (cons 42 0)
           (cons 91 0)
           (list 10 17.8 3.16666667)
           (cons 40 0)
           (cons 41 0)
           (cons 42 0)
           (cons 91 0)
           (list 10 15.4 3.16666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4 0)
           (cons 50 0)
          )
         )
         (entmake
          (list
           (cons 0 "POINT")
           (cons 100 "AcDbEntity")
           (cons 67 0)
           (cons 8 "0")
           (cons 100 "AcDbPoint")
           (list 10 2.3 -4 0)
           (cons 50 0)
          )
         )
         (entmake
          (list
           (cons 0 "POINT")
           (cons 100 "AcDbEntity")
           (cons 67 0)
           (cons 8 "0")
           (cons 100 "AcDbPoint")
           (list 10 0 4 0)
           (cons 50 0)
          )
         )
         (entmake
          (list
           (cons 0 "POINT")
           (cons 100 "AcDbEntity")
           (cons 67 0)
           (cons 8 "0")
           (cons 100 "AcDbPoint")
           (list 10 2.3 4 0)
           (cons 50 0)
          )
         )
         (entmake
          (list
           (cons 0 "POINT")
           (cons 100 "AcDbEntity")
           (cons 67 0)
           (cons 8 "0")
           (cons 100 "AcDbPoint")
           (list 10 2.3 0 0)
           (cons 50 0)
          )
         )
         (entmake
          (list
           (cons 0 "POINT")
           (cons 100 "AcDbEntity")
           (cons 67 0)
           (cons 8 "0")
           (cons 100 "AcDbPoint")
           (list 10 14 0 0)
           (cons 50 0)
          )
         )
         (entmake
          (list
           (cons 0 "POINT")
           (cons 100 "AcDbEntity")
           (cons 67 0)
           (cons 8 "0")
           (cons 100 "AcDbPoint")
           (list 10 14.5 4 0)
           (cons 50 0)
          )
         )
         (entmake
          (list
           (cons 0 "POINT")
           (cons 100 "AcDbEntity")
           (cons 67 0)
           (cons 8 "0")
           (cons 100 "AcDbPoint")
           (list 10 14.5 -4 0)
           (cons 50 0)
          )
         )
         (entmake
          (list
           (cons 0 "INSERT")
           (cons 100 "AcDbEntity")
           (cons 67 0)
           (cons 8 "0")
           (cons 100 "AcDbBlockReference")
           (cons 2 "WheelLeft2")
           (list 10 2.3 -3.16666667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRight2")
           (list 10 2.3 3.16666667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 0.0328084 1.85914261 0)
           (cons 40 0.65616798)
           (cons 1 "2.300")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.0328084 0.76552931 0)
           (cons 40 0.65616798)
           (cons 1 "2.300")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.0328084 -0.32808399 0)
           (cons 40 0.65616798)
           (cons 1 "14.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.0328084 -1.42169729 0)
           (cons 40 0.65616798)
           (cons 1 "14.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.0328084 -2.51531059 0)
           (cons 40 0.65616798)
           (cons 1 "12.6")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-100T-TRAILER"))
        (progn
         (entmake)
         (entmake
          (list
           (cons 0 "BLOCK")
           (cons 2 "AASHTO-2011-WB-100T-TRAILER")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4.25)
           (cons 40 0)
           (cons 41 0)
           (cons 42 0)
           (cons 91 0)
           (list 10 28.5 -4.25)
           (cons 40 0)
           (cons 41 0)
           (cons 42 0)
           (cons 91 0)
           (list 10 28.5 4.25)
           (cons 40 0)
           (cons 41 0)
           (cons 42 0)
           (cons 91 0)
           (list 10 0 4.25)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 28.5 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 28.5 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 2.5 0 0)
           (cons 40 0.34)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 -2.59333333)
           (cons 40 0)
           (cons 41 0)
           (cons 42 0)
           (cons 91 0)
           (list 10 23.83333333 -2.07333333)
           (cons 40 0)
           (cons 41 0)
           (cons 42 0)
           (cons 91 0)
           (list 10 24.3 -1.91666667)
           (cons 40 0)
           (cons 41 0)
           (cons 42 0)
           (cons 91 0)
           (list 10 26.7 -1.91666667)
           (cons 40 0)
           (cons 41 0)
           (cons 42 0)
           (cons 91 0)
           (list 10 27.16666667 -2.07333333)
           (cons 40 0)
           (cons 41 0)
           (cons 42 0)
           (cons 91 0)
           (list 10 27.16666667 -2.59333333)
           (cons 40 0)
           (cons 41 0)
           (cons 42 0)
           (cons 91 0)
           (list 10 26.7 -2.75)
           (cons 40 0)
           (cons 41 0)
           (cons 42 0)
           (cons 91 0)
           (list 10 24.3 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 -4.09333333)
           (cons 40 0)
           (cons 41 0)
           (cons 42 0)
           (cons 91 0)
           (list 10 23.83333333 -3.57333333)
           (cons 40 0)
           (cons 41 0)
           (cons 42 0)
           (cons 91 0)
           (list 10 24.3 -3.41666667)
           (cons 40 0)
           (cons 41 0)
           (cons 42 0)
           (cons 91 0)
           (list 10 26.7 -3.41666667)
           (cons 40 0)
           (cons 41 0)
           (cons 42 0)
           (cons 91 0)
           (list 10 27.16666667 -3.57333333)
           (cons 40 0)
           (cons 41 0)
           (cons 42 0)
           (cons 91 0)
           (list 10 27.16666667 -4.09333333)
           (cons 40 0)
           (cons 41 0)
           (cons 42 0)
           (cons 91 0)
           (list 10 26.7 -4.25)
           (cons 40 0)
           (cons 41 0)
           (cons 42 0)
           (cons 91 0)
           (list 10 24.3 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 2.07333333)
           (cons 40 0)
           (cons 41 0)
           (cons 42 0)
           (cons 91 0)
           (list 10 23.83333333 2.59333333)
           (cons 40 0)
           (cons 41 0)
           (cons 42 0)
           (cons 91 0)
           (list 10 24.3 2.75)
           (cons 40 0)
           (cons 41 0)
           (cons 42 0)
           (cons 91 0)
           (list 10 26.7 2.75)
           (cons 40 0)
           (cons 41 0)
           (cons 42 0)
           (cons 91 0)
           (list 10 27.16666667 2.59333333)
           (cons 40 0)
           (cons 41 0)
           (cons 42 0)
           (cons 91 0)
           (list 10 27.16666667 2.07333333)
           (cons 40 0)
           (cons 41 0)
           (cons 42 0)
           (cons 91 0)
           (list 10 26.7 1.91666667)
           (cons 40 0)
           (cons 41 0)
           (cons 42 0)
           (cons 91 0)
           (list 10 24.3 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 3.57333333)
           (cons 40 0)
           (cons 41 0)
           (cons 42 0)
           (cons 91 0)
           (list 10 23.83333333 4.09333333)
           (cons 40 0)
           (cons 41 0)
           (cons 42 0)
           (cons 91 0)
           (list 10 24.3 4.25)
           (cons 40 0)
           (cons 41 0)
           (cons 42 0)
           (cons 91 0)
           (list 10 26.7 4.25)
           (cons 40 0)
           (cons 41 0)
           (cons 42 0)
           (cons 91 0)
           (list 10 27.16666667 4.09333333)
           (cons 40 0)
           (cons 41 0)
           (cons 42 0)
           (cons 91 0)
           (list 10 27.16666667 3.57333333)
           (cons 40 0)
           (cons 41 0)
           (cons 42 0)
           (cons 91 0)
           (list 10 26.7 3.41666667)
           (cons 40 0)
           (cons 41 0)
           (cons 42 0)
           (cons 91 0)
           (list 10 24.3 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4.25 0)
           (cons 50 0)
          )
         )
         (entmake
          (list
           (cons 0 "POINT")
           (cons 100 "AcDbEntity")
           (cons 67 0)
           (cons 8 "0")
           (cons 100 "AcDbPoint")
           (list 10 25.5 -4.25 0)
           (cons 50 0)
          )
         )
         (entmake
          (list
           (cons 0 "POINT")
           (cons 100 "AcDbEntity")
           (cons 67 0)
           (cons 8 "0")
           (cons 100 "AcDbPoint")
           (list 10 28.5 -4.25 0)
           (cons 50 0)
          )
         )
         (entmake
          (list
           (cons 0 "POINT")
           (cons 100 "AcDbEntity")
           (cons 67 0)
           (cons 8 "0")
           (cons 100 "AcDbPoint")
           (list 10 28.5 0 0)
           (cons 50 0)
          )
         )
         (entmake
          (list
           (cons 0 "POINT")
           (cons 100 "AcDbEntity")
           (cons 67 0)
           (cons 8 "0")
           (cons 100 "AcDbPoint")
           (list 10 28.5 4.25 0)
           (cons 50 0)
          )
         )
         (entmake
          (list
           (cons 0 "POINT")
           (cons 100 "AcDbEntity")
           (cons 67 0)
           (cons 8 "0")
           (cons 100 "AcDbPoint")
           (list 10 25.5 4.25 0)
           (cons 50 0)
          )
         )
         (entmake
          (list
           (cons 0 "POINT")
           (cons 100 "AcDbEntity")
           (cons 67 0)
           (cons 8 "0")
           (cons 100 "AcDbPoint")
           (list 10 0 4.25 0)
           (cons 50 0)
          )
         )
         (entmake
          (list
           (cons 0 "POINT")
           (cons 100 "AcDbEntity")
           (cons 67 0)
           (cons 8 "0")
           (cons 100 "AcDbPoint")
           (list 10 2.5 0 0)
           (cons 50 0)
          )
         )
         (entmake
          (list
           (cons 0 "ATTDEF")
           (cons 100 "AcDbEntity")
           (cons 67 0)
           (cons 8 "0")
           (cons 100 "AcDbText")
           (list 10 0.20341207 1.85914261 0)
           (cons 40 0.65616798)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 0.76552931 0)
           (cons 40 0.65616798)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -0.32808399 0)
           (cons 40 0.65616798)
           (cons 1 "25.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -1.42169729 0)
           (cons 40 0.65616798)
           (cons 1 "28.500")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-100T-PUP"))
        (progn
         (entmake)
         (entmake
          (list
           (cons 0 "BLOCK")
           (cons 2 "AASHTO-2011-WB-100T-PUP")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 3)
           (cons 70 1)
           (cons 43 0)
           (cons 38 0)
           (cons 39 0)
           (list 10 0 0)
           (cons 40 0)
           (cons 41 0)
           (cons 42 0)
           (cons 91 0)
           (list 10 7 4.25)
           (cons 40 0)
           (cons 41 0)
           (cons 42 0)
           (cons 91 0)
           (list 10 7 -4.25)
           (cons 40 0)
           (cons 41 0)
           (cons 42 0)
           (cons 91 0)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 7 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.56666667)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.33333333 -4.09333333)
           (cons 40 0)
           (cons 41 0)
           (cons 42 0)
           (cons 91 0)
           (list 10 5.33333333 -3.57333333)
           (cons 40 0)
           (cons 41 0)
           (cons 42 0)
           (cons 91 0)
           (list 10 5.8 -3.41666667)
           (cons 40 0)
           (cons 41 0)
           (cons 42 0)
           (cons 91 0)
           (list 10 8.2 -3.41666667)
           (cons 40 0)
           (cons 41 0)
           (cons 42 0)
           (cons 91 0)
           (list 10 8.66666667 -3.57333333)
           (cons 40 0)
           (cons 41 0)
           (cons 42 0)
           (cons 91 0)
           (list 10 8.66666667 -4.09333333)
           (cons 40 0)
           (cons 41 0)
           (cons 42 0)
           (cons 91 0)
           (list 10 8.2 -4.25)
           (cons 40 0)
           (cons 41 0)
           (cons 42 0)
           (cons 91 0)
           (list 10 5.8 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.33333333 3.57333333)
           (cons 40 0)
           (cons 41 0)
           (cons 42 0)
           (cons 91 0)
           (list 10 5.33333333 4.09333333)
           (cons 40 0)
           (cons 41 0)
           (cons 42 0)
           (cons 91 0)
           (list 10 5.8 4.25)
           (cons 40 0)
           (cons 41 0)
           (cons 42 0)
           (cons 91 0)
           (list 10 8.2 4.25)
           (cons 40 0)
           (cons 41 0)
           (cons 42 0)
           (cons 91 0)
           (list 10 8.66666667 4.09333333)
           (cons 40 0)
           (cons 41 0)
           (cons 42 0)
           (cons 91 0)
           (list 10 8.66666667 3.57333333)
           (cons 40 0)
           (cons 41 0)
           (cons 42 0)
           (cons 91 0)
           (list 10 8.2 3.41666667)
           (cons 40 0)
           (cons 41 0)
           (cons 42 0)
           (cons 91 0)
           (list 10 5.8 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 7 0 0)
           (cons 50 0)
          )
         )
         (entmake
          (list
           (cons 0 "POINT")
           (cons 100 "AcDbEntity")
           (cons 67 0)
           (cons 8 "0")
           (cons 100 "AcDbPoint")
           (list 10 7 4.25 0)
           (cons 50 0)
          )
         )
         (entmake
          (list
           (cons 0 "POINT")
           (cons 100 "AcDbEntity")
           (cons 67 0)
           (cons 8 "0")
           (cons 100 "AcDbPoint")
           (list 10 7 -4.25 0)
           (cons 50 0)
          )
         )
         (entmake
          (list
           (cons 0 "ATTDEF")
           (cons 100 "AcDbEntity")
           (cons 67 0)
           (cons 8 "0")
           (cons 100 "AcDbText")
           (list 10 -2.29658793 1.85914261 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 0.76552931 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -0.32808399 0)
           (cons 40 0.65616798)
           (cons 1 "7.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -1.42169729 0)
           (cons 40 0.65616798)
           (cons 1 "7.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-100T-TRAILER"))
        (progn
         (entmake)
         (entmake
          (list
           (cons 0 "BLOCK")
           (cons 2 "AASHTO-2011-WB-100T-TRAILER")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4.25)
           (cons 40 0)
           (cons 41 0)
           (cons 42 0)
           (cons 91 0)
           (list 10 28.5 -4.25)
           (cons 40 0)
           (cons 41 0)
           (cons 42 0)
           (cons 91 0)
           (list 10 28.5 4.25)
           (cons 40 0)
           (cons 41 0)
           (cons 42 0)
           (cons 91 0)
           (list 10 0 4.25)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 28.5 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 28.5 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 2.5 0 0)
           (cons 40 0.34)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 -2.59333333)
           (cons 40 0)
           (cons 41 0)
           (cons 42 0)
           (cons 91 0)
           (list 10 23.83333333 -2.07333333)
           (cons 40 0)
           (cons 41 0)
           (cons 42 0)
           (cons 91 0)
           (list 10 24.3 -1.91666667)
           (cons 40 0)
           (cons 41 0)
           (cons 42 0)
           (cons 91 0)
           (list 10 26.7 -1.91666667)
           (cons 40 0)
           (cons 41 0)
           (cons 42 0)
           (cons 91 0)
           (list 10 27.16666667 -2.07333333)
           (cons 40 0)
           (cons 41 0)
           (cons 42 0)
           (cons 91 0)
           (list 10 27.16666667 -2.59333333)
           (cons 40 0)
           (cons 41 0)
           (cons 42 0)
           (cons 91 0)
           (list 10 26.7 -2.75)
           (cons 40 0)
           (cons 41 0)
           (cons 42 0)
           (cons 91 0)
           (list 10 24.3 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 -4.09333333)
           (cons 40 0)
           (cons 41 0)
           (cons 42 0)
           (cons 91 0)
           (list 10 23.83333333 -3.57333333)
           (cons 40 0)
           (cons 41 0)
           (cons 42 0)
           (cons 91 0)
           (list 10 24.3 -3.41666667)
           (cons 40 0)
           (cons 41 0)
           (cons 42 0)
           (cons 91 0)
           (list 10 26.7 -3.41666667)
           (cons 40 0)
           (cons 41 0)
           (cons 42 0)
           (cons 91 0)
           (list 10 27.16666667 -3.57333333)
           (cons 40 0)
           (cons 41 0)
           (cons 42 0)
           (cons 91 0)
           (list 10 27.16666667 -4.09333333)
           (cons 40 0)
           (cons 41 0)
           (cons 42 0)
           (cons 91 0)
           (list 10 26.7 -4.25)
           (cons 40 0)
           (cons 41 0)
           (cons 42 0)
           (cons 91 0)
           (list 10 24.3 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 2.07333333)
           (cons 40 0)
           (cons 41 0)
           (cons 42 0)
           (cons 91 0)
           (list 10 23.83333333 2.59333333)
           (cons 40 0)
           (cons 41 0)
           (cons 42 0)
           (cons 91 0)
           (list 10 24.3 2.75)
           (cons 40 0)
           (cons 41 0)
           (cons 42 0)
           (cons 91 0)
           (list 10 26.7 2.75)
           (cons 40 0)
           (cons 41 0)
           (cons 42 0)
           (cons 91 0)
           (list 10 27.16666667 2.59333333)
           (cons 40 0)
           (cons 41 0)
           (cons 42 0)
           (cons 91 0)
           (list 10 27.16666667 2.07333333)
           (cons 40 0)
           (cons 41 0)
           (cons 42 0)
           (cons 91 0)
           (list 10 26.7 1.91666667)
           (cons 40 0)
           (cons 41 0)
           (cons 42 0)
           (cons 91 0)
           (list 10 24.3 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 3.57333333)
           (cons 40 0)
           (cons 41 0)
           (cons 42 0)
           (cons 91 0)
           (list 10 23.83333333 4.09333333)
           (cons 40 0)
           (cons 41 0)
           (cons 42 0)
           (cons 91 0)
           (list 10 24.3 4.25)
           (cons 40 0)
           (cons 41 0)
           (cons 42 0)
           (cons 91 0)
           (list 10 26.7 4.25)
           (cons 40 0)
           (cons 41 0)
           (cons 42 0)
           (cons 91 0)
           (list 10 27.16666667 4.09333333)
           (cons 40 0)
           (cons 41 0)
           (cons 42 0)
           (cons 91 0)
           (list 10 27.16666667 3.57333333)
           (cons 40 0)
           (cons 41 0)
           (cons 42 0)
           (cons 91 0)
           (list 10 26.7 3.41666667)
           (cons 40 0)
           (cons 41 0)
           (cons 42 0)
           (cons 91 0)
           (list 10 24.3 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4.25 0)
           (cons 50 0)
          )
         )
         (entmake
          (list
           (cons 0 "POINT")
           (cons 100 "AcDbEntity")
           (cons 67 0)
           (cons 8 "0")
           (cons 100 "AcDbPoint")
           (list 10 25.5 -4.25 0)
           (cons 50 0)
          )
         )
         (entmake
          (list
           (cons 0 "POINT")
           (cons 100 "AcDbEntity")
           (cons 67 0)
           (cons 8 "0")
           (cons 100 "AcDbPoint")
           (list 10 28.5 -4.25 0)
           (cons 50 0)
          )
         )
         (entmake
          (list
           (cons 0 "POINT")
           (cons 100 "AcDbEntity")
           (cons 67 0)
           (cons 8 "0")
           (cons 100 "AcDbPoint")
           (list 10 28.5 0 0)
           (cons 50 0)
          )
         )
         (entmake
          (list
           (cons 0 "POINT")
           (cons 100 "AcDbEntity")
           (cons 67 0)
           (cons 8 "0")
           (cons 100 "AcDbPoint")
           (list 10 28.5 4.25 0)
           (cons 50 0)
          )
         )
         (entmake
          (list
           (cons 0 "POINT")
           (cons 100 "AcDbEntity")
           (cons 67 0)
           (cons 8 "0")
           (cons 100 "AcDbPoint")
           (list 10 25.5 4.25 0)
           (cons 50 0)
          )
         )
         (entmake
          (list
           (cons 0 "POINT")
           (cons 100 "AcDbEntity")
           (cons 67 0)
           (cons 8 "0")
           (cons 100 "AcDbPoint")
           (list 10 0 4.25 0)
           (cons 50 0)
          )
         )
         (entmake
          (list
           (cons 0 "POINT")
           (cons 100 "AcDbEntity")
           (cons 67 0)
           (cons 8 "0")
           (cons 100 "AcDbPoint")
           (list 10 2.5 0 0)
           (cons 50 0)
          )
         )
         (entmake
          (list
           (cons 0 "ATTDEF")
           (cons 100 "AcDbEntity")
           (cons 67 0)
           (cons 8 "0")
           (cons 100 "AcDbText")
           (list 10 0.20341207 1.85914261 0)
           (cons 40 0.65616798)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 0.76552931 0)
           (cons 40 0.65616798)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -0.32808399 0)
           (cons 40 0.65616798)
           (cons 1 "25.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -1.42169729 0)
           (cons 40 0.65616798)
           (cons 1 "28.500")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-100T-PUP"))
        (progn
         (entmake)
         (entmake
          (list
           (cons 0 "BLOCK")
           (cons 2 "AASHTO-2011-WB-100T-PUP")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 3)
           (cons 70 1)
           (cons 43 0)
           (cons 38 0)
           (cons 39 0)
           (list 10 0 0)
           (cons 40 0)
           (cons 41 0)
           (cons 42 0)
           (cons 91 0)
           (list 10 7 4.25)
           (cons 40 0)
           (cons 41 0)
           (cons 42 0)
           (cons 91 0)
           (list 10 7 -4.25)
           (cons 40 0)
           (cons 41 0)
           (cons 42 0)
           (cons 91 0)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 7 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.56666667)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.33333333 -4.09333333)
           (cons 40 0)
           (cons 41 0)
           (cons 42 0)
           (cons 91 0)
           (list 10 5.33333333 -3.57333333)
           (cons 40 0)
           (cons 41 0)
           (cons 42 0)
           (cons 91 0)
           (list 10 5.8 -3.41666667)
           (cons 40 0)
           (cons 41 0)
           (cons 42 0)
           (cons 91 0)
           (list 10 8.2 -3.41666667)
           (cons 40 0)
           (cons 41 0)
           (cons 42 0)
           (cons 91 0)
           (list 10 8.66666667 -3.57333333)
           (cons 40 0)
           (cons 41 0)
           (cons 42 0)
           (cons 91 0)
           (list 10 8.66666667 -4.09333333)
           (cons 40 0)
           (cons 41 0)
           (cons 42 0)
           (cons 91 0)
           (list 10 8.2 -4.25)
           (cons 40 0)
           (cons 41 0)
           (cons 42 0)
           (cons 91 0)
           (list 10 5.8 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.33333333 3.57333333)
           (cons 40 0)
           (cons 41 0)
           (cons 42 0)
           (cons 91 0)
           (list 10 5.33333333 4.09333333)
           (cons 40 0)
           (cons 41 0)
           (cons 42 0)
           (cons 91 0)
           (list 10 5.8 4.25)
           (cons 40 0)
           (cons 41 0)
           (cons 42 0)
           (cons 91 0)
           (list 10 8.2 4.25)
           (cons 40 0)
           (cons 41 0)
           (cons 42 0)
           (cons 91 0)
           (list 10 8.66666667 4.09333333)
           (cons 40 0)
           (cons 41 0)
           (cons 42 0)
           (cons 91 0)
           (list 10 8.66666667 3.57333333)
           (cons 40 0)
           (cons 41 0)
           (cons 42 0)
           (cons 91 0)
           (list 10 8.2 3.41666667)
           (cons 40 0)
           (cons 41 0)
           (cons 42 0)
           (cons 91 0)
           (list 10 5.8 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 7 0 0)
           (cons 50 0)
          )
         )
         (entmake
          (list
           (cons 0 "POINT")
           (cons 100 "AcDbEntity")
           (cons 67 0)
           (cons 8 "0")
           (cons 100 "AcDbPoint")
           (list 10 7 4.25 0)
           (cons 50 0)
          )
         )
         (entmake
          (list
           (cons 0 "POINT")
           (cons 100 "AcDbEntity")
           (cons 67 0)
           (cons 8 "0")
           (cons 100 "AcDbPoint")
           (list 10 7 -4.25 0)
           (cons 50 0)
          )
         )
         (entmake
          (list
           (cons 0 "ATTDEF")
           (cons 100 "AcDbEntity")
           (cons 67 0)
           (cons 8 "0")
           (cons 100 "AcDbText")
           (list 10 -2.29658793 1.85914261 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 0.76552931 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -0.32808399 0)
           (cons 40 0.65616798)
           (cons 1 "7.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -1.42169729 0)
           (cons 40 0.65616798)
           (cons 1 "7.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-100T-TRAILER"))
        (progn
         (entmake)
         (entmake
          (list
           (cons 0 "BLOCK")
           (cons 2 "AASHTO-2011-WB-100T-TRAILER")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4.25)
           (cons 40 0)
           (cons 41 0)
           (cons 42 0)
           (cons 91 0)
           (list 10 28.5 -4.25)
           (cons 40 0)
           (cons 41 0)
           (cons 42 0)
           (cons 91 0)
           (list 10 28.5 4.25)
           (cons 40 0)
           (cons 41 0)
           (cons 42 0)
           (cons 91 0)
           (list 10 0 4.25)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 28.5 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 28.5 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 2.5 0 0)
           (cons 40 0.34)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 -2.59333333)
           (cons 40 0)
           (cons 41 0)
           (cons 42 0)
           (cons 91 0)
           (list 10 23.83333333 -2.07333333)
           (cons 40 0)
           (cons 41 0)
           (cons 42 0)
           (cons 91 0)
           (list 10 24.3 -1.91666667)
           (cons 40 0)
           (cons 41 0)
           (cons 42 0)
           (cons 91 0)
           (list 10 26.7 -1.91666667)
           (cons 40 0)
           (cons 41 0)
           (cons 42 0)
           (cons 91 0)
           (list 10 27.16666667 -2.07333333)
           (cons 40 0)
           (cons 41 0)
           (cons 42 0)
           (cons 91 0)
           (list 10 27.16666667 -2.59333333)
           (cons 40 0)
           (cons 41 0)
           (cons 42 0)
           (cons 91 0)
           (list 10 26.7 -2.75)
           (cons 40 0)
           (cons 41 0)
           (cons 42 0)
           (cons 91 0)
           (list 10 24.3 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 -4.09333333)
           (cons 40 0)
           (cons 41 0)
           (cons 42 0)
           (cons 91 0)
           (list 10 23.83333333 -3.57333333)
           (cons 40 0)
           (cons 41 0)
           (cons 42 0)
           (cons 91 0)
           (list 10 24.3 -3.41666667)
           (cons 40 0)
           (cons 41 0)
           (cons 42 0)
           (cons 91 0)
           (list 10 26.7 -3.41666667)
           (cons 40 0)
           (cons 41 0)
           (cons 42 0)
           (cons 91 0)
           (list 10 27.16666667 -3.57333333)
           (cons 40 0)
           (cons 41 0)
           (cons 42 0)
           (cons 91 0)
           (list 10 27.16666667 -4.09333333)
           (cons 40 0)
           (cons 41 0)
           (cons 42 0)
           (cons 91 0)
           (list 10 26.7 -4.25)
           (cons 40 0)
           (cons 41 0)
           (cons 42 0)
           (cons 91 0)
           (list 10 24.3 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 2.07333333)
           (cons 40 0)
           (cons 41 0)
           (cons 42 0)
           (cons 91 0)
           (list 10 23.83333333 2.59333333)
           (cons 40 0)
           (cons 41 0)
           (cons 42 0)
           (cons 91 0)
           (list 10 24.3 2.75)
           (cons 40 0)
           (cons 41 0)
           (cons 42 0)
           (cons 91 0)
           (list 10 26.7 2.75)
           (cons 40 0)
           (cons 41 0)
           (cons 42 0)
           (cons 91 0)
           (list 10 27.16666667 2.59333333)
           (cons 40 0)
           (cons 41 0)
           (cons 42 0)
           (cons 91 0)
           (list 10 27.16666667 2.07333333)
           (cons 40 0)
           (cons 41 0)
           (cons 42 0)
           (cons 91 0)
           (list 10 26.7 1.91666667)
           (cons 40 0)
           (cons 41 0)
           (cons 42 0)
           (cons 91 0)
           (list 10 24.3 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 3.57333333)
           (cons 40 0)
           (cons 41 0)
           (cons 42 0)
           (cons 91 0)
           (list 10 23.83333333 4.09333333)
           (cons 40 0)
           (cons 41 0)
           (cons 42 0)
           (cons 91 0)
           (list 10 24.3 4.25)
           (cons 40 0)
           (cons 41 0)
           (cons 42 0)
           (cons 91 0)
           (list 10 26.7 4.25)
           (cons 40 0)
           (cons 41 0)
           (cons 42 0)
           (cons 91 0)
           (list 10 27.16666667 4.09333333)
           (cons 40 0)
           (cons 41 0)
           (cons 42 0)
           (cons 91 0)
           (list 10 27.16666667 3.57333333)
           (cons 40 0)
           (cons 41 0)
           (cons 42 0)
           (cons 91 0)
           (list 10 26.7 3.41666667)
           (cons 40 0)
           (cons 41 0)
           (cons 42 0)
           (cons 91 0)
           (list 10 24.3 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4.25 0)
           (cons 50 0)
          )
         )
         (entmake
          (list
           (cons 0 "POINT")
           (cons 100 "AcDbEntity")
           (cons 67 0)
           (cons 8 "0")
           (cons 100 "AcDbPoint")
           (list 10 25.5 -4.25 0)
           (cons 50 0)
          )
         )
         (entmake
          (list
           (cons 0 "POINT")
           (cons 100 "AcDbEntity")
           (cons 67 0)
           (cons 8 "0")
           (cons 100 "AcDbPoint")
           (list 10 28.5 -4.25 0)
           (cons 50 0)
          )
         )
         (entmake
          (list
           (cons 0 "POINT")
           (cons 100 "AcDbEntity")
           (cons 67 0)
           (cons 8 "0")
           (cons 100 "AcDbPoint")
           (list 10 28.5 0 0)
           (cons 50 0)
          )
         )
         (entmake
          (list
           (cons 0 "POINT")
           (cons 100 "AcDbEntity")
           (cons 67 0)
           (cons 8 "0")
           (cons 100 "AcDbPoint")
           (list 10 28.5 4.25 0)
           (cons 50 0)
          )
         )
         (entmake
          (list
           (cons 0 "POINT")
           (cons 100 "AcDbEntity")
           (cons 67 0)
           (cons 8 "0")
           (cons 100 "AcDbPoint")
           (list 10 25.5 4.25 0)
           (cons 50 0)
          )
         )
         (entmake
          (list
           (cons 0 "POINT")
           (cons 100 "AcDbEntity")
           (cons 67 0)
           (cons 8 "0")
           (cons 100 "AcDbPoint")
           (list 10 0 4.25 0)
           (cons 50 0)
          )
         )
         (entmake
          (list
           (cons 0 "POINT")
           (cons 100 "AcDbEntity")
           (cons 67 0)
           (cons 8 "0")
           (cons 100 "AcDbPoint")
           (list 10 2.5 0 0)
           (cons 50 0)
          )
         )
         (entmake
          (list
           (cons 0 "ATTDEF")
           (cons 100 "AcDbEntity")
           (cons 67 0)
           (cons 8 "0")
           (cons 100 "AcDbText")
           (list 10 0.20341207 1.85914261 0)
           (cons 40 0.65616798)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 0.76552931 0)
           (cons 40 0.65616798)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -0.32808399 0)
           (cons 40 0.65616798)
           (cons 1 "25.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -1.42169729 0)
           (cons 40 0.65616798)
           (cons 1 "28.500")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-100T-TRUCK"))
        (progn
         (entmake)
         (entmake
          (list
           (cons 0 "BLOCK")
           (cons 2 "AASHTO-2011-WB-100T-TRUCK")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4)
           (cons 40 0)
           (cons 41 0)
           (cons 42 0)
           (cons 91 0)
           (list 10 13.3 -4)
           (cons 40 0)
           (cons 41 0)
           (cons 42 0)
           (cons 91 0)
           (list 10 13.3 4)
           (cons 40 0)
           (cons 41 0)
           (cons 42 0)
           (cons 91 0)
           (list 10 0 4)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.5 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.5 -1.66666667 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 13.3 -1.66666667 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 13.3 1.66666667 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.5 1.66666667 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.5 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 12.8 0 0)
           (cons 40 1.14285714)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 13.60812204 -0.80812204 0)
           (list 11 13.60812204 0.80812204 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.63333333 -2.34333333)
           (cons 40 0)
           (cons 41 0)
           (cons 42 0)
           (cons 91 0)
           (list 10 11.63333333 -1.82333333)
           (cons 40 0)
           (cons 41 0)
           (cons 42 0)
           (cons 91 0)
           (list 10 12.1 -1.66666667)
           (cons 40 0)
           (cons 41 0)
           (cons 42 0)
           (cons 91 0)
           (list 10 14.5 -1.66666667)
           (cons 40 0)
           (cons 41 0)
           (cons 42 0)
           (cons 91 0)
           (list 10 14.96666667 -1.82333333)
           (cons 40 0)
           (cons 41 0)
           (cons 42 0)
           (cons 91 0)
           (list 10 14.96666667 -2.34333333)
           (cons 40 0)
           (cons 41 0)
           (cons 42 0)
           (cons 91 0)
           (list 10 14.5 -2.5)
           (cons 40 0)
           (cons 41 0)
           (cons 42 0)
           (cons 91 0)
           (list 10 12.1 -2.5)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.63333333 -3.84333333)
           (cons 40 0)
           (cons 41 0)
           (cons 42 0)
           (cons 91 0)
           (list 10 11.63333333 -3.32333333)
           (cons 40 0)
           (cons 41 0)
           (cons 42 0)
           (cons 91 0)
           (list 10 12.1 -3.16666667)
           (cons 40 0)
           (cons 41 0)
           (cons 42 0)
           (cons 91 0)
           (list 10 14.5 -3.16666667)
           (cons 40 0)
           (cons 41 0)
           (cons 42 0)
           (cons 91 0)
           (list 10 14.96666667 -3.32333333)
           (cons 40 0)
           (cons 41 0)
           (cons 42 0)
           (cons 91 0)
           (list 10 14.96666667 -3.84333333)
           (cons 40 0)
           (cons 41 0)
           (cons 42 0)
           (cons 91 0)
           (list 10 14.5 -4)
           (cons 40 0)
           (cons 41 0)
           (cons 42 0)
           (cons 91 0)
           (list 10 12.1 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.63333333 1.82333333)
           (cons 40 0)
           (cons 41 0)
           (cons 42 0)
           (cons 91 0)
           (list 10 11.63333333 2.34333333)
           (cons 40 0)
           (cons 41 0)
           (cons 42 0)
           (cons 91 0)
           (list 10 12.1 2.5)
           (cons 40 0)
           (cons 41 0)
           (cons 42 0)
           (cons 91 0)
           (list 10 14.5 2.5)
           (cons 40 0)
           (cons 41 0)
           (cons 42 0)
           (cons 91 0)
           (list 10 14.96666667 2.34333333)
           (cons 40 0)
           (cons 41 0)
           (cons 42 0)
           (cons 91 0)
           (list 10 14.96666667 1.82333333)
           (cons 40 0)
           (cons 41 0)
           (cons 42 0)
           (cons 91 0)
           (list 10 14.5 1.66666667)
           (cons 40 0)
           (cons 41 0)
           (cons 42 0)
           (cons 91 0)
           (list 10 12.1 1.66666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.63333333 3.32333333)
           (cons 40 0)
           (cons 41 0)
           (cons 42 0)
           (cons 91 0)
           (list 10 11.63333333 3.84333333)
           (cons 40 0)
           (cons 41 0)
           (cons 42 0)
           (cons 91 0)
           (list 10 12.1 4)
           (cons 40 0)
           (cons 41 0)
           (cons 42 0)
           (cons 91 0)
           (list 10 14.5 4)
           (cons 40 0)
           (cons 41 0)
           (cons 42 0)
           (cons 91 0)
           (list 10 14.96666667 3.84333333)
           (cons 40 0)
           (cons 41 0)
           (cons 42 0)
           (cons 91 0)
           (list 10 14.96666667 3.32333333)
           (cons 40 0)
           (cons 41 0)
           (cons 42 0)
           (cons 91 0)
           (list 10 14.5 3.16666667)
           (cons 40 0)
           (cons 41 0)
           (cons 42 0)
           (cons 91 0)
           (list 10 12.1 3.16666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4 0)
           (cons 50 0)
          )
         )
         (entmake
          (list
           (cons 0 "POINT")
           (cons 100 "AcDbEntity")
           (cons 67 0)
           (cons 8 "0")
           (cons 100 "AcDbPoint")
           (list 10 2.3 -4 0)
           (cons 50 0)
          )
         )
         (entmake
          (list
           (cons 0 "POINT")
           (cons 100 "AcDbEntity")
           (cons 67 0)
           (cons 8 "0")
           (cons 100 "AcDbPoint")
           (list 10 13.3 -4 0)
           (cons 50 0)
          )
         )
         (entmake
          (list
           (cons 0 "POINT")
           (cons 100 "AcDbEntity")
           (cons 67 0)
           (cons 8 "0")
           (cons 100 "AcDbPoint")
           (list 10 13.3 4 0)
           (cons 50 0)
          )
         )
         (entmake
          (list
           (cons 0 "POINT")
           (cons 100 "AcDbEntity")
           (cons 67 0)
           (cons 8 "0")
           (cons 100 "AcDbPoint")
           (list 10 2.3 4 0)
           (cons 50 0)
          )
         )
         (entmake
          (list
           (cons 0 "POINT")
           (cons 100 "AcDbEntity")
           (cons 67 0)
           (cons 8 "0")
           (cons 100 "AcDbPoint")
           (list 10 0 4 0)
           (cons 50 0)
          )
         )
         (entmake
          (list
           (cons 0 "POINT")
           (cons 100 "AcDbEntity")
           (cons 67 0)
           (cons 8 "0")
           (cons 100 "AcDbPoint")
           (list 10 12.8 0 0)
           (cons 50 0)
          )
         )
         (entmake
          (list
           (cons 0 "POINT")
           (cons 100 "AcDbEntity")
           (cons 67 0)
           (cons 8 "0")
           (cons 100 "AcDbPoint")
           (list 10 2.3 0 0)
           (cons 50 0)
          )
         )
         (entmake
          (list
           (cons 0 "INSERT")
           (cons 100 "AcDbEntity")
           (cons 67 0)
           (cons 8 "0")
           (cons 100 "AcDbBlockReference")
           (cons 2 "WheelLeft2")
           (list 10 2.3 -3.16666667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRight2")
           (list 10 2.3 3.16666667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 0.0328084 1.85914261 0)
           (cons 40 0.65616798)
           (cons 1 "2.300")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.0328084 0.76552931 0)
           (cons 40 0.65616798)
           (cons 1 "2.300")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.0328084 -0.32808399 0)
           (cons 40 0.65616798)
           (cons 1 "13.300")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.0328084 -1.42169729 0)
           (cons 40 0.65616798)
           (cons 1 "12.800")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.0328084 -2.51531059 0)
           (cons 40 0.65616798)
           (cons 1 "15.6")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-92D-TRAILER2"))
        (progn
         (entmake)
         (entmake
          (list
           (cons 0 "BLOCK")
           (cons 2 "AASHTO-2011-WB-92D-TRAILER2")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 28.5 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 28.5 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 2.5 0 0)
           (cons 40 0.56666667)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 -2.59333333)
           (cons 40 0)
           (cons 41 0)
           (cons 42 0)
           (cons 91 0)
           (list 10 23.83333333 -2.07333333)
           (cons 40 0)
           (cons 41 0)
           (cons 42 0)
           (cons 91 0)
           (list 10 24.3 -1.91666667)
           (cons 40 0)
           (cons 41 0)
           (cons 42 0)
           (cons 91 0)
           (list 10 26.7 -1.91666667)
           (cons 40 0)
           (cons 41 0)
           (cons 42 0)
           (cons 91 0)
           (list 10 27.16666667 -2.07333333)
           (cons 40 0)
           (cons 41 0)
           (cons 42 0)
           (cons 91 0)
           (list 10 27.16666667 -2.59333333)
           (cons 40 0)
           (cons 41 0)
           (cons 42 0)
           (cons 91 0)
           (list 10 26.7 -2.75)
           (cons 40 0)
           (cons 41 0)
           (cons 42 0)
           (cons 91 0)
           (list 10 24.3 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 -4.09333333)
           (cons 40 0)
           (cons 41 0)
           (cons 42 0)
           (cons 91 0)
           (list 10 23.83333333 -3.57333333)
           (cons 40 0)
           (cons 41 0)
           (cons 42 0)
           (cons 91 0)
           (list 10 24.3 -3.41666667)
           (cons 40 0)
           (cons 41 0)
           (cons 42 0)
           (cons 91 0)
           (list 10 26.7 -3.41666667)
           (cons 40 0)
           (cons 41 0)
           (cons 42 0)
           (cons 91 0)
           (list 10 27.16666667 -3.57333333)
           (cons 40 0)
           (cons 41 0)
           (cons 42 0)
           (cons 91 0)
           (list 10 27.16666667 -4.09333333)
           (cons 40 0)
           (cons 41 0)
           (cons 42 0)
           (cons 91 0)
           (list 10 26.7 -4.25)
           (cons 40 0)
           (cons 41 0)
           (cons 42 0)
           (cons 91 0)
           (list 10 24.3 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 2.07333333)
           (cons 40 0)
           (cons 41 0)
           (cons 42 0)
           (cons 91 0)
           (list 10 23.83333333 2.59333333)
           (cons 40 0)
           (cons 41 0)
           (cons 42 0)
           (cons 91 0)
           (list 10 24.3 2.75)
           (cons 40 0)
           (cons 41 0)
           (cons 42 0)
           (cons 91 0)
           (list 10 26.7 2.75)
           (cons 40 0)
           (cons 41 0)
           (cons 42 0)
           (cons 91 0)
           (list 10 27.16666667 2.59333333)
           (cons 40 0)
           (cons 41 0)
           (cons 42 0)
           (cons 91 0)
           (list 10 27.16666667 2.07333333)
           (cons 40 0)
           (cons 41 0)
           (cons 42 0)
           (cons 91 0)
           (list 10 26.7 1.91666667)
           (cons 40 0)
           (cons 41 0)
           (cons 42 0)
           (cons 91 0)
           (list 10 24.3 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 3.57333333)
           (cons 40 0)
           (cons 41 0)
           (cons 42 0)
           (cons 91 0)
           (list 10 23.83333333 4.09333333)
           (cons 40 0)
           (cons 41 0)
           (cons 42 0)
           (cons 91 0)
           (list 10 24.3 4.25)
           (cons 40 0)
           (cons 41 0)
           (cons 42 0)
           (cons 91 0)
           (list 10 26.7 4.25)
           (cons 40 0)
           (cons 41 0)
           (cons 42 0)
           (cons 91 0)
           (list 10 27.16666667 4.09333333)
           (cons 40 0)
           (cons 41 0)
           (cons 42 0)
           (cons 91 0)
           (list 10 27.16666667 3.57333333)
           (cons 40 0)
           (cons 41 0)
           (cons 42 0)
           (cons 91 0)
           (list 10 26.7 3.41666667)
           (cons 40 0)
           (cons 41 0)
           (cons 42 0)
           (cons 91 0)
           (list 10 24.3 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4.25 0)
           (cons 50 0)
          )
         )
         (entmake
          (list
           (cons 0 "POINT")
           (cons 100 "AcDbEntity")
           (cons 67 0)
           (cons 8 "0")
           (cons 100 "AcDbPoint")
           (list 10 25.5 -4.25 0)
           (cons 50 0)
          )
         )
         (entmake
          (list
           (cons 0 "POINT")
           (cons 100 "AcDbEntity")
           (cons 67 0)
           (cons 8 "0")
           (cons 100 "AcDbPoint")
           (list 10 28.5 -4.25 0)
           (cons 50 0)
          )
         )
         (entmake
          (list
           (cons 0 "POINT")
           (cons 100 "AcDbEntity")
           (cons 67 0)
           (cons 8 "0")
           (cons 100 "AcDbPoint")
           (list 10 28.5 4.25 0)
           (cons 50 0)
          )
         )
         (entmake
          (list
           (cons 0 "POINT")
           (cons 100 "AcDbEntity")
           (cons 67 0)
           (cons 8 "0")
           (cons 100 "AcDbPoint")
           (list 10 25.5 4.25 0)
           (cons 50 0)
          )
         )
         (entmake
          (list
           (cons 0 "POINT")
           (cons 100 "AcDbEntity")
           (cons 67 0)
           (cons 8 "0")
           (cons 100 "AcDbPoint")
           (list 10 0 4.25 0)
           (cons 50 0)
          )
         )
         (entmake
          (list
           (cons 0 "POINT")
           (cons 100 "AcDbEntity")
           (cons 67 0)
           (cons 8 "0")
           (cons 100 "AcDbPoint")
           (list 10 2.5 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4.25)
           (cons 40 0)
           (cons 41 0)
           (cons 42 0)
           (cons 91 0)
           (list 10 28.5 -4.25)
           (cons 40 0)
           (cons 41 0)
           (cons 42 0)
           (cons 91 0)
           (list 10 28.5 4.25)
           (cons 40 0)
           (cons 41 0)
           (cons 42 0)
           (cons 91 0)
           (list 10 0 4.25)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.20341207 1.85914261 0)
           (cons 40 0.65616798)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 0.76552931 0)
           (cons 40 0.65616798)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -0.32808399 0)
           (cons 40 0.65616798)
           (cons 1 "25.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-92D-PUP"))
        (progn
         (entmake)
         (entmake
          (list
           (cons 0 "BLOCK")
           (cons 2 "AASHTO-2011-WB-92D-PUP")
           (cons 70 2)
           (cons 4 "")
           (list 10 0 0 0)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 7 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.56666667)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.33333333 -2.59333333)
           (cons 40 0)
           (cons 41 0)
           (cons 42 0)
           (cons 91 0)
           (list 10 5.33333333 -2.07333333)
           (cons 40 0)
           (cons 41 0)
           (cons 42 0)
           (cons 91 0)
           (list 10 5.8 -1.91666667)
           (cons 40 0)
           (cons 41 0)
           (cons 42 0)
           (cons 91 0)
           (list 10 8.2 -1.91666667)
           (cons 40 0)
           (cons 41 0)
           (cons 42 0)
           (cons 91 0)
           (list 10 8.66666667 -2.07333333)
           (cons 40 0)
           (cons 41 0)
           (cons 42 0)
           (cons 91 0)
           (list 10 8.66666667 -2.59333333)
           (cons 40 0)
           (cons 41 0)
           (cons 42 0)
           (cons 91 0)
           (list 10 8.2 -2.75)
           (cons 40 0)
           (cons 41 0)
           (cons 42 0)
           (cons 91 0)
           (list 10 5.8 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.33333333 -4.09333333)
           (cons 40 0)
           (cons 41 0)
           (cons 42 0)
           (cons 91 0)
           (list 10 5.33333333 -3.57333333)
           (cons 40 0)
           (cons 41 0)
           (cons 42 0)
           (cons 91 0)
           (list 10 5.8 -3.41666667)
           (cons 40 0)
           (cons 41 0)
           (cons 42 0)
           (cons 91 0)
           (list 10 8.2 -3.41666667)
           (cons 40 0)
           (cons 41 0)
           (cons 42 0)
           (cons 91 0)
           (list 10 8.66666667 -3.57333333)
           (cons 40 0)
           (cons 41 0)
           (cons 42 0)
           (cons 91 0)
           (list 10 8.66666667 -4.09333333)
           (cons 40 0)
           (cons 41 0)
           (cons 42 0)
           (cons 91 0)
           (list 10 8.2 -4.25)
           (cons 40 0)
           (cons 41 0)
           (cons 42 0)
           (cons 91 0)
           (list 10 5.8 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.33333333 2.07333333)
           (cons 40 0)
           (cons 41 0)
           (cons 42 0)
           (cons 91 0)
           (list 10 5.33333333 2.59333333)
           (cons 40 0)
           (cons 41 0)
           (cons 42 0)
           (cons 91 0)
           (list 10 5.8 2.75)
           (cons 40 0)
           (cons 41 0)
           (cons 42 0)
           (cons 91 0)
           (list 10 8.2 2.75)
           (cons 40 0)
           (cons 41 0)
           (cons 42 0)
           (cons 91 0)
           (list 10 8.66666667 2.59333333)
           (cons 40 0)
           (cons 41 0)
           (cons 42 0)
           (cons 91 0)
           (list 10 8.66666667 2.07333333)
           (cons 40 0)
           (cons 41 0)
           (cons 42 0)
           (cons 91 0)
           (list 10 8.2 1.91666667)
           (cons 40 0)
           (cons 41 0)
           (cons 42 0)
           (cons 91 0)
           (list 10 5.8 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.33333333 3.57333333)
           (cons 40 0)
           (cons 41 0)
           (cons 42 0)
           (cons 91 0)
           (list 10 5.33333333 4.09333333)
           (cons 40 0)
           (cons 41 0)
           (cons 42 0)
           (cons 91 0)
           (list 10 5.8 4.25)
           (cons 40 0)
           (cons 41 0)
           (cons 42 0)
           (cons 91 0)
           (list 10 8.2 4.25)
           (cons 40 0)
           (cons 41 0)
           (cons 42 0)
           (cons 91 0)
           (list 10 8.66666667 4.09333333)
           (cons 40 0)
           (cons 41 0)
           (cons 42 0)
           (cons 91 0)
           (list 10 8.66666667 3.57333333)
           (cons 40 0)
           (cons 41 0)
           (cons 42 0)
           (cons 91 0)
           (list 10 8.2 3.41666667)
           (cons 40 0)
           (cons 41 0)
           (cons 42 0)
           (cons 91 0)
           (list 10 5.8 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 7 -4.25 0)
           (cons 50 0)
          )
         )
         (entmake
          (list
           (cons 0 "POINT")
           (cons 100 "AcDbEntity")
           (cons 67 0)
           (cons 8 "0")
           (cons 100 "AcDbPoint")
           (list 10 7 4.25 0)
           (cons 50 0)
          )
         )
         (entmake
          (list
           (cons 0 "POINT")
           (cons 100 "AcDbEntity")
           (cons 67 0)
           (cons 8 "0")
           (cons 100 "AcDbPoint")
           (list 10 7 0 0)
           (cons 50 0)
          )
         )
         (entmake
          (list
           (cons 0 "LWPOLYLINE")
           (cons 100 "AcDbEntity")
           (cons 67 0)
           (cons 8 "Defpoints")
           (cons 100 "AcDbPolyline")
           (cons 90 3)
           (cons 70 1)
           (cons 43 0)
           (cons 38 0)
           (cons 39 0)
           (list 10 0 0)
           (cons 40 0)
           (cons 41 0)
           (cons 42 0)
           (cons 91 0)
           (list 10 7 4.25)
           (cons 40 0)
           (cons 41 0)
           (cons 42 0)
           (cons 91 0)
           (list 10 7 -4.25)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 -2.29658793 1.85914261 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 0.76552931 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -0.32808399 0)
           (cons 40 0.65616798)
           (cons 1 "7.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -1.42169729 0)
           (cons 40 0.65616798)
           (cons 1 "7.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-92D-TRAILER1"))
        (progn
         (entmake)
         (entmake
          (list
           (cons 0 "BLOCK")
           (cons 2 "AASHTO-2011-WB-92D-TRAILER1")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 48 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 48 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 48 0 0)
           (list 11 48 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 48 0 0)
           (cons 40 0.33333333)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 3 0 0)
           (cons 40 0.34)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 39.75 -2.59333333)
           (cons 40 0)
           (cons 41 0)
           (cons 42 0)
           (cons 91 0)
           (list 10 39.75 -2.07333333)
           (cons 40 0)
           (cons 41 0)
           (cons 42 0)
           (cons 91 0)
           (list 10 40.21666667 -1.91666667)
           (cons 40 0)
           (cons 41 0)
           (cons 42 0)
           (cons 91 0)
           (list 10 42.61666667 -1.91666667)
           (cons 40 0)
           (cons 41 0)
           (cons 42 0)
           (cons 91 0)
           (list 10 43.08333333 -2.07333333)
           (cons 40 0)
           (cons 41 0)
           (cons 42 0)
           (cons 91 0)
           (list 10 43.08333333 -2.59333333)
           (cons 40 0)
           (cons 41 0)
           (cons 42 0)
           (cons 91 0)
           (list 10 42.61666667 -2.75)
           (cons 40 0)
           (cons 41 0)
           (cons 42 0)
           (cons 91 0)
           (list 10 40.21666667 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 39.75 -4.09333333)
           (cons 40 0)
           (cons 41 0)
           (cons 42 0)
           (cons 91 0)
           (list 10 39.75 -3.57333333)
           (cons 40 0)
           (cons 41 0)
           (cons 42 0)
           (cons 91 0)
           (list 10 40.21666667 -3.41666667)
           (cons 40 0)
           (cons 41 0)
           (cons 42 0)
           (cons 91 0)
           (list 10 42.61666667 -3.41666667)
           (cons 40 0)
           (cons 41 0)
           (cons 42 0)
           (cons 91 0)
           (list 10 43.08333333 -3.57333333)
           (cons 40 0)
           (cons 41 0)
           (cons 42 0)
           (cons 91 0)
           (list 10 43.08333333 -4.09333333)
           (cons 40 0)
           (cons 41 0)
           (cons 42 0)
           (cons 91 0)
           (list 10 42.61666667 -4.25)
           (cons 40 0)
           (cons 41 0)
           (cons 42 0)
           (cons 91 0)
           (list 10 40.21666667 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 39.75 2.07333333)
           (cons 40 0)
           (cons 41 0)
           (cons 42 0)
           (cons 91 0)
           (list 10 39.75 2.59333333)
           (cons 40 0)
           (cons 41 0)
           (cons 42 0)
           (cons 91 0)
           (list 10 40.21666667 2.75)
           (cons 40 0)
           (cons 41 0)
           (cons 42 0)
           (cons 91 0)
           (list 10 42.61666667 2.75)
           (cons 40 0)
           (cons 41 0)
           (cons 42 0)
           (cons 91 0)
           (list 10 43.08333333 2.59333333)
           (cons 40 0)
           (cons 41 0)
           (cons 42 0)
           (cons 91 0)
           (list 10 43.08333333 2.07333333)
           (cons 40 0)
           (cons 41 0)
           (cons 42 0)
           (cons 91 0)
           (list 10 42.61666667 1.91666667)
           (cons 40 0)
           (cons 41 0)
           (cons 42 0)
           (cons 91 0)
           (list 10 40.21666667 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 39.75 3.57333333)
           (cons 40 0)
           (cons 41 0)
           (cons 42 0)
           (cons 91 0)
           (list 10 39.75 4.09333333)
           (cons 40 0)
           (cons 41 0)
           (cons 42 0)
           (cons 91 0)
           (list 10 40.21666667 4.25)
           (cons 40 0)
           (cons 41 0)
           (cons 42 0)
           (cons 91 0)
           (list 10 42.61666667 4.25)
           (cons 40 0)
           (cons 41 0)
           (cons 42 0)
           (cons 91 0)
           (list 10 43.08333333 4.09333333)
           (cons 40 0)
           (cons 41 0)
           (cons 42 0)
           (cons 91 0)
           (list 10 43.08333333 3.57333333)
           (cons 40 0)
           (cons 41 0)
           (cons 42 0)
           (cons 91 0)
           (list 10 42.61666667 3.41666667)
           (cons 40 0)
           (cons 41 0)
           (cons 42 0)
           (cons 91 0)
           (list 10 40.21666667 3.41666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 43.91666667 -2.59333333)
           (cons 40 0)
           (cons 41 0)
           (cons 42 0)
           (cons 91 0)
           (list 10 43.91666667 -2.07333333)
           (cons 40 0)
           (cons 41 0)
           (cons 42 0)
           (cons 91 0)
           (list 10 44.38333333 -1.91666667)
           (cons 40 0)
           (cons 41 0)
           (cons 42 0)
           (cons 91 0)
           (list 10 46.78333333 -1.91666667)
           (cons 40 0)
           (cons 41 0)
           (cons 42 0)
           (cons 91 0)
           (list 10 47.25 -2.07333333)
           (cons 40 0)
           (cons 41 0)
           (cons 42 0)
           (cons 91 0)
           (list 10 47.25 -2.59333333)
           (cons 40 0)
           (cons 41 0)
           (cons 42 0)
           (cons 91 0)
           (list 10 46.78333333 -2.75)
           (cons 40 0)
           (cons 41 0)
           (cons 42 0)
           (cons 91 0)
           (list 10 44.38333333 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 43.91666667 -4.09333333)
           (cons 40 0)
           (cons 41 0)
           (cons 42 0)
           (cons 91 0)
           (list 10 43.91666667 -3.57333333)
           (cons 40 0)
           (cons 41 0)
           (cons 42 0)
           (cons 91 0)
           (list 10 44.38333333 -3.41666667)
           (cons 40 0)
           (cons 41 0)
           (cons 42 0)
           (cons 91 0)
           (list 10 46.78333333 -3.41666667)
           (cons 40 0)
           (cons 41 0)
           (cons 42 0)
           (cons 91 0)
           (list 10 47.25 -3.57333333)
           (cons 40 0)
           (cons 41 0)
           (cons 42 0)
           (cons 91 0)
           (list 10 47.25 -4.09333333)
           (cons 40 0)
           (cons 41 0)
           (cons 42 0)
           (cons 91 0)
           (list 10 46.78333333 -4.25)
           (cons 40 0)
           (cons 41 0)
           (cons 42 0)
           (cons 91 0)
           (list 10 44.38333333 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 43.91666667 2.07333333)
           (cons 40 0)
           (cons 41 0)
           (cons 42 0)
           (cons 91 0)
           (list 10 43.91666667 2.59333333)
           (cons 40 0)
           (cons 41 0)
           (cons 42 0)
           (cons 91 0)
           (list 10 44.38333333 2.75)
           (cons 40 0)
           (cons 41 0)
           (cons 42 0)
           (cons 91 0)
           (list 10 46.78333333 2.75)
           (cons 40 0)
           (cons 41 0)
           (cons 42 0)
           (cons 91 0)
           (list 10 47.25 2.59333333)
           (cons 40 0)
           (cons 41 0)
           (cons 42 0)
           (cons 91 0)
           (list 10 47.25 2.07333333)
           (cons 40 0)
           (cons 41 0)
           (cons 42 0)
           (cons 91 0)
           (list 10 46.78333333 1.91666667)
           (cons 40 0)
           (cons 41 0)
           (cons 42 0)
           (cons 91 0)
           (list 10 44.38333333 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 43.91666667 3.57333333)
           (cons 40 0)
           (cons 41 0)
           (cons 42 0)
           (cons 91 0)
           (list 10 43.91666667 4.09333333)
           (cons 40 0)
           (cons 41 0)
           (cons 42 0)
           (cons 91 0)
           (list 10 44.38333333 4.25)
           (cons 40 0)
           (cons 41 0)
           (cons 42 0)
           (cons 91 0)
           (list 10 46.78333333 4.25)
           (cons 40 0)
           (cons 41 0)
           (cons 42 0)
           (cons 91 0)
           (list 10 47.25 4.09333333)
           (cons 40 0)
           (cons 41 0)
           (cons 42 0)
           (cons 91 0)
           (list 10 47.25 3.57333333)
           (cons 40 0)
           (cons 41 0)
           (cons 42 0)
           (cons 91 0)
           (list 10 46.78333333 3.41666667)
           (cons 40 0)
           (cons 41 0)
           (cons 42 0)
           (cons 91 0)
           (list 10 44.38333333 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 3 0 0)
           (cons 50 0)
          )
         )
         (entmake
          (list
           (cons 0 "POINT")
           (cons 100 "AcDbEntity")
           (cons 67 0)
           (cons 8 "0")
           (cons 100 "AcDbPoint")
           (list 10 48 0 0)
           (cons 50 0)
          )
         )
         (entmake
          (list
           (cons 0 "POINT")
           (cons 100 "AcDbEntity")
           (cons 67 0)
           (cons 8 "0")
           (cons 100 "AcDbPoint")
           (list 10 43.5 4.25 0)
           (cons 50 0)
          )
         )
         (entmake
          (list
           (cons 0 "POINT")
           (cons 100 "AcDbEntity")
           (cons 67 0)
           (cons 8 "0")
           (cons 100 "AcDbPoint")
           (list 10 43.5 -4.25 0)
           (cons 50 0)
          )
         )
         (entmake
          (list
           (cons 0 "POINT")
           (cons 100 "AcDbEntity")
           (cons 67 0)
           (cons 8 "0")
           (cons 100 "AcDbPoint")
           (list 10 0 -4.25 0)
           (cons 50 0)
          )
         )
         (entmake
          (list
           (cons 0 "POINT")
           (cons 100 "AcDbEntity")
           (cons 67 0)
           (cons 8 "0")
           (cons 100 "AcDbPoint")
           (list 10 0 4.25 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4.25)
           (cons 40 0)
           (cons 41 0)
           (cons 42 0)
           (cons 91 0)
           (list 10 48 -4.25)
           (cons 40 0)
           (cons 41 0)
           (cons 42 0)
           (cons 91 0)
           (list 10 48 4.25)
           (cons 40 0)
           (cons 41 0)
           (cons 42 0)
           (cons 91 0)
           (list 10 0 4.25)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 48 4.25 0)
           (cons 50 0)
          )
         )
         (entmake
          (list
           (cons 0 "POINT")
           (cons 100 "AcDbEntity")
           (cons 67 0)
           (cons 8 "0")
           (cons 100 "AcDbPoint")
           (list 10 48 -4.25 0)
           (cons 50 0)
          )
         )
         (entmake
          (list
           (cons 0 "ATTDEF")
           (cons 100 "AcDbEntity")
           (cons 67 0)
           (cons 8 "0")
           (cons 100 "AcDbText")
           (list 10 0.70341207 1.85914261 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 0.76552931 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -0.32808399 0)
           (cons 40 0.65616798)
           (cons 1 "43.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -1.42169729 0)
           (cons 40 0.65616798)
           (cons 1 "48.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-92D-TRUCK"))
        (progn
         (entmake)
         (entmake
          (list
           (cons 0 "BLOCK")
           (cons 2 "AASHTO-2011-WB-92D-TRUCK")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.5 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.5 -1.66666667 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 21.9 -1.66666667 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 21.9 1.66666667 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.5 1.66666667 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.5 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 19.3 0 0)
           (cons 40 1.14285714)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 20.10812204 -0.80812204 0)
           (list 11 20.10812204 0.80812204 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 16.03333333 -2.34333333)
           (cons 40 0)
           (cons 41 0)
           (cons 42 0)
           (cons 91 0)
           (list 10 16.03333333 -1.82333333)
           (cons 40 0)
           (cons 41 0)
           (cons 42 0)
           (cons 91 0)
           (list 10 16.5 -1.66666667)
           (cons 40 0)
           (cons 41 0)
           (cons 42 0)
           (cons 91 0)
           (list 10 18.9 -1.66666667)
           (cons 40 0)
           (cons 41 0)
           (cons 42 0)
           (cons 91 0)
           (list 10 19.36666667 -1.82333333)
           (cons 40 0)
           (cons 41 0)
           (cons 42 0)
           (cons 91 0)
           (list 10 19.36666667 -2.34333333)
           (cons 40 0)
           (cons 41 0)
           (cons 42 0)
           (cons 91 0)
           (list 10 18.9 -2.5)
           (cons 40 0)
           (cons 41 0)
           (cons 42 0)
           (cons 91 0)
           (list 10 16.5 -2.5)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 16.03333333 -3.84333333)
           (cons 40 0)
           (cons 41 0)
           (cons 42 0)
           (cons 91 0)
           (list 10 16.03333333 -3.32333333)
           (cons 40 0)
           (cons 41 0)
           (cons 42 0)
           (cons 91 0)
           (list 10 16.5 -3.16666667)
           (cons 40 0)
           (cons 41 0)
           (cons 42 0)
           (cons 91 0)
           (list 10 18.9 -3.16666667)
           (cons 40 0)
           (cons 41 0)
           (cons 42 0)
           (cons 91 0)
           (list 10 19.36666667 -3.32333333)
           (cons 40 0)
           (cons 41 0)
           (cons 42 0)
           (cons 91 0)
           (list 10 19.36666667 -3.84333333)
           (cons 40 0)
           (cons 41 0)
           (cons 42 0)
           (cons 91 0)
           (list 10 18.9 -4)
           (cons 40 0)
           (cons 41 0)
           (cons 42 0)
           (cons 91 0)
           (list 10 16.5 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 16.03333333 1.82333333)
           (cons 40 0)
           (cons 41 0)
           (cons 42 0)
           (cons 91 0)
           (list 10 16.03333333 2.34333333)
           (cons 40 0)
           (cons 41 0)
           (cons 42 0)
           (cons 91 0)
           (list 10 16.5 2.5)
           (cons 40 0)
           (cons 41 0)
           (cons 42 0)
           (cons 91 0)
           (list 10 18.9 2.5)
           (cons 40 0)
           (cons 41 0)
           (cons 42 0)
           (cons 91 0)
           (list 10 19.36666667 2.34333333)
           (cons 40 0)
           (cons 41 0)
           (cons 42 0)
           (cons 91 0)
           (list 10 19.36666667 1.82333333)
           (cons 40 0)
           (cons 41 0)
           (cons 42 0)
           (cons 91 0)
           (list 10 18.9 1.66666667)
           (cons 40 0)
           (cons 41 0)
           (cons 42 0)
           (cons 91 0)
           (list 10 16.5 1.66666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 16.03333333 3.32333333)
           (cons 40 0)
           (cons 41 0)
           (cons 42 0)
           (cons 91 0)
           (list 10 16.03333333 3.84333333)
           (cons 40 0)
           (cons 41 0)
           (cons 42 0)
           (cons 91 0)
           (list 10 16.5 4)
           (cons 40 0)
           (cons 41 0)
           (cons 42 0)
           (cons 91 0)
           (list 10 18.9 4)
           (cons 40 0)
           (cons 41 0)
           (cons 42 0)
           (cons 91 0)
           (list 10 19.36666667 3.84333333)
           (cons 40 0)
           (cons 41 0)
           (cons 42 0)
           (cons 91 0)
           (list 10 19.36666667 3.32333333)
           (cons 40 0)
           (cons 41 0)
           (cons 42 0)
           (cons 91 0)
           (list 10 18.9 3.16666667)
           (cons 40 0)
           (cons 41 0)
           (cons 42 0)
           (cons 91 0)
           (list 10 16.5 3.16666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 20.23333333 -2.34333333)
           (cons 40 0)
           (cons 41 0)
           (cons 42 0)
           (cons 91 0)
           (list 10 20.23333333 -1.82333333)
           (cons 40 0)
           (cons 41 0)
           (cons 42 0)
           (cons 91 0)
           (list 10 20.7 -1.66666667)
           (cons 40 0)
           (cons 41 0)
           (cons 42 0)
           (cons 91 0)
           (list 10 23.1 -1.66666667)
           (cons 40 0)
           (cons 41 0)
           (cons 42 0)
           (cons 91 0)
           (list 10 23.56666667 -1.82333333)
           (cons 40 0)
           (cons 41 0)
           (cons 42 0)
           (cons 91 0)
           (list 10 23.56666667 -2.34333333)
           (cons 40 0)
           (cons 41 0)
           (cons 42 0)
           (cons 91 0)
           (list 10 23.1 -2.5)
           (cons 40 0)
           (cons 41 0)
           (cons 42 0)
           (cons 91 0)
           (list 10 20.7 -2.5)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 20.23333333 -3.84333333)
           (cons 40 0)
           (cons 41 0)
           (cons 42 0)
           (cons 91 0)
           (list 10 20.23333333 -3.32333333)
           (cons 40 0)
           (cons 41 0)
           (cons 42 0)
           (cons 91 0)
           (list 10 20.7 -3.16666667)
           (cons 40 0)
           (cons 41 0)
           (cons 42 0)
           (cons 91 0)
           (list 10 23.1 -3.16666667)
           (cons 40 0)
           (cons 41 0)
           (cons 42 0)
           (cons 91 0)
           (list 10 23.56666667 -3.32333333)
           (cons 40 0)
           (cons 41 0)
           (cons 42 0)
           (cons 91 0)
           (list 10 23.56666667 -3.84333333)
           (cons 40 0)
           (cons 41 0)
           (cons 42 0)
           (cons 91 0)
           (list 10 23.1 -4)
           (cons 40 0)
           (cons 41 0)
           (cons 42 0)
           (cons 91 0)
           (list 10 20.7 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 20.23333333 1.82333333)
           (cons 40 0)
           (cons 41 0)
           (cons 42 0)
           (cons 91 0)
           (list 10 20.23333333 2.34333333)
           (cons 40 0)
           (cons 41 0)
           (cons 42 0)
           (cons 91 0)
           (list 10 20.7 2.5)
           (cons 40 0)
           (cons 41 0)
           (cons 42 0)
           (cons 91 0)
           (list 10 23.1 2.5)
           (cons 40 0)
           (cons 41 0)
           (cons 42 0)
           (cons 91 0)
           (list 10 23.56666667 2.34333333)
           (cons 40 0)
           (cons 41 0)
           (cons 42 0)
           (cons 91 0)
           (list 10 23.56666667 1.82333333)
           (cons 40 0)
           (cons 41 0)
           (cons 42 0)
           (cons 91 0)
           (list 10 23.1 1.66666667)
           (cons 40 0)
           (cons 41 0)
           (cons 42 0)
           (cons 91 0)
           (list 10 20.7 1.66666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 20.23333333 3.32333333)
           (cons 40 0)
           (cons 41 0)
           (cons 42 0)
           (cons 91 0)
           (list 10 20.23333333 3.84333333)
           (cons 40 0)
           (cons 41 0)
           (cons 42 0)
           (cons 91 0)
           (list 10 20.7 4)
           (cons 40 0)
           (cons 41 0)
           (cons 42 0)
           (cons 91 0)
           (list 10 23.1 4)
           (cons 40 0)
           (cons 41 0)
           (cons 42 0)
           (cons 91 0)
           (list 10 23.56666667 3.84333333)
           (cons 40 0)
           (cons 41 0)
           (cons 42 0)
           (cons 91 0)
           (list 10 23.56666667 3.32333333)
           (cons 40 0)
           (cons 41 0)
           (cons 42 0)
           (cons 91 0)
           (list 10 23.1 3.16666667)
           (cons 40 0)
           (cons 41 0)
           (cons 42 0)
           (cons 91 0)
           (list 10 20.7 3.16666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4 0)
           (cons 50 0)
          )
         )
         (entmake
          (list
           (cons 0 "POINT")
           (cons 100 "AcDbEntity")
           (cons 67 0)
           (cons 8 "0")
           (cons 100 "AcDbPoint")
           (list 10 2.3 -4 0)
           (cons 50 0)
          )
         )
         (entmake
          (list
           (cons 0 "POINT")
           (cons 100 "AcDbEntity")
           (cons 67 0)
           (cons 8 "0")
           (cons 100 "AcDbPoint")
           (list 10 0 4 0)
           (cons 50 0)
          )
         )
         (entmake
          (list
           (cons 0 "POINT")
           (cons 100 "AcDbEntity")
           (cons 67 0)
           (cons 8 "0")
           (cons 100 "AcDbPoint")
           (list 10 2.3 4 0)
           (cons 50 0)
          )
         )
         (entmake
          (list
           (cons 0 "POINT")
           (cons 100 "AcDbEntity")
           (cons 67 0)
           (cons 8 "0")
           (cons 100 "AcDbPoint")
           (list 10 19.3 0 0)
           (cons 50 0)
          )
         )
         (entmake
          (list
           (cons 0 "POINT")
           (cons 100 "AcDbEntity")
           (cons 67 0)
           (cons 8 "0")
           (cons 100 "AcDbPoint")
           (list 10 19.8 4 0)
           (cons 50 0)
          )
         )
         (entmake
          (list
           (cons 0 "POINT")
           (cons 100 "AcDbEntity")
           (cons 67 0)
           (cons 8 "0")
           (cons 100 "AcDbPoint")
           (list 10 19.8 -4 0)
           (cons 50 0)
          )
         )
         (entmake
          (list
           (cons 0 "POINT")
           (cons 100 "AcDbEntity")
           (cons 67 0)
           (cons 8 "0")
           (cons 100 "AcDbPoint")
           (list 10 2.3 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4)
           (cons 40 0)
           (cons 41 0)
           (cons 42 0)
           (cons 91 0)
           (list 10 21.9 -4)
           (cons 40 0)
           (cons 41 0)
           (cons 42 0)
           (cons 91 0)
           (list 10 21.9 4)
           (cons 40 0)
           (cons 41 0)
           (cons 42 0)
           (cons 91 0)
           (list 10 0 4)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelLeft2")
           (list 10 2.3 -3.16666667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRight2")
           (list 10 2.3 3.16666667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 0.0328084 1.85914261 0)
           (cons 40 0.65616798)
           (cons 1 "2.300")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.0328084 0.76552931 0)
           (cons 40 0.65616798)
           (cons 1 "2.300")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.0328084 -0.32808399 0)
           (cons 40 0.65616798)
           (cons 1 "19.800")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.0328084 -1.42169729 0)
           (cons 40 0.65616798)
           (cons 1 "19.300")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.0328084 -2.51531059 0)
           (cons 40 0.65616798)
           (cons 1 "13.0")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-67D-TRAILER2"))
        (progn
         (entmake)
         (entmake
          (list
           (cons 0 "BLOCK")
           (cons 2 "AASHTO-2011-WB-67D-TRAILER2")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 28.5 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 28.5 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 2.5 0 0)
           (cons 40 0.56666667)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 -2.59333333)
           (cons 40 0)
           (cons 41 0)
           (cons 42 0)
           (cons 91 0)
           (list 10 23.83333333 -2.07333333)
           (cons 40 0)
           (cons 41 0)
           (cons 42 0)
           (cons 91 0)
           (list 10 24.3 -1.91666667)
           (cons 40 0)
           (cons 41 0)
           (cons 42 0)
           (cons 91 0)
           (list 10 26.7 -1.91666667)
           (cons 40 0)
           (cons 41 0)
           (cons 42 0)
           (cons 91 0)
           (list 10 27.16666667 -2.07333333)
           (cons 40 0)
           (cons 41 0)
           (cons 42 0)
           (cons 91 0)
           (list 10 27.16666667 -2.59333333)
           (cons 40 0)
           (cons 41 0)
           (cons 42 0)
           (cons 91 0)
           (list 10 26.7 -2.75)
           (cons 40 0)
           (cons 41 0)
           (cons 42 0)
           (cons 91 0)
           (list 10 24.3 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 -4.09333333)
           (cons 40 0)
           (cons 41 0)
           (cons 42 0)
           (cons 91 0)
           (list 10 23.83333333 -3.57333333)
           (cons 40 0)
           (cons 41 0)
           (cons 42 0)
           (cons 91 0)
           (list 10 24.3 -3.41666667)
           (cons 40 0)
           (cons 41 0)
           (cons 42 0)
           (cons 91 0)
           (list 10 26.7 -3.41666667)
           (cons 40 0)
           (cons 41 0)
           (cons 42 0)
           (cons 91 0)
           (list 10 27.16666667 -3.57333333)
           (cons 40 0)
           (cons 41 0)
           (cons 42 0)
           (cons 91 0)
           (list 10 27.16666667 -4.09333333)
           (cons 40 0)
           (cons 41 0)
           (cons 42 0)
           (cons 91 0)
           (list 10 26.7 -4.25)
           (cons 40 0)
           (cons 41 0)
           (cons 42 0)
           (cons 91 0)
           (list 10 24.3 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 2.07333333)
           (cons 40 0)
           (cons 41 0)
           (cons 42 0)
           (cons 91 0)
           (list 10 23.83333333 2.59333333)
           (cons 40 0)
           (cons 41 0)
           (cons 42 0)
           (cons 91 0)
           (list 10 24.3 2.75)
           (cons 40 0)
           (cons 41 0)
           (cons 42 0)
           (cons 91 0)
           (list 10 26.7 2.75)
           (cons 40 0)
           (cons 41 0)
           (cons 42 0)
           (cons 91 0)
           (list 10 27.16666667 2.59333333)
           (cons 40 0)
           (cons 41 0)
           (cons 42 0)
           (cons 91 0)
           (list 10 27.16666667 2.07333333)
           (cons 40 0)
           (cons 41 0)
           (cons 42 0)
           (cons 91 0)
           (list 10 26.7 1.91666667)
           (cons 40 0)
           (cons 41 0)
           (cons 42 0)
           (cons 91 0)
           (list 10 24.3 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 3.57333333)
           (cons 40 0)
           (cons 41 0)
           (cons 42 0)
           (cons 91 0)
           (list 10 23.83333333 4.09333333)
           (cons 40 0)
           (cons 41 0)
           (cons 42 0)
           (cons 91 0)
           (list 10 24.3 4.25)
           (cons 40 0)
           (cons 41 0)
           (cons 42 0)
           (cons 91 0)
           (list 10 26.7 4.25)
           (cons 40 0)
           (cons 41 0)
           (cons 42 0)
           (cons 91 0)
           (list 10 27.16666667 4.09333333)
           (cons 40 0)
           (cons 41 0)
           (cons 42 0)
           (cons 91 0)
           (list 10 27.16666667 3.57333333)
           (cons 40 0)
           (cons 41 0)
           (cons 42 0)
           (cons 91 0)
           (list 10 26.7 3.41666667)
           (cons 40 0)
           (cons 41 0)
           (cons 42 0)
           (cons 91 0)
           (list 10 24.3 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 2.5 0 0)
           (cons 50 0)
          )
         )
         (entmake
          (list
           (cons 0 "POINT")
           (cons 100 "AcDbEntity")
           (cons 67 0)
           (cons 8 "0")
           (cons 100 "AcDbPoint")
           (list 10 0 -4.25 0)
           (cons 50 0)
          )
         )
         (entmake
          (list
           (cons 0 "POINT")
           (cons 100 "AcDbEntity")
           (cons 67 0)
           (cons 8 "0")
           (cons 100 "AcDbPoint")
           (list 10 0 4.25 0)
           (cons 50 0)
          )
         )
         (entmake
          (list
           (cons 0 "POINT")
           (cons 100 "AcDbEntity")
           (cons 67 0)
           (cons 8 "0")
           (cons 100 "AcDbPoint")
           (list 10 25.5 4.25 0)
           (cons 50 0)
          )
         )
         (entmake
          (list
           (cons 0 "POINT")
           (cons 100 "AcDbEntity")
           (cons 67 0)
           (cons 8 "0")
           (cons 100 "AcDbPoint")
           (list 10 28.5 4.25 0)
           (cons 50 0)
          )
         )
         (entmake
          (list
           (cons 0 "POINT")
           (cons 100 "AcDbEntity")
           (cons 67 0)
           (cons 8 "0")
           (cons 100 "AcDbPoint")
           (list 10 28.5 -4.25 0)
           (cons 50 0)
          )
         )
         (entmake
          (list
           (cons 0 "POINT")
           (cons 100 "AcDbEntity")
           (cons 67 0)
           (cons 8 "0")
           (cons 100 "AcDbPoint")
           (list 10 25.5 -4.25 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4.25)
           (cons 40 0)
           (cons 41 0)
           (cons 42 0)
           (cons 91 0)
           (list 10 28.5 -4.25)
           (cons 40 0)
           (cons 41 0)
           (cons 42 0)
           (cons 91 0)
           (list 10 28.5 4.25)
           (cons 40 0)
           (cons 41 0)
           (cons 42 0)
           (cons 91 0)
           (list 10 0 4.25)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.20341207 1.85914261 0)
           (cons 40 0.65616798)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 0.76552931 0)
           (cons 40 0.65616798)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -0.32808399 0)
           (cons 40 0.65616798)
           (cons 1 "25.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-67D-PUP"))
        (progn
         (entmake)
         (entmake
          (list
           (cons 0 "BLOCK")
           (cons 2 "AASHTO-2011-WB-67D-PUP")
           (cons 70 2)
           (cons 4 "")
           (list 10 0 0 0)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 7 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.56666667)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.33333333 -2.59333333)
           (cons 40 0)
           (cons 41 0)
           (cons 42 0)
           (cons 91 0)
           (list 10 5.33333333 -2.07333333)
           (cons 40 0)
           (cons 41 0)
           (cons 42 0)
           (cons 91 0)
           (list 10 5.8 -1.91666667)
           (cons 40 0)
           (cons 41 0)
           (cons 42 0)
           (cons 91 0)
           (list 10 8.2 -1.91666667)
           (cons 40 0)
           (cons 41 0)
           (cons 42 0)
           (cons 91 0)
           (list 10 8.66666667 -2.07333333)
           (cons 40 0)
           (cons 41 0)
           (cons 42 0)
           (cons 91 0)
           (list 10 8.66666667 -2.59333333)
           (cons 40 0)
           (cons 41 0)
           (cons 42 0)
           (cons 91 0)
           (list 10 8.2 -2.75)
           (cons 40 0)
           (cons 41 0)
           (cons 42 0)
           (cons 91 0)
           (list 10 5.8 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.33333333 -4.09333333)
           (cons 40 0)
           (cons 41 0)
           (cons 42 0)
           (cons 91 0)
           (list 10 5.33333333 -3.57333333)
           (cons 40 0)
           (cons 41 0)
           (cons 42 0)
           (cons 91 0)
           (list 10 5.8 -3.41666667)
           (cons 40 0)
           (cons 41 0)
           (cons 42 0)
           (cons 91 0)
           (list 10 8.2 -3.41666667)
           (cons 40 0)
           (cons 41 0)
           (cons 42 0)
           (cons 91 0)
           (list 10 8.66666667 -3.57333333)
           (cons 40 0)
           (cons 41 0)
           (cons 42 0)
           (cons 91 0)
           (list 10 8.66666667 -4.09333333)
           (cons 40 0)
           (cons 41 0)
           (cons 42 0)
           (cons 91 0)
           (list 10 8.2 -4.25)
           (cons 40 0)
           (cons 41 0)
           (cons 42 0)
           (cons 91 0)
           (list 10 5.8 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.33333333 2.07333333)
           (cons 40 0)
           (cons 41 0)
           (cons 42 0)
           (cons 91 0)
           (list 10 5.33333333 2.59333333)
           (cons 40 0)
           (cons 41 0)
           (cons 42 0)
           (cons 91 0)
           (list 10 5.8 2.75)
           (cons 40 0)
           (cons 41 0)
           (cons 42 0)
           (cons 91 0)
           (list 10 8.2 2.75)
           (cons 40 0)
           (cons 41 0)
           (cons 42 0)
           (cons 91 0)
           (list 10 8.66666667 2.59333333)
           (cons 40 0)
           (cons 41 0)
           (cons 42 0)
           (cons 91 0)
           (list 10 8.66666667 2.07333333)
           (cons 40 0)
           (cons 41 0)
           (cons 42 0)
           (cons 91 0)
           (list 10 8.2 1.91666667)
           (cons 40 0)
           (cons 41 0)
           (cons 42 0)
           (cons 91 0)
           (list 10 5.8 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.33333333 3.57333333)
           (cons 40 0)
           (cons 41 0)
           (cons 42 0)
           (cons 91 0)
           (list 10 5.33333333 4.09333333)
           (cons 40 0)
           (cons 41 0)
           (cons 42 0)
           (cons 91 0)
           (list 10 5.8 4.25)
           (cons 40 0)
           (cons 41 0)
           (cons 42 0)
           (cons 91 0)
           (list 10 8.2 4.25)
           (cons 40 0)
           (cons 41 0)
           (cons 42 0)
           (cons 91 0)
           (list 10 8.66666667 4.09333333)
           (cons 40 0)
           (cons 41 0)
           (cons 42 0)
           (cons 91 0)
           (list 10 8.66666667 3.57333333)
           (cons 40 0)
           (cons 41 0)
           (cons 42 0)
           (cons 91 0)
           (list 10 8.2 3.41666667)
           (cons 40 0)
           (cons 41 0)
           (cons 42 0)
           (cons 91 0)
           (list 10 5.8 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 7 0 0)
           (cons 50 0)
          )
         )
         (entmake
          (list
           (cons 0 "POINT")
           (cons 100 "AcDbEntity")
           (cons 67 0)
           (cons 8 "0")
           (cons 100 "AcDbPoint")
           (list 10 7 -4.25 0)
           (cons 50 0)
          )
         )
         (entmake
          (list
           (cons 0 "POINT")
           (cons 100 "AcDbEntity")
           (cons 67 0)
           (cons 8 "0")
           (cons 100 "AcDbPoint")
           (list 10 7 4.25 0)
           (cons 50 0)
          )
         )
         (entmake
          (list
           (cons 0 "LWPOLYLINE")
           (cons 100 "AcDbEntity")
           (cons 67 0)
           (cons 8 "Defpoints")
           (cons 100 "AcDbPolyline")
           (cons 90 3)
           (cons 70 1)
           (cons 43 0)
           (cons 38 0)
           (cons 39 0)
           (list 10 0 0)
           (cons 40 0)
           (cons 41 0)
           (cons 42 0)
           (cons 91 0)
           (list 10 7 4.25)
           (cons 40 0)
           (cons 41 0)
           (cons 42 0)
           (cons 91 0)
           (list 10 7 -4.25)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 -2.29658793 1.85914261 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 0.76552931 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -0.32808399 0)
           (cons 40 0.65616798)
           (cons 1 "7.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -1.42169729 0)
           (cons 40 0.65616798)
           (cons 1 "7.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-67D-TRAILER1"))
        (progn
         (entmake)
         (entmake
          (list
           (cons 0 "BLOCK")
           (cons 2 "AASHTO-2011-WB-67D-TRAILER1")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 28.5 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 28.5 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 2.5 0 0)
           (cons 40 0.34)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 -2.59333333)
           (cons 40 0)
           (cons 41 0)
           (cons 42 0)
           (cons 91 0)
           (list 10 23.83333333 -2.07333333)
           (cons 40 0)
           (cons 41 0)
           (cons 42 0)
           (cons 91 0)
           (list 10 24.3 -1.91666667)
           (cons 40 0)
           (cons 41 0)
           (cons 42 0)
           (cons 91 0)
           (list 10 26.7 -1.91666667)
           (cons 40 0)
           (cons 41 0)
           (cons 42 0)
           (cons 91 0)
           (list 10 27.16666667 -2.07333333)
           (cons 40 0)
           (cons 41 0)
           (cons 42 0)
           (cons 91 0)
           (list 10 27.16666667 -2.59333333)
           (cons 40 0)
           (cons 41 0)
           (cons 42 0)
           (cons 91 0)
           (list 10 26.7 -2.75)
           (cons 40 0)
           (cons 41 0)
           (cons 42 0)
           (cons 91 0)
           (list 10 24.3 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 -4.09333333)
           (cons 40 0)
           (cons 41 0)
           (cons 42 0)
           (cons 91 0)
           (list 10 23.83333333 -3.57333333)
           (cons 40 0)
           (cons 41 0)
           (cons 42 0)
           (cons 91 0)
           (list 10 24.3 -3.41666667)
           (cons 40 0)
           (cons 41 0)
           (cons 42 0)
           (cons 91 0)
           (list 10 26.7 -3.41666667)
           (cons 40 0)
           (cons 41 0)
           (cons 42 0)
           (cons 91 0)
           (list 10 27.16666667 -3.57333333)
           (cons 40 0)
           (cons 41 0)
           (cons 42 0)
           (cons 91 0)
           (list 10 27.16666667 -4.09333333)
           (cons 40 0)
           (cons 41 0)
           (cons 42 0)
           (cons 91 0)
           (list 10 26.7 -4.25)
           (cons 40 0)
           (cons 41 0)
           (cons 42 0)
           (cons 91 0)
           (list 10 24.3 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 2.07333333)
           (cons 40 0)
           (cons 41 0)
           (cons 42 0)
           (cons 91 0)
           (list 10 23.83333333 2.59333333)
           (cons 40 0)
           (cons 41 0)
           (cons 42 0)
           (cons 91 0)
           (list 10 24.3 2.75)
           (cons 40 0)
           (cons 41 0)
           (cons 42 0)
           (cons 91 0)
           (list 10 26.7 2.75)
           (cons 40 0)
           (cons 41 0)
           (cons 42 0)
           (cons 91 0)
           (list 10 27.16666667 2.59333333)
           (cons 40 0)
           (cons 41 0)
           (cons 42 0)
           (cons 91 0)
           (list 10 27.16666667 2.07333333)
           (cons 40 0)
           (cons 41 0)
           (cons 42 0)
           (cons 91 0)
           (list 10 26.7 1.91666667)
           (cons 40 0)
           (cons 41 0)
           (cons 42 0)
           (cons 91 0)
           (list 10 24.3 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 3.57333333)
           (cons 40 0)
           (cons 41 0)
           (cons 42 0)
           (cons 91 0)
           (list 10 23.83333333 4.09333333)
           (cons 40 0)
           (cons 41 0)
           (cons 42 0)
           (cons 91 0)
           (list 10 24.3 4.25)
           (cons 40 0)
           (cons 41 0)
           (cons 42 0)
           (cons 91 0)
           (list 10 26.7 4.25)
           (cons 40 0)
           (cons 41 0)
           (cons 42 0)
           (cons 91 0)
           (list 10 27.16666667 4.09333333)
           (cons 40 0)
           (cons 41 0)
           (cons 42 0)
           (cons 91 0)
           (list 10 27.16666667 3.57333333)
           (cons 40 0)
           (cons 41 0)
           (cons 42 0)
           (cons 91 0)
           (list 10 26.7 3.41666667)
           (cons 40 0)
           (cons 41 0)
           (cons 42 0)
           (cons 91 0)
           (list 10 24.3 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 2.5 0 0)
           (cons 50 0)
          )
         )
         (entmake
          (list
           (cons 0 "POINT")
           (cons 100 "AcDbEntity")
           (cons 67 0)
           (cons 8 "0")
           (cons 100 "AcDbPoint")
           (list 10 0 -4.25 0)
           (cons 50 0)
          )
         )
         (entmake
          (list
           (cons 0 "POINT")
           (cons 100 "AcDbEntity")
           (cons 67 0)
           (cons 8 "0")
           (cons 100 "AcDbPoint")
           (list 10 0 4.25 0)
           (cons 50 0)
          )
         )
         (entmake
          (list
           (cons 0 "POINT")
           (cons 100 "AcDbEntity")
           (cons 67 0)
           (cons 8 "0")
           (cons 100 "AcDbPoint")
           (list 10 25.5 4.25 0)
           (cons 50 0)
          )
         )
         (entmake
          (list
           (cons 0 "POINT")
           (cons 100 "AcDbEntity")
           (cons 67 0)
           (cons 8 "0")
           (cons 100 "AcDbPoint")
           (list 10 28.5 4.25 0)
           (cons 50 0)
          )
         )
         (entmake
          (list
           (cons 0 "POINT")
           (cons 100 "AcDbEntity")
           (cons 67 0)
           (cons 8 "0")
           (cons 100 "AcDbPoint")
           (list 10 25.5 -4.25 0)
           (cons 50 0)
          )
         )
         (entmake
          (list
           (cons 0 "POINT")
           (cons 100 "AcDbEntity")
           (cons 67 0)
           (cons 8 "0")
           (cons 100 "AcDbPoint")
           (list 10 28.5 -4.25 0)
           (cons 50 0)
          )
         )
         (entmake
          (list
           (cons 0 "POINT")
           (cons 100 "AcDbEntity")
           (cons 67 0)
           (cons 8 "0")
           (cons 100 "AcDbPoint")
           (list 10 28.5 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4.25)
           (cons 40 0)
           (cons 41 0)
           (cons 42 0)
           (cons 91 0)
           (list 10 28.5 -4.25)
           (cons 40 0)
           (cons 41 0)
           (cons 42 0)
           (cons 91 0)
           (list 10 28.5 4.25)
           (cons 40 0)
           (cons 41 0)
           (cons 42 0)
           (cons 91 0)
           (list 10 0 4.25)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.20341207 1.85914261 0)
           (cons 40 0.65616798)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 0.76552931 0)
           (cons 40 0.65616798)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -0.32808399 0)
           (cons 40 0.65616798)
           (cons 1 "25.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -1.42169729 0)
           (cons 40 0.65616798)
           (cons 1 "28.500")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-67D-TRUCK"))
        (progn
         (entmake)
         (entmake
          (list
           (cons 0 "BLOCK")
           (cons 2 "AASHTO-2011-WB-67D-TRUCK")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.5 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.5 -1.66666667 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 13.3 -1.66666667 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 13.3 1.66666667 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.5 1.66666667 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.5 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 13.3 0 0)
           (cons 40 1.14285714)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 14.10812204 -0.80812204 0)
           (list 11 14.10812204 0.80812204 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.63333333 -2.34333333)
           (cons 40 0)
           (cons 41 0)
           (cons 42 0)
           (cons 91 0)
           (list 10 11.63333333 -1.82333333)
           (cons 40 0)
           (cons 41 0)
           (cons 42 0)
           (cons 91 0)
           (list 10 12.1 -1.66666667)
           (cons 40 0)
           (cons 41 0)
           (cons 42 0)
           (cons 91 0)
           (list 10 14.5 -1.66666667)
           (cons 40 0)
           (cons 41 0)
           (cons 42 0)
           (cons 91 0)
           (list 10 14.96666667 -1.82333333)
           (cons 40 0)
           (cons 41 0)
           (cons 42 0)
           (cons 91 0)
           (list 10 14.96666667 -2.34333333)
           (cons 40 0)
           (cons 41 0)
           (cons 42 0)
           (cons 91 0)
           (list 10 14.5 -2.5)
           (cons 40 0)
           (cons 41 0)
           (cons 42 0)
           (cons 91 0)
           (list 10 12.1 -2.5)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.63333333 -3.84333333)
           (cons 40 0)
           (cons 41 0)
           (cons 42 0)
           (cons 91 0)
           (list 10 11.63333333 -3.32333333)
           (cons 40 0)
           (cons 41 0)
           (cons 42 0)
           (cons 91 0)
           (list 10 12.1 -3.16666667)
           (cons 40 0)
           (cons 41 0)
           (cons 42 0)
           (cons 91 0)
           (list 10 14.5 -3.16666667)
           (cons 40 0)
           (cons 41 0)
           (cons 42 0)
           (cons 91 0)
           (list 10 14.96666667 -3.32333333)
           (cons 40 0)
           (cons 41 0)
           (cons 42 0)
           (cons 91 0)
           (list 10 14.96666667 -3.84333333)
           (cons 40 0)
           (cons 41 0)
           (cons 42 0)
           (cons 91 0)
           (list 10 14.5 -4)
           (cons 40 0)
           (cons 41 0)
           (cons 42 0)
           (cons 91 0)
           (list 10 12.1 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.63333333 1.82333333)
           (cons 40 0)
           (cons 41 0)
           (cons 42 0)
           (cons 91 0)
           (list 10 11.63333333 2.34333333)
           (cons 40 0)
           (cons 41 0)
           (cons 42 0)
           (cons 91 0)
           (list 10 12.1 2.5)
           (cons 40 0)
           (cons 41 0)
           (cons 42 0)
           (cons 91 0)
           (list 10 14.5 2.5)
           (cons 40 0)
           (cons 41 0)
           (cons 42 0)
           (cons 91 0)
           (list 10 14.96666667 2.34333333)
           (cons 40 0)
           (cons 41 0)
           (cons 42 0)
           (cons 91 0)
           (list 10 14.96666667 1.82333333)
           (cons 40 0)
           (cons 41 0)
           (cons 42 0)
           (cons 91 0)
           (list 10 14.5 1.66666667)
           (cons 40 0)
           (cons 41 0)
           (cons 42 0)
           (cons 91 0)
           (list 10 12.1 1.66666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.63333333 3.32333333)
           (cons 40 0)
           (cons 41 0)
           (cons 42 0)
           (cons 91 0)
           (list 10 11.63333333 3.84333333)
           (cons 40 0)
           (cons 41 0)
           (cons 42 0)
           (cons 91 0)
           (list 10 12.1 4)
           (cons 40 0)
           (cons 41 0)
           (cons 42 0)
           (cons 91 0)
           (list 10 14.5 4)
           (cons 40 0)
           (cons 41 0)
           (cons 42 0)
           (cons 91 0)
           (list 10 14.96666667 3.84333333)
           (cons 40 0)
           (cons 41 0)
           (cons 42 0)
           (cons 91 0)
           (list 10 14.96666667 3.32333333)
           (cons 40 0)
           (cons 41 0)
           (cons 42 0)
           (cons 91 0)
           (list 10 14.5 3.16666667)
           (cons 40 0)
           (cons 41 0)
           (cons 42 0)
           (cons 91 0)
           (list 10 12.1 3.16666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 2.3 0 0)
           (cons 50 0)
          )
         )
         (entmake
          (list
           (cons 0 "POINT")
           (cons 100 "AcDbEntity")
           (cons 67 0)
           (cons 8 "0")
           (cons 100 "AcDbPoint")
           (list 10 13.3 0 0)
           (cons 50 0)
          )
         )
         (entmake
          (list
           (cons 0 "POINT")
           (cons 100 "AcDbEntity")
           (cons 67 0)
           (cons 8 "0")
           (cons 100 "AcDbPoint")
           (list 10 2.3 -4 0)
           (cons 50 0)
          )
         )
         (entmake
          (list
           (cons 0 "POINT")
           (cons 100 "AcDbEntity")
           (cons 67 0)
           (cons 8 "0")
           (cons 100 "AcDbPoint")
           (list 10 13.3 -4 0)
           (cons 50 0)
          )
         )
         (entmake
          (list
           (cons 0 "POINT")
           (cons 100 "AcDbEntity")
           (cons 67 0)
           (cons 8 "0")
           (cons 100 "AcDbPoint")
           (list 10 13.3 4 0)
           (cons 50 0)
          )
         )
         (entmake
          (list
           (cons 0 "POINT")
           (cons 100 "AcDbEntity")
           (cons 67 0)
           (cons 8 "0")
           (cons 100 "AcDbPoint")
           (list 10 2.3 4 0)
           (cons 50 0)
          )
         )
         (entmake
          (list
           (cons 0 "POINT")
           (cons 100 "AcDbEntity")
           (cons 67 0)
           (cons 8 "0")
           (cons 100 "AcDbPoint")
           (list 10 0 4 0)
           (cons 50 0)
          )
         )
         (entmake
          (list
           (cons 0 "POINT")
           (cons 100 "AcDbEntity")
           (cons 67 0)
           (cons 8 "0")
           (cons 100 "AcDbPoint")
           (list 10 0 -4 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4)
           (cons 40 0)
           (cons 41 0)
           (cons 42 0)
           (cons 91 0)
           (list 10 13.3 -4)
           (cons 40 0)
           (cons 41 0)
           (cons 42 0)
           (cons 91 0)
           (list 10 13.3 4)
           (cons 40 0)
           (cons 41 0)
           (cons 42 0)
           (cons 91 0)
           (list 10 0 4)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelRight2")
           (list 10 2.3 3.16666667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeft2")
           (list 10 2.3 -3.16666667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 0.0328084 1.85914261 0)
           (cons 40 0.65616798)
           (cons 1 "2.300")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.0328084 0.76552931 0)
           (cons 40 0.65616798)
           (cons 1 "2.300")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.0328084 -0.32808399 0)
           (cons 40 0.65616798)
           (cons 1 "13.300")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.0328084 -1.42169729 0)
           (cons 40 0.65616798)
           (cons 1 "13.300")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.0328084 -2.51531059 0)
           (cons 40 0.65616798)
           (cons 1 "27.3")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-62-TRAILER"))
        (progn
         (entmake)
         (entmake
          (list
           (cons 0 "BLOCK")
           (cons 2 "AASHTO-2011-WB-62-TRAILER")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 48 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 48 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 2.5 0 0)
           (cons 40 0.34)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 39.84868766 -2.42766667)
           (cons 40 0)
           (cons 41 0)
           (cons 42 0)
           (cons 91 0)
           (list 10 39.84868766 -1.85566667)
           (cons 40 0)
           (cons 41 0)
           (cons 42 0)
           (cons 91 0)
           (list 10 40.31068766 -1.68333333)
           (cons 40 0)
           (cons 41 0)
           (cons 42 0)
           (cons 91 0)
           (list 10 42.68668766 -1.68333333)
           (cons 40 0)
           (cons 41 0)
           (cons 42 0)
           (cons 91 0)
           (list 10 43.14868766 -1.85566667)
           (cons 40 0)
           (cons 41 0)
           (cons 42 0)
           (cons 91 0)
           (list 10 43.14868766 -2.42766667)
           (cons 40 0)
           (cons 41 0)
           (cons 42 0)
           (cons 91 0)
           (list 10 42.68668766 -2.6)
           (cons 40 0)
           (cons 41 0)
           (cons 42 0)
           (cons 91 0)
           (list 10 40.31068766 -2.6)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 39.84868766 -4.07766667)
           (cons 40 0)
           (cons 41 0)
           (cons 42 0)
           (cons 91 0)
           (list 10 39.84868766 -3.50566667)
           (cons 40 0)
           (cons 41 0)
           (cons 42 0)
           (cons 91 0)
           (list 10 40.31068766 -3.33333333)
           (cons 40 0)
           (cons 41 0)
           (cons 42 0)
           (cons 91 0)
           (list 10 42.68668766 -3.33333333)
           (cons 40 0)
           (cons 41 0)
           (cons 42 0)
           (cons 91 0)
           (list 10 43.14868766 -3.50566667)
           (cons 40 0)
           (cons 41 0)
           (cons 42 0)
           (cons 91 0)
           (list 10 43.14868766 -4.07766667)
           (cons 40 0)
           (cons 41 0)
           (cons 42 0)
           (cons 91 0)
           (list 10 42.68668766 -4.25)
           (cons 40 0)
           (cons 41 0)
           (cons 42 0)
           (cons 91 0)
           (list 10 40.31068766 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 39.84868766 3.50566667)
           (cons 40 0)
           (cons 41 0)
           (cons 42 0)
           (cons 91 0)
           (list 10 39.84868766 4.07766667)
           (cons 40 0)
           (cons 41 0)
           (cons 42 0)
           (cons 91 0)
           (list 10 40.31068766 4.25)
           (cons 40 0)
           (cons 41 0)
           (cons 42 0)
           (cons 91 0)
           (list 10 42.68668766 4.25)
           (cons 40 0)
           (cons 41 0)
           (cons 42 0)
           (cons 91 0)
           (list 10 43.14868766 4.07766667)
           (cons 40 0)
           (cons 41 0)
           (cons 42 0)
           (cons 91 0)
           (list 10 43.14868766 3.50566667)
           (cons 40 0)
           (cons 41 0)
           (cons 42 0)
           (cons 91 0)
           (list 10 42.68668766 3.33333333)
           (cons 40 0)
           (cons 41 0)
           (cons 42 0)
           (cons 91 0)
           (list 10 40.31068766 3.33333333)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 43.85131234 -2.42766667)
           (cons 40 0)
           (cons 41 0)
           (cons 42 0)
           (cons 91 0)
           (list 10 43.85131234 -1.85566667)
           (cons 40 0)
           (cons 41 0)
           (cons 42 0)
           (cons 91 0)
           (list 10 44.31331234 -1.68333333)
           (cons 40 0)
           (cons 41 0)
           (cons 42 0)
           (cons 91 0)
           (list 10 46.68931234 -1.68333333)
           (cons 40 0)
           (cons 41 0)
           (cons 42 0)
           (cons 91 0)
           (list 10 47.15131234 -1.85566667)
           (cons 40 0)
           (cons 41 0)
           (cons 42 0)
           (cons 91 0)
           (list 10 47.15131234 -2.42766667)
           (cons 40 0)
           (cons 41 0)
           (cons 42 0)
           (cons 91 0)
           (list 10 46.68931234 -2.6)
           (cons 40 0)
           (cons 41 0)
           (cons 42 0)
           (cons 91 0)
           (list 10 44.31331234 -2.6)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 43.85131234 -4.07766667)
           (cons 40 0)
           (cons 41 0)
           (cons 42 0)
           (cons 91 0)
           (list 10 43.85131234 -3.50566667)
           (cons 40 0)
           (cons 41 0)
           (cons 42 0)
           (cons 91 0)
           (list 10 44.31331234 -3.33333333)
           (cons 40 0)
           (cons 41 0)
           (cons 42 0)
           (cons 91 0)
           (list 10 46.68931234 -3.33333333)
           (cons 40 0)
           (cons 41 0)
           (cons 42 0)
           (cons 91 0)
           (list 10 47.15131234 -3.50566667)
           (cons 40 0)
           (cons 41 0)
           (cons 42 0)
           (cons 91 0)
           (list 10 47.15131234 -4.07766667)
           (cons 40 0)
           (cons 41 0)
           (cons 42 0)
           (cons 91 0)
           (list 10 46.68931234 -4.25)
           (cons 40 0)
           (cons 41 0)
           (cons 42 0)
           (cons 91 0)
           (list 10 44.31331234 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 43.85131234 3.50566667)
           (cons 40 0)
           (cons 41 0)
           (cons 42 0)
           (cons 91 0)
           (list 10 43.85131234 4.07766667)
           (cons 40 0)
           (cons 41 0)
           (cons 42 0)
           (cons 91 0)
           (list 10 44.31331234 4.25)
           (cons 40 0)
           (cons 41 0)
           (cons 42 0)
           (cons 91 0)
           (list 10 46.68931234 4.25)
           (cons 40 0)
           (cons 41 0)
           (cons 42 0)
           (cons 91 0)
           (list 10 47.15131234 4.07766667)
           (cons 40 0)
           (cons 41 0)
           (cons 42 0)
           (cons 91 0)
           (list 10 47.15131234 3.50566667)
           (cons 40 0)
           (cons 41 0)
           (cons 42 0)
           (cons 91 0)
           (list 10 46.68931234 3.33333333)
           (cons 40 0)
           (cons 41 0)
           (cons 42 0)
           (cons 91 0)
           (list 10 44.31331234 3.33333333)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 2.5 0 0)
           (cons 50 0)
          )
         )
         (entmake
          (list
           (cons 0 "POINT")
           (cons 100 "AcDbEntity")
           (cons 67 0)
           (cons 8 "0")
           (cons 100 "AcDbPoint")
           (list 10 0 -4.25 0)
           (cons 50 0)
          )
         )
         (entmake
          (list
           (cons 0 "POINT")
           (cons 100 "AcDbEntity")
           (cons 67 0)
           (cons 8 "0")
           (cons 100 "AcDbPoint")
           (list 10 48 -4.25 0)
           (cons 50 0)
          )
         )
         (entmake
          (list
           (cons 0 "POINT")
           (cons 100 "AcDbEntity")
           (cons 67 0)
           (cons 8 "0")
           (cons 100 "AcDbPoint")
           (list 10 48 4.25 0)
           (cons 50 0)
          )
         )
         (entmake
          (list
           (cons 0 "POINT")
           (cons 100 "AcDbEntity")
           (cons 67 0)
           (cons 8 "0")
           (cons 100 "AcDbPoint")
           (list 10 0 4.25 0)
           (cons 50 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 39.84868766 2.42766667)
           (cons 40 0)
           (cons 41 0)
           (cons 42 0)
           (cons 91 0)
           (list 10 39.84868766 1.85566667)
           (cons 40 0)
           (cons 41 0)
           (cons 42 0)
           (cons 91 0)
           (list 10 40.31068766 1.68333333)
           (cons 40 0)
           (cons 41 0)
           (cons 42 0)
           (cons 91 0)
           (list 10 42.68668766 1.68333333)
           (cons 40 0)
           (cons 41 0)
           (cons 42 0)
           (cons 91 0)
           (list 10 43.14868766 1.85566667)
           (cons 40 0)
           (cons 41 0)
           (cons 42 0)
           (cons 91 0)
           (list 10 43.14868766 2.42766667)
           (cons 40 0)
           (cons 41 0)
           (cons 42 0)
           (cons 91 0)
           (list 10 42.68668766 2.6)
           (cons 40 0)
           (cons 41 0)
           (cons 42 0)
           (cons 91 0)
           (list 10 40.31068766 2.6)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 43.85131234 2.42766667)
           (cons 40 0)
           (cons 41 0)
           (cons 42 0)
           (cons 91 0)
           (list 10 43.85131234 1.85566667)
           (cons 40 0)
           (cons 41 0)
           (cons 42 0)
           (cons 91 0)
           (list 10 44.31331234 1.68333333)
           (cons 40 0)
           (cons 41 0)
           (cons 42 0)
           (cons 91 0)
           (list 10 46.68931234 1.68333333)
           (cons 40 0)
           (cons 41 0)
           (cons 42 0)
           (cons 91 0)
           (list 10 47.15131234 1.85566667)
           (cons 40 0)
           (cons 41 0)
           (cons 42 0)
           (cons 91 0)
           (list 10 47.15131234 2.42766667)
           (cons 40 0)
           (cons 41 0)
           (cons 42 0)
           (cons 91 0)
           (list 10 46.68931234 2.6)
           (cons 40 0)
           (cons 41 0)
           (cons 42 0)
           (cons 91 0)
           (list 10 44.31331234 2.6)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 43.5 -4.25 0)
           (cons 50 0)
          )
         )
         (entmake
          (list
           (cons 0 "POINT")
           (cons 100 "AcDbEntity")
           (cons 67 0)
           (cons 8 "0")
           (cons 100 "AcDbPoint")
           (list 10 43.5 4.25 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4.25)
           (cons 40 0)
           (cons 41 0)
           (cons 42 0)
           (cons 91 0)
           (list 10 48 -4.25)
           (cons 40 0)
           (cons 41 0)
           (cons 42 0)
           (cons 91 0)
           (list 10 48 4.25)
           (cons 40 0)
           (cons 41 0)
           (cons 42 0)
           (cons 91 0)
           (list 10 0 4.25)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.20341207 1.85914261 0)
           (cons 40 0.65616798)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 0.76552931 0)
           (cons 40 0.65616798)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -0.32808399 0)
           (cons 40 0.65616798)
           (cons 1 "43.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-62-TRUCK"))
        (progn
         (entmake)
         (entmake
          (list
           (cons 0 "BLOCK")
           (cons 2 "AASHTO-2011-WB-62-TRUCK")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15 -1.43333333 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 25.6 -1.43333333 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 25.6 1.43333333 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15 1.43333333 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 23.5 0 0)
           (cons 40 1.14285714)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 24.30812204 -0.80812204 0)
           (list 11 24.30812204 0.80812204 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 19.56666667 -2.17766667)
           (cons 40 0)
           (cons 41 0)
           (cons 42 0)
           (cons 91 0)
           (list 10 19.56666667 -1.60566667)
           (cons 40 0)
           (cons 41 0)
           (cons 42 0)
           (cons 91 0)
           (list 10 20.08 -1.43333333)
           (cons 40 0)
           (cons 41 0)
           (cons 42 0)
           (cons 91 0)
           (list 10 22.72 -1.43333333)
           (cons 40 0)
           (cons 41 0)
           (cons 42 0)
           (cons 91 0)
           (list 10 23.23333333 -1.60566667)
           (cons 40 0)
           (cons 41 0)
           (cons 42 0)
           (cons 91 0)
           (list 10 23.23333333 -2.17766667)
           (cons 40 0)
           (cons 41 0)
           (cons 42 0)
           (cons 91 0)
           (list 10 22.72 -2.35)
           (cons 40 0)
           (cons 41 0)
           (cons 42 0)
           (cons 91 0)
           (list 10 20.08 -2.35)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 19.56666667 -3.82766667)
           (cons 40 0)
           (cons 41 0)
           (cons 42 0)
           (cons 91 0)
           (list 10 19.56666667 -3.25566667)
           (cons 40 0)
           (cons 41 0)
           (cons 42 0)
           (cons 91 0)
           (list 10 20.08 -3.08333333)
           (cons 40 0)
           (cons 41 0)
           (cons 42 0)
           (cons 91 0)
           (list 10 22.72 -3.08333333)
           (cons 40 0)
           (cons 41 0)
           (cons 42 0)
           (cons 91 0)
           (list 10 23.23333333 -3.25566667)
           (cons 40 0)
           (cons 41 0)
           (cons 42 0)
           (cons 91 0)
           (list 10 23.23333333 -3.82766667)
           (cons 40 0)
           (cons 41 0)
           (cons 42 0)
           (cons 91 0)
           (list 10 22.72 -4)
           (cons 40 0)
           (cons 41 0)
           (cons 42 0)
           (cons 91 0)
           (list 10 20.08 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 19.56666667 1.60566667)
           (cons 40 0)
           (cons 41 0)
           (cons 42 0)
           (cons 91 0)
           (list 10 19.56666667 2.17766667)
           (cons 40 0)
           (cons 41 0)
           (cons 42 0)
           (cons 91 0)
           (list 10 20.08 2.35)
           (cons 40 0)
           (cons 41 0)
           (cons 42 0)
           (cons 91 0)
           (list 10 22.72 2.35)
           (cons 40 0)
           (cons 41 0)
           (cons 42 0)
           (cons 91 0)
           (list 10 23.23333333 2.17766667)
           (cons 40 0)
           (cons 41 0)
           (cons 42 0)
           (cons 91 0)
           (list 10 23.23333333 1.60566667)
           (cons 40 0)
           (cons 41 0)
           (cons 42 0)
           (cons 91 0)
           (list 10 22.72 1.43333333)
           (cons 40 0)
           (cons 41 0)
           (cons 42 0)
           (cons 91 0)
           (list 10 20.08 1.43333333)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 19.56666667 3.25566667)
           (cons 40 0)
           (cons 41 0)
           (cons 42 0)
           (cons 91 0)
           (list 10 19.56666667 3.82766667)
           (cons 40 0)
           (cons 41 0)
           (cons 42 0)
           (cons 91 0)
           (list 10 20.08 4)
           (cons 40 0)
           (cons 41 0)
           (cons 42 0)
           (cons 91 0)
           (list 10 22.72 4)
           (cons 40 0)
           (cons 41 0)
           (cons 42 0)
           (cons 91 0)
           (list 10 23.23333333 3.82766667)
           (cons 40 0)
           (cons 41 0)
           (cons 42 0)
           (cons 91 0)
           (list 10 23.23333333 3.25566667)
           (cons 40 0)
           (cons 41 0)
           (cons 42 0)
           (cons 91 0)
           (list 10 22.72 3.08333333)
           (cons 40 0)
           (cons 41 0)
           (cons 42 0)
           (cons 91 0)
           (list 10 20.08 3.08333333)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.76666667 -2.17766667)
           (cons 40 0)
           (cons 41 0)
           (cons 42 0)
           (cons 91 0)
           (list 10 23.76666667 -1.60566667)
           (cons 40 0)
           (cons 41 0)
           (cons 42 0)
           (cons 91 0)
           (list 10 24.28 -1.43333333)
           (cons 40 0)
           (cons 41 0)
           (cons 42 0)
           (cons 91 0)
           (list 10 26.92 -1.43333333)
           (cons 40 0)
           (cons 41 0)
           (cons 42 0)
           (cons 91 0)
           (list 10 27.43333333 -1.60566667)
           (cons 40 0)
           (cons 41 0)
           (cons 42 0)
           (cons 91 0)
           (list 10 27.43333333 -2.17766667)
           (cons 40 0)
           (cons 41 0)
           (cons 42 0)
           (cons 91 0)
           (list 10 26.92 -2.35)
           (cons 40 0)
           (cons 41 0)
           (cons 42 0)
           (cons 91 0)
           (list 10 24.28 -2.35)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.76666667 -3.82766667)
           (cons 40 0)
           (cons 41 0)
           (cons 42 0)
           (cons 91 0)
           (list 10 23.76666667 -3.25566667)
           (cons 40 0)
           (cons 41 0)
           (cons 42 0)
           (cons 91 0)
           (list 10 24.28 -3.08333333)
           (cons 40 0)
           (cons 41 0)
           (cons 42 0)
           (cons 91 0)
           (list 10 26.92 -3.08333333)
           (cons 40 0)
           (cons 41 0)
           (cons 42 0)
           (cons 91 0)
           (list 10 27.43333333 -3.25566667)
           (cons 40 0)
           (cons 41 0)
           (cons 42 0)
           (cons 91 0)
           (list 10 27.43333333 -3.82766667)
           (cons 40 0)
           (cons 41 0)
           (cons 42 0)
           (cons 91 0)
           (list 10 26.92 -4)
           (cons 40 0)
           (cons 41 0)
           (cons 42 0)
           (cons 91 0)
           (list 10 24.28 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.76666667 1.60566667)
           (cons 40 0)
           (cons 41 0)
           (cons 42 0)
           (cons 91 0)
           (list 10 23.76666667 2.17766667)
           (cons 40 0)
           (cons 41 0)
           (cons 42 0)
           (cons 91 0)
           (list 10 24.28 2.35)
           (cons 40 0)
           (cons 41 0)
           (cons 42 0)
           (cons 91 0)
           (list 10 26.92 2.35)
           (cons 40 0)
           (cons 41 0)
           (cons 42 0)
           (cons 91 0)
           (list 10 27.43333333 2.17766667)
           (cons 40 0)
           (cons 41 0)
           (cons 42 0)
           (cons 91 0)
           (list 10 27.43333333 1.60566667)
           (cons 40 0)
           (cons 41 0)
           (cons 42 0)
           (cons 91 0)
           (list 10 26.92 1.43333333)
           (cons 40 0)
           (cons 41 0)
           (cons 42 0)
           (cons 91 0)
           (list 10 24.28 1.43333333)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.76666667 3.25566667)
           (cons 40 0)
           (cons 41 0)
           (cons 42 0)
           (cons 91 0)
           (list 10 23.76666667 3.82766667)
           (cons 40 0)
           (cons 41 0)
           (cons 42 0)
           (cons 91 0)
           (list 10 24.28 4)
           (cons 40 0)
           (cons 41 0)
           (cons 42 0)
           (cons 91 0)
           (list 10 26.92 4)
           (cons 40 0)
           (cons 41 0)
           (cons 42 0)
           (cons 91 0)
           (list 10 27.43333333 3.82766667)
           (cons 40 0)
           (cons 41 0)
           (cons 42 0)
           (cons 91 0)
           (list 10 27.43333333 3.25566667)
           (cons 40 0)
           (cons 41 0)
           (cons 42 0)
           (cons 91 0)
           (list 10 26.92 3.08333333)
           (cons 40 0)
           (cons 41 0)
           (cons 42 0)
           (cons 91 0)
           (list 10 24.28 3.08333333)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4 0)
           (cons 50 0)
          )
         )
         (entmake
          (list
           (cons 0 "POINT")
           (cons 100 "AcDbEntity")
           (cons 67 0)
           (cons 8 "0")
           (cons 100 "AcDbPoint")
           (list 10 4 -4 0)
           (cons 50 0)
          )
         )
         (entmake
          (list
           (cons 0 "POINT")
           (cons 100 "AcDbEntity")
           (cons 67 0)
           (cons 8 "0")
           (cons 100 "AcDbPoint")
           (list 10 23.5 -4 0)
           (cons 50 0)
          )
         )
         (entmake
          (list
           (cons 0 "POINT")
           (cons 100 "AcDbEntity")
           (cons 67 0)
           (cons 8 "0")
           (cons 100 "AcDbPoint")
           (list 10 23.5 4 0)
           (cons 50 0)
          )
         )
         (entmake
          (list
           (cons 0 "POINT")
           (cons 100 "AcDbEntity")
           (cons 67 0)
           (cons 8 "0")
           (cons 100 "AcDbPoint")
           (list 10 4 0 0)
           (cons 50 0)
          )
         )
         (entmake
          (list
           (cons 0 "POINT")
           (cons 100 "AcDbEntity")
           (cons 67 0)
           (cons 8 "0")
           (cons 100 "AcDbPoint")
           (list 10 4 4 0)
           (cons 50 0)
          )
         )
         (entmake
          (list
           (cons 0 "POINT")
           (cons 100 "AcDbEntity")
           (cons 67 0)
           (cons 8 "0")
           (cons 100 "AcDbPoint")
           (list 10 0 4 0)
           (cons 50 0)
          )
         )
         (entmake
          (list
           (cons 0 "POINT")
           (cons 100 "AcDbEntity")
           (cons 67 0)
           (cons 8 "0")
           (cons 100 "AcDbPoint")
           (list 10 23.5 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4)
           (cons 40 0)
           (cons 41 0)
           (cons 42 0)
           (cons 91 0)
           (list 10 25.6 -4)
           (cons 40 0)
           (cons 41 0)
           (cons 42 0)
           (cons 91 0)
           (list 10 25.6 4)
           (cons 40 0)
           (cons 41 0)
           (cons 42 0)
           (cons 91 0)
           (list 10 0 4)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelLeft1")
           (list 10 4 -3.08333333 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRight1")
           (list 10 4 3.08333333 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 1.70341207 1.85914261 0)
           (cons 40 0.65616798)
           (cons 1 "4.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 0.76552931 0)
           (cons 40 0.65616798)
           (cons 1 "4.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -0.32808399 0)
           (cons 40 0.65616798)
           (cons 1 "23.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -1.42169729 0)
           (cons 40 0.65616798)
           (cons 1 "23.500")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -2.51531059 0)
           (cons 40 0.65616798)
           (cons 1 "28.4")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-40-TRAILER"))
        (progn
         (entmake)
         (entmake
          (list
           (cons 0 "BLOCK")
           (cons 2 "AASHTO-2011-WB-40-TRAILER")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 33 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 33 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 3 0 0)
           (cons 40 0.32)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 24.86509186 -2.17766667)
           (cons 40 0)
           (cons 41 0)
           (cons 42 0)
           (cons 91 0)
           (list 10 24.86509186 -1.60566667)
           (cons 40 0)
           (cons 41 0)
           (cons 42 0)
           (cons 91 0)
           (list 10 25.32709186 -1.43333333)
           (cons 40 0)
           (cons 41 0)
           (cons 42 0)
           (cons 91 0)
           (list 10 27.70309186 -1.43333333)
           (cons 40 0)
           (cons 41 0)
           (cons 42 0)
           (cons 91 0)
           (list 10 28.16509186 -1.60566667)
           (cons 40 0)
           (cons 41 0)
           (cons 42 0)
           (cons 91 0)
           (list 10 28.16509186 -2.17766667)
           (cons 40 0)
           (cons 41 0)
           (cons 42 0)
           (cons 91 0)
           (list 10 27.70309186 -2.35)
           (cons 40 0)
           (cons 41 0)
           (cons 42 0)
           (cons 91 0)
           (list 10 25.32709186 -2.35)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 24.86509186 -3.82766667)
           (cons 40 0)
           (cons 41 0)
           (cons 42 0)
           (cons 91 0)
           (list 10 24.86509186 -3.25566667)
           (cons 40 0)
           (cons 41 0)
           (cons 42 0)
           (cons 91 0)
           (list 10 25.32709186 -3.08333333)
           (cons 40 0)
           (cons 41 0)
           (cons 42 0)
           (cons 91 0)
           (list 10 27.70309186 -3.08333333)
           (cons 40 0)
           (cons 41 0)
           (cons 42 0)
           (cons 91 0)
           (list 10 28.16509186 -3.25566667)
           (cons 40 0)
           (cons 41 0)
           (cons 42 0)
           (cons 91 0)
           (list 10 28.16509186 -3.82766667)
           (cons 40 0)
           (cons 41 0)
           (cons 42 0)
           (cons 91 0)
           (list 10 27.70309186 -4)
           (cons 40 0)
           (cons 41 0)
           (cons 42 0)
           (cons 91 0)
           (list 10 25.32709186 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 24.86509186 1.60566667)
           (cons 40 0)
           (cons 41 0)
           (cons 42 0)
           (cons 91 0)
           (list 10 24.86509186 2.17766667)
           (cons 40 0)
           (cons 41 0)
           (cons 42 0)
           (cons 91 0)
           (list 10 25.32709186 2.35)
           (cons 40 0)
           (cons 41 0)
           (cons 42 0)
           (cons 91 0)
           (list 10 27.70309186 2.35)
           (cons 40 0)
           (cons 41 0)
           (cons 42 0)
           (cons 91 0)
           (list 10 28.16509186 2.17766667)
           (cons 40 0)
           (cons 41 0)
           (cons 42 0)
           (cons 91 0)
           (list 10 28.16509186 1.60566667)
           (cons 40 0)
           (cons 41 0)
           (cons 42 0)
           (cons 91 0)
           (list 10 27.70309186 1.43333333)
           (cons 40 0)
           (cons 41 0)
           (cons 42 0)
           (cons 91 0)
           (list 10 25.32709186 1.43333333)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 24.86509186 3.25566667)
           (cons 40 0)
           (cons 41 0)
           (cons 42 0)
           (cons 91 0)
           (list 10 24.86509186 3.82766667)
           (cons 40 0)
           (cons 41 0)
           (cons 42 0)
           (cons 91 0)
           (list 10 25.32709186 4)
           (cons 40 0)
           (cons 41 0)
           (cons 42 0)
           (cons 91 0)
           (list 10 27.70309186 4)
           (cons 40 0)
           (cons 41 0)
           (cons 42 0)
           (cons 91 0)
           (list 10 28.16509186 3.82766667)
           (cons 40 0)
           (cons 41 0)
           (cons 42 0)
           (cons 91 0)
           (list 10 28.16509186 3.25566667)
           (cons 40 0)
           (cons 41 0)
           (cons 42 0)
           (cons 91 0)
           (list 10 27.70309186 3.08333333)
           (cons 40 0)
           (cons 41 0)
           (cons 42 0)
           (cons 91 0)
           (list 10 25.32709186 3.08333333)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 28.83490814 -2.17766667)
           (cons 40 0)
           (cons 41 0)
           (cons 42 0)
           (cons 91 0)
           (list 10 28.83490814 -1.60566667)
           (cons 40 0)
           (cons 41 0)
           (cons 42 0)
           (cons 91 0)
           (list 10 29.29690814 -1.43333333)
           (cons 40 0)
           (cons 41 0)
           (cons 42 0)
           (cons 91 0)
           (list 10 31.67290814 -1.43333333)
           (cons 40 0)
           (cons 41 0)
           (cons 42 0)
           (cons 91 0)
           (list 10 32.13490814 -1.60566667)
           (cons 40 0)
           (cons 41 0)
           (cons 42 0)
           (cons 91 0)
           (list 10 32.13490814 -2.17766667)
           (cons 40 0)
           (cons 41 0)
           (cons 42 0)
           (cons 91 0)
           (list 10 31.67290814 -2.35)
           (cons 40 0)
           (cons 41 0)
           (cons 42 0)
           (cons 91 0)
           (list 10 29.29690814 -2.35)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 28.83490814 -3.82766667)
           (cons 40 0)
           (cons 41 0)
           (cons 42 0)
           (cons 91 0)
           (list 10 28.83490814 -3.25566667)
           (cons 40 0)
           (cons 41 0)
           (cons 42 0)
           (cons 91 0)
           (list 10 29.29690814 -3.08333333)
           (cons 40 0)
           (cons 41 0)
           (cons 42 0)
           (cons 91 0)
           (list 10 31.67290814 -3.08333333)
           (cons 40 0)
           (cons 41 0)
           (cons 42 0)
           (cons 91 0)
           (list 10 32.13490814 -3.25566667)
           (cons 40 0)
           (cons 41 0)
           (cons 42 0)
           (cons 91 0)
           (list 10 32.13490814 -3.82766667)
           (cons 40 0)
           (cons 41 0)
           (cons 42 0)
           (cons 91 0)
           (list 10 31.67290814 -4)
           (cons 40 0)
           (cons 41 0)
           (cons 42 0)
           (cons 91 0)
           (list 10 29.29690814 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 28.83490814 1.60566667)
           (cons 40 0)
           (cons 41 0)
           (cons 42 0)
           (cons 91 0)
           (list 10 28.83490814 2.17766667)
           (cons 40 0)
           (cons 41 0)
           (cons 42 0)
           (cons 91 0)
           (list 10 29.29690814 2.35)
           (cons 40 0)
           (cons 41 0)
           (cons 42 0)
           (cons 91 0)
           (list 10 31.67290814 2.35)
           (cons 40 0)
           (cons 41 0)
           (cons 42 0)
           (cons 91 0)
           (list 10 32.13490814 2.17766667)
           (cons 40 0)
           (cons 41 0)
           (cons 42 0)
           (cons 91 0)
           (list 10 32.13490814 1.60566667)
           (cons 40 0)
           (cons 41 0)
           (cons 42 0)
           (cons 91 0)
           (list 10 31.67290814 1.43333333)
           (cons 40 0)
           (cons 41 0)
           (cons 42 0)
           (cons 91 0)
           (list 10 29.29690814 1.43333333)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 28.83490814 3.25566667)
           (cons 40 0)
           (cons 41 0)
           (cons 42 0)
           (cons 91 0)
           (list 10 28.83490814 3.82766667)
           (cons 40 0)
           (cons 41 0)
           (cons 42 0)
           (cons 91 0)
           (list 10 29.29690814 4)
           (cons 40 0)
           (cons 41 0)
           (cons 42 0)
           (cons 91 0)
           (list 10 31.67290814 4)
           (cons 40 0)
           (cons 41 0)
           (cons 42 0)
           (cons 91 0)
           (list 10 32.13490814 3.82766667)
           (cons 40 0)
           (cons 41 0)
           (cons 42 0)
           (cons 91 0)
           (list 10 32.13490814 3.25566667)
           (cons 40 0)
           (cons 41 0)
           (cons 42 0)
           (cons 91 0)
           (list 10 31.67290814 3.08333333)
           (cons 40 0)
           (cons 41 0)
           (cons 42 0)
           (cons 91 0)
           (list 10 29.29690814 3.08333333)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4 0)
           (cons 50 0)
          )
         )
         (entmake
          (list
           (cons 0 "POINT")
           (cons 100 "AcDbEntity")
           (cons 67 0)
           (cons 8 "0")
           (cons 100 "AcDbPoint")
           (list 10 0 4 0)
           (cons 50 0)
          )
         )
         (entmake
          (list
           (cons 0 "POINT")
           (cons 100 "AcDbEntity")
           (cons 67 0)
           (cons 8 "0")
           (cons 100 "AcDbPoint")
           (list 10 3 0 0)
           (cons 50 0)
          )
         )
         (entmake
          (list
           (cons 0 "POINT")
           (cons 100 "AcDbEntity")
           (cons 67 0)
           (cons 8 "0")
           (cons 100 "AcDbPoint")
           (list 10 33 -4 0)
           (cons 50 0)
          )
         )
         (entmake
          (list
           (cons 0 "POINT")
           (cons 100 "AcDbEntity")
           (cons 67 0)
           (cons 8 "0")
           (cons 100 "AcDbPoint")
           (list 10 33 4 0)
           (cons 50 0)
          )
         )
         (entmake
          (list
           (cons 0 "POINT")
           (cons 100 "AcDbEntity")
           (cons 67 0)
           (cons 8 "0")
           (cons 100 "AcDbPoint")
           (list 10 28.5 -4 0)
           (cons 50 0)
          )
         )
         (entmake
          (list
           (cons 0 "POINT")
           (cons 100 "AcDbEntity")
           (cons 67 0)
           (cons 8 "0")
           (cons 100 "AcDbPoint")
           (list 10 28.5 4 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4)
           (cons 40 0)
           (cons 41 0)
           (cons 42 0)
           (cons 91 0)
           (list 10 33 -4)
           (cons 40 0)
           (cons 41 0)
           (cons 42 0)
           (cons 91 0)
           (list 10 33 4)
           (cons 40 0)
           (cons 41 0)
           (cons 42 0)
           (cons 91 0)
           (list 10 0 4)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.70341207 1.85914261 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 0.76552931 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -0.32808399 0)
           (cons 40 0.65616798)
           (cons 1 "28.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-40-TRUCK"))
        (progn
         (entmake)
         (entmake
          (list
           (cons 0 "BLOCK")
           (cons 2 "AASHTO-2011-WB-40-TRUCK")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.5 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.5 -1.43333333 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15.5 -1.43333333 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15.5 1.43333333 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.5 1.43333333 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.5 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 15.5 0 0)
           (cons 40 1.14285714)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 16.30812204 -0.80812204 0)
           (list 11 16.30812204 0.80812204 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.66666667 -2.17766667)
           (cons 40 0)
           (cons 41 0)
           (cons 42 0)
           (cons 91 0)
           (list 10 13.66666667 -1.60566667)
           (cons 40 0)
           (cons 41 0)
           (cons 42 0)
           (cons 91 0)
           (list 10 14.18 -1.43333333)
           (cons 40 0)
           (cons 41 0)
           (cons 42 0)
           (cons 91 0)
           (list 10 16.82 -1.43333333)
           (cons 40 0)
           (cons 41 0)
           (cons 42 0)
           (cons 91 0)
           (list 10 17.33333333 -1.60566667)
           (cons 40 0)
           (cons 41 0)
           (cons 42 0)
           (cons 91 0)
           (list 10 17.33333333 -2.17766667)
           (cons 40 0)
           (cons 41 0)
           (cons 42 0)
           (cons 91 0)
           (list 10 16.82 -2.35)
           (cons 40 0)
           (cons 41 0)
           (cons 42 0)
           (cons 91 0)
           (list 10 14.18 -2.35)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.66666667 -3.82766667)
           (cons 40 0)
           (cons 41 0)
           (cons 42 0)
           (cons 91 0)
           (list 10 13.66666667 -3.25566667)
           (cons 40 0)
           (cons 41 0)
           (cons 42 0)
           (cons 91 0)
           (list 10 14.18 -3.08333333)
           (cons 40 0)
           (cons 41 0)
           (cons 42 0)
           (cons 91 0)
           (list 10 16.82 -3.08333333)
           (cons 40 0)
           (cons 41 0)
           (cons 42 0)
           (cons 91 0)
           (list 10 17.33333333 -3.25566667)
           (cons 40 0)
           (cons 41 0)
           (cons 42 0)
           (cons 91 0)
           (list 10 17.33333333 -3.82766667)
           (cons 40 0)
           (cons 41 0)
           (cons 42 0)
           (cons 91 0)
           (list 10 16.82 -4)
           (cons 40 0)
           (cons 41 0)
           (cons 42 0)
           (cons 91 0)
           (list 10 14.18 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.66666667 1.60566667)
           (cons 40 0)
           (cons 41 0)
           (cons 42 0)
           (cons 91 0)
           (list 10 13.66666667 2.17766667)
           (cons 40 0)
           (cons 41 0)
           (cons 42 0)
           (cons 91 0)
           (list 10 14.18 2.35)
           (cons 40 0)
           (cons 41 0)
           (cons 42 0)
           (cons 91 0)
           (list 10 16.82 2.35)
           (cons 40 0)
           (cons 41 0)
           (cons 42 0)
           (cons 91 0)
           (list 10 17.33333333 2.17766667)
           (cons 40 0)
           (cons 41 0)
           (cons 42 0)
           (cons 91 0)
           (list 10 17.33333333 1.60566667)
           (cons 40 0)
           (cons 41 0)
           (cons 42 0)
           (cons 91 0)
           (list 10 16.82 1.43333333)
           (cons 40 0)
           (cons 41 0)
           (cons 42 0)
           (cons 91 0)
           (list 10 14.18 1.43333333)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.66666667 3.25566667)
           (cons 40 0)
           (cons 41 0)
           (cons 42 0)
           (cons 91 0)
           (list 10 13.66666667 3.82766667)
           (cons 40 0)
           (cons 41 0)
           (cons 42 0)
           (cons 91 0)
           (list 10 14.18 4)
           (cons 40 0)
           (cons 41 0)
           (cons 42 0)
           (cons 91 0)
           (list 10 16.82 4)
           (cons 40 0)
           (cons 41 0)
           (cons 42 0)
           (cons 91 0)
           (list 10 17.33333333 3.82766667)
           (cons 40 0)
           (cons 41 0)
           (cons 42 0)
           (cons 91 0)
           (list 10 17.33333333 3.25566667)
           (cons 40 0)
           (cons 41 0)
           (cons 42 0)
           (cons 91 0)
           (list 10 16.82 3.08333333)
           (cons 40 0)
           (cons 41 0)
           (cons 42 0)
           (cons 91 0)
           (list 10 14.18 3.08333333)
           (cons 40 0)
           (cons 41 0)
           (cons 42 0)
           (cons 91 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4)
           (cons 40 0)
           (cons 41 0)
           (cons 42 0)
           (cons 91 0)
           (list 10 15.5 -4)
           (cons 40 0)
           (cons 41 0)
           (cons 42 0)
           (cons 91 0)
           (list 10 15.5 4)
           (cons 40 0)
           (cons 41 0)
           (cons 42 0)
           (cons 91 0)
           (list 10 0 4)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 3 -4 0)
           (cons 50 0)
          )
         )
         (entmake
          (list
           (cons 0 "POINT")
           (cons 100 "AcDbEntity")
           (cons 67 0)
           (cons 8 "0")
           (cons 100 "AcDbPoint")
           (list 10 15.5 -4 0)
           (cons 50 0)
          )
         )
         (entmake
          (list
           (cons 0 "POINT")
           (cons 100 "AcDbEntity")
           (cons 67 0)
           (cons 8 "0")
           (cons 100 "AcDbPoint")
           (list 10 15.5 4 0)
           (cons 50 0)
          )
         )
         (entmake
          (list
           (cons 0 "POINT")
           (cons 100 "AcDbEntity")
           (cons 67 0)
           (cons 8 "0")
           (cons 100 "AcDbPoint")
           (list 10 15.5 0 0)
           (cons 50 0)
          )
         )
         (entmake
          (list
           (cons 0 "POINT")
           (cons 100 "AcDbEntity")
           (cons 67 0)
           (cons 8 "0")
           (cons 100 "AcDbPoint")
           (list 10 3 4 0)
           (cons 50 0)
          )
         )
         (entmake
          (list
           (cons 0 "POINT")
           (cons 100 "AcDbEntity")
           (cons 67 0)
           (cons 8 "0")
           (cons 100 "AcDbPoint")
           (list 10 0 4 0)
           (cons 50 0)
          )
         )
         (entmake
          (list
           (cons 0 "POINT")
           (cons 100 "AcDbEntity")
           (cons 67 0)
           (cons 8 "0")
           (cons 100 "AcDbPoint")
           (list 10 0 -4 0)
           (cons 50 0)
          )
         )
         (entmake
          (list
           (cons 0 "POINT")
           (cons 100 "AcDbEntity")
           (cons 67 0)
           (cons 8 "0")
           (cons 100 "AcDbPoint")
           (list 10 3 0 0)
           (cons 50 0)
          )
         )
         (entmake
          (list
           (cons 0 "INSERT")
           (cons 100 "AcDbEntity")
           (cons 67 0)
           (cons 8 "0")
           (cons 100 "AcDbBlockReference")
           (cons 2 "WheelLeft1")
           (list 10 3 -3.08333333 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRight1")
           (list 10 3 3.08333333 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 0.70341207 1.85914261 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 0.76552931 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -0.32808399 0)
           (cons 40 0.65616798)
           (cons 1 "15.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -1.42169729 0)
           (cons 40 0.65616798)
           (cons 1 "15.500")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -2.51531059 0)
           (cons 40 0.65616798)
           (cons 1 "20.3")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-SU-40"))
        (progn
         (entmake)
         (entmake
          (list
           (cons 0 "BLOCK")
           (cons 2 "AASHTO-2011-SU-40")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 39.5 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 39.5 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 25.13333333 -2.34333333)
           (cons 40 0)
           (cons 41 0)
           (cons 42 0)
           (cons 91 0)
           (list 10 25.13333333 -1.82333333)
           (cons 40 0)
           (cons 41 0)
           (cons 42 0)
           (cons 91 0)
           (list 10 25.6 -1.66666667)
           (cons 40 0)
           (cons 41 0)
           (cons 42 0)
           (cons 91 0)
           (list 10 28 -1.66666667)
           (cons 40 0)
           (cons 41 0)
           (cons 42 0)
           (cons 91 0)
           (list 10 28.46666667 -1.82333333)
           (cons 40 0)
           (cons 41 0)
           (cons 42 0)
           (cons 91 0)
           (list 10 28.46666667 -2.34333333)
           (cons 40 0)
           (cons 41 0)
           (cons 42 0)
           (cons 91 0)
           (list 10 28 -2.5)
           (cons 40 0)
           (cons 41 0)
           (cons 42 0)
           (cons 91 0)
           (list 10 25.6 -2.5)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 25.13333333 -3.84333333)
           (cons 40 0)
           (cons 41 0)
           (cons 42 0)
           (cons 91 0)
           (list 10 25.13333333 -3.32333333)
           (cons 40 0)
           (cons 41 0)
           (cons 42 0)
           (cons 91 0)
           (list 10 25.6 -3.16666667)
           (cons 40 0)
           (cons 41 0)
           (cons 42 0)
           (cons 91 0)
           (list 10 28 -3.16666667)
           (cons 40 0)
           (cons 41 0)
           (cons 42 0)
           (cons 91 0)
           (list 10 28.46666667 -3.32333333)
           (cons 40 0)
           (cons 41 0)
           (cons 42 0)
           (cons 91 0)
           (list 10 28.46666667 -3.84333333)
           (cons 40 0)
           (cons 41 0)
           (cons 42 0)
           (cons 91 0)
           (list 10 28 -4)
           (cons 40 0)
           (cons 41 0)
           (cons 42 0)
           (cons 91 0)
           (list 10 25.6 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 25.13333333 1.82333333)
           (cons 40 0)
           (cons 41 0)
           (cons 42 0)
           (cons 91 0)
           (list 10 25.13333333 2.34333333)
           (cons 40 0)
           (cons 41 0)
           (cons 42 0)
           (cons 91 0)
           (list 10 25.6 2.5)
           (cons 40 0)
           (cons 41 0)
           (cons 42 0)
           (cons 91 0)
           (list 10 28 2.5)
           (cons 40 0)
           (cons 41 0)
           (cons 42 0)
           (cons 91 0)
           (list 10 28.46666667 2.34333333)
           (cons 40 0)
           (cons 41 0)
           (cons 42 0)
           (cons 91 0)
           (list 10 28.46666667 1.82333333)
           (cons 40 0)
           (cons 41 0)
           (cons 42 0)
           (cons 91 0)
           (list 10 28 1.66666667)
           (cons 40 0)
           (cons 41 0)
           (cons 42 0)
           (cons 91 0)
           (list 10 25.6 1.66666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 25.13333333 3.32333333)
           (cons 40 0)
           (cons 41 0)
           (cons 42 0)
           (cons 91 0)
           (list 10 25.13333333 3.84333333)
           (cons 40 0)
           (cons 41 0)
           (cons 42 0)
           (cons 91 0)
           (list 10 25.6 4)
           (cons 40 0)
           (cons 41 0)
           (cons 42 0)
           (cons 91 0)
           (list 10 28 4)
           (cons 40 0)
           (cons 41 0)
           (cons 42 0)
           (cons 91 0)
           (list 10 28.46666667 3.84333333)
           (cons 40 0)
           (cons 41 0)
           (cons 42 0)
           (cons 91 0)
           (list 10 28.46666667 3.32333333)
           (cons 40 0)
           (cons 41 0)
           (cons 42 0)
           (cons 91 0)
           (list 10 28 3.16666667)
           (cons 40 0)
           (cons 41 0)
           (cons 42 0)
           (cons 91 0)
           (list 10 25.6 3.16666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 29.53333333 -2.34333333)
           (cons 40 0)
           (cons 41 0)
           (cons 42 0)
           (cons 91 0)
           (list 10 29.53333333 -1.82333333)
           (cons 40 0)
           (cons 41 0)
           (cons 42 0)
           (cons 91 0)
           (list 10 30 -1.66666667)
           (cons 40 0)
           (cons 41 0)
           (cons 42 0)
           (cons 91 0)
           (list 10 32.4 -1.66666667)
           (cons 40 0)
           (cons 41 0)
           (cons 42 0)
           (cons 91 0)
           (list 10 32.86666667 -1.82333333)
           (cons 40 0)
           (cons 41 0)
           (cons 42 0)
           (cons 91 0)
           (list 10 32.86666667 -2.34333333)
           (cons 40 0)
           (cons 41 0)
           (cons 42 0)
           (cons 91 0)
           (list 10 32.4 -2.5)
           (cons 40 0)
           (cons 41 0)
           (cons 42 0)
           (cons 91 0)
           (list 10 30 -2.5)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 29.53333333 -3.84333333)
           (cons 40 0)
           (cons 41 0)
           (cons 42 0)
           (cons 91 0)
           (list 10 29.53333333 -3.32333333)
           (cons 40 0)
           (cons 41 0)
           (cons 42 0)
           (cons 91 0)
           (list 10 30 -3.16666667)
           (cons 40 0)
           (cons 41 0)
           (cons 42 0)
           (cons 91 0)
           (list 10 32.4 -3.16666667)
           (cons 40 0)
           (cons 41 0)
           (cons 42 0)
           (cons 91 0)
           (list 10 32.86666667 -3.32333333)
           (cons 40 0)
           (cons 41 0)
           (cons 42 0)
           (cons 91 0)
           (list 10 32.86666667 -3.84333333)
           (cons 40 0)
           (cons 41 0)
           (cons 42 0)
           (cons 91 0)
           (list 10 32.4 -4)
           (cons 40 0)
           (cons 41 0)
           (cons 42 0)
           (cons 91 0)
           (list 10 30 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 29.53333333 1.82333333)
           (cons 40 0)
           (cons 41 0)
           (cons 42 0)
           (cons 91 0)
           (list 10 29.53333333 2.34333333)
           (cons 40 0)
           (cons 41 0)
           (cons 42 0)
           (cons 91 0)
           (list 10 30 2.5)
           (cons 40 0)
           (cons 41 0)
           (cons 42 0)
           (cons 91 0)
           (list 10 32.4 2.5)
           (cons 40 0)
           (cons 41 0)
           (cons 42 0)
           (cons 91 0)
           (list 10 32.86666667 2.34333333)
           (cons 40 0)
           (cons 41 0)
           (cons 42 0)
           (cons 91 0)
           (list 10 32.86666667 1.82333333)
           (cons 40 0)
           (cons 41 0)
           (cons 42 0)
           (cons 91 0)
           (list 10 32.4 1.66666667)
           (cons 40 0)
           (cons 41 0)
           (cons 42 0)
           (cons 91 0)
           (list 10 30 1.66666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 29.53333333 3.32333333)
           (cons 40 0)
           (cons 41 0)
           (cons 42 0)
           (cons 91 0)
           (list 10 29.53333333 3.84333333)
           (cons 40 0)
           (cons 41 0)
           (cons 42 0)
           (cons 91 0)
           (list 10 30 4)
           (cons 40 0)
           (cons 41 0)
           (cons 42 0)
           (cons 91 0)
           (list 10 32.4 4)
           (cons 40 0)
           (cons 41 0)
           (cons 42 0)
           (cons 91 0)
           (list 10 32.86666667 3.84333333)
           (cons 40 0)
           (cons 41 0)
           (cons 42 0)
           (cons 91 0)
           (list 10 32.86666667 3.32333333)
           (cons 40 0)
           (cons 41 0)
           (cons 42 0)
           (cons 91 0)
           (list 10 32.4 3.16666667)
           (cons 40 0)
           (cons 41 0)
           (cons 42 0)
           (cons 91 0)
           (list 10 30 3.16666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4 0)
           (cons 50 0)
          )
         )
         (entmake
          (list
           (cons 0 "POINT")
           (cons 100 "AcDbEntity")
           (cons 67 0)
           (cons 8 "0")
           (cons 100 "AcDbPoint")
           (list 10 0 4 0)
           (cons 50 0)
          )
         )
         (entmake
          (list
           (cons 0 "POINT")
           (cons 100 "AcDbEntity")
           (cons 67 0)
           (cons 8 "0")
           (cons 100 "AcDbPoint")
           (list 10 4 4 0)
           (cons 50 0)
          )
         )
         (entmake
          (list
           (cons 0 "POINT")
           (cons 100 "AcDbEntity")
           (cons 67 0)
           (cons 8 "0")
           (cons 100 "AcDbPoint")
           (list 10 29 4 0)
           (cons 50 0)
          )
         )
         (entmake
          (list
           (cons 0 "POINT")
           (cons 100 "AcDbEntity")
           (cons 67 0)
           (cons 8 "0")
           (cons 100 "AcDbPoint")
           (list 10 39.5 4 0)
           (cons 50 0)
          )
         )
         (entmake
          (list
           (cons 0 "POINT")
           (cons 100 "AcDbEntity")
           (cons 67 0)
           (cons 8 "0")
           (cons 100 "AcDbPoint")
           (list 10 39.5 -4 0)
           (cons 50 0)
          )
         )
         (entmake
          (list
           (cons 0 "POINT")
           (cons 100 "AcDbEntity")
           (cons 67 0)
           (cons 8 "0")
           (cons 100 "AcDbPoint")
           (list 10 29 -4 0)
           (cons 50 0)
          )
         )
         (entmake
          (list
           (cons 0 "POINT")
           (cons 100 "AcDbEntity")
           (cons 67 0)
           (cons 8 "0")
           (cons 100 "AcDbPoint")
           (list 10 4 -4 0)
           (cons 50 0)
          )
         )
         (entmake
          (list
           (cons 0 "POINT")
           (cons 100 "AcDbEntity")
           (cons 67 0)
           (cons 8 "0")
           (cons 100 "AcDbPoint")
           (list 10 4 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4)
           (cons 40 0)
           (cons 41 0)
           (cons 42 0)
           (cons 91 0)
           (list 10 39.5 -4)
           (cons 40 0)
           (cons 41 0)
           (cons 42 0)
           (cons 91 0)
           (list 10 39.5 4)
           (cons 40 0)
           (cons 41 0)
           (cons 42 0)
           (cons 91 0)
           (list 10 0 4)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelRight2")
           (list 10 4 3.16666667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeft2")
           (list 10 4 -3.16666667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 1.70341207 1.85914261 0)
           (cons 40 0.65616798)
           (cons 1 "4.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 0.76552931 0)
           (cons 40 0.65616798)
           (cons 1 "4.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -0.32808399 0)
           (cons 40 0.65616798)
           (cons 1 "29.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -2.51531059 0)
           (cons 40 0.65616798)
           (cons 1 "31.8")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-SU-30"))
        (progn
         (entmake)
         (entmake
          (list
           (cons 0 "BLOCK")
           (cons 2 "AASHTO-2011-SU-30")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 30 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 30 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 22.33333333 -2.34333333)
           (cons 40 0)
           (cons 41 0)
           (cons 42 0)
           (cons 91 0)
           (list 10 22.33333333 -1.82333333)
           (cons 40 0)
           (cons 41 0)
           (cons 42 0)
           (cons 91 0)
           (list 10 22.8 -1.66666667)
           (cons 40 0)
           (cons 41 0)
           (cons 42 0)
           (cons 91 0)
           (list 10 25.2 -1.66666667)
           (cons 40 0)
           (cons 41 0)
           (cons 42 0)
           (cons 91 0)
           (list 10 25.66666667 -1.82333333)
           (cons 40 0)
           (cons 41 0)
           (cons 42 0)
           (cons 91 0)
           (list 10 25.66666667 -2.34333333)
           (cons 40 0)
           (cons 41 0)
           (cons 42 0)
           (cons 91 0)
           (list 10 25.2 -2.5)
           (cons 40 0)
           (cons 41 0)
           (cons 42 0)
           (cons 91 0)
           (list 10 22.8 -2.5)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 22.33333333 -3.84333333)
           (cons 40 0)
           (cons 41 0)
           (cons 42 0)
           (cons 91 0)
           (list 10 22.33333333 -3.32333333)
           (cons 40 0)
           (cons 41 0)
           (cons 42 0)
           (cons 91 0)
           (list 10 22.8 -3.16666667)
           (cons 40 0)
           (cons 41 0)
           (cons 42 0)
           (cons 91 0)
           (list 10 25.2 -3.16666667)
           (cons 40 0)
           (cons 41 0)
           (cons 42 0)
           (cons 91 0)
           (list 10 25.66666667 -3.32333333)
           (cons 40 0)
           (cons 41 0)
           (cons 42 0)
           (cons 91 0)
           (list 10 25.66666667 -3.84333333)
           (cons 40 0)
           (cons 41 0)
           (cons 42 0)
           (cons 91 0)
           (list 10 25.2 -4)
           (cons 40 0)
           (cons 41 0)
           (cons 42 0)
           (cons 91 0)
           (list 10 22.8 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 22.33333333 1.82333333)
           (cons 40 0)
           (cons 41 0)
           (cons 42 0)
           (cons 91 0)
           (list 10 22.33333333 2.34333333)
           (cons 40 0)
           (cons 41 0)
           (cons 42 0)
           (cons 91 0)
           (list 10 22.8 2.5)
           (cons 40 0)
           (cons 41 0)
           (cons 42 0)
           (cons 91 0)
           (list 10 25.2 2.5)
           (cons 40 0)
           (cons 41 0)
           (cons 42 0)
           (cons 91 0)
           (list 10 25.66666667 2.34333333)
           (cons 40 0)
           (cons 41 0)
           (cons 42 0)
           (cons 91 0)
           (list 10 25.66666667 1.82333333)
           (cons 40 0)
           (cons 41 0)
           (cons 42 0)
           (cons 91 0)
           (list 10 25.2 1.66666667)
           (cons 40 0)
           (cons 41 0)
           (cons 42 0)
           (cons 91 0)
           (list 10 22.8 1.66666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 22.33333333 3.32333333)
           (cons 40 0)
           (cons 41 0)
           (cons 42 0)
           (cons 91 0)
           (list 10 22.33333333 3.84333333)
           (cons 40 0)
           (cons 41 0)
           (cons 42 0)
           (cons 91 0)
           (list 10 22.8 4)
           (cons 40 0)
           (cons 41 0)
           (cons 42 0)
           (cons 91 0)
           (list 10 25.2 4)
           (cons 40 0)
           (cons 41 0)
           (cons 42 0)
           (cons 91 0)
           (list 10 25.66666667 3.84333333)
           (cons 40 0)
           (cons 41 0)
           (cons 42 0)
           (cons 91 0)
           (list 10 25.66666667 3.32333333)
           (cons 40 0)
           (cons 41 0)
           (cons 42 0)
           (cons 91 0)
           (list 10 25.2 3.16666667)
           (cons 40 0)
           (cons 41 0)
           (cons 42 0)
           (cons 91 0)
           (list 10 22.8 3.16666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 4 0 0)
           (cons 50 0)
          )
         )
         (entmake
          (list
           (cons 0 "POINT")
           (cons 100 "AcDbEntity")
           (cons 67 0)
           (cons 8 "0")
           (cons 100 "AcDbPoint")
           (list 10 0 -4 0)
           (cons 50 0)
          )
         )
         (entmake
          (list
           (cons 0 "POINT")
           (cons 100 "AcDbEntity")
           (cons 67 0)
           (cons 8 "0")
           (cons 100 "AcDbPoint")
           (list 10 4 -4 0)
           (cons 50 0)
          )
         )
         (entmake
          (list
           (cons 0 "POINT")
           (cons 100 "AcDbEntity")
           (cons 67 0)
           (cons 8 "0")
           (cons 100 "AcDbPoint")
           (list 10 24 -4 0)
           (cons 50 0)
          )
         )
         (entmake
          (list
           (cons 0 "POINT")
           (cons 100 "AcDbEntity")
           (cons 67 0)
           (cons 8 "0")
           (cons 100 "AcDbPoint")
           (list 10 30 -4 0)
           (cons 50 0)
          )
         )
         (entmake
          (list
           (cons 0 "POINT")
           (cons 100 "AcDbEntity")
           (cons 67 0)
           (cons 8 "0")
           (cons 100 "AcDbPoint")
           (list 10 30 4 0)
           (cons 50 0)
          )
         )
         (entmake
          (list
           (cons 0 "POINT")
           (cons 100 "AcDbEntity")
           (cons 67 0)
           (cons 8 "0")
           (cons 100 "AcDbPoint")
           (list 10 24 4 0)
           (cons 50 0)
          )
         )
         (entmake
          (list
           (cons 0 "POINT")
           (cons 100 "AcDbEntity")
           (cons 67 0)
           (cons 8 "0")
           (cons 100 "AcDbPoint")
           (list 10 4 4 0)
           (cons 50 0)
          )
         )
         (entmake
          (list
           (cons 0 "POINT")
           (cons 100 "AcDbEntity")
           (cons 67 0)
           (cons 8 "0")
           (cons 100 "AcDbPoint")
           (list 10 0 4 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4)
           (cons 40 0)
           (cons 41 0)
           (cons 42 0)
           (cons 91 0)
           (list 10 30 -4)
           (cons 40 0)
           (cons 41 0)
           (cons 42 0)
           (cons 91 0)
           (list 10 30 4)
           (cons 40 0)
           (cons 41 0)
           (cons 42 0)
           (cons 91 0)
           (list 10 0 4)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelRight2")
           (list 10 4 3.16666667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeft2")
           (list 10 4 -3.16666667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 1.70341207 1.85914261 0)
           (cons 40 0.65616798)
           (cons 1 "4.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 0.76552931 0)
           (cons 40 0.65616798)
           (cons 1 "4.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -0.32808399 0)
           (cons 40 0.65616798)
           (cons 1 "24.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -2.51531059 0)
           (cons 40 0.65616798)
           (cons 1 "31.8")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-S-BUS-40"))
        (progn
         (entmake)
         (entmake
          (list
           (cons 0 "BLOCK")
           (cons 2 "AASHTO-2011-S-BUS-40")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 39.99343832 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 39.99343832 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 25.33333333 -3.84333333)
           (cons 40 0)
           (cons 41 0)
           (cons 42 0)
           (cons 91 0)
           (list 10 25.33333333 -3.32333333)
           (cons 40 0)
           (cons 41 0)
           (cons 42 0)
           (cons 91 0)
           (list 10 25.8 -3.16666667)
           (cons 40 0)
           (cons 41 0)
           (cons 42 0)
           (cons 91 0)
           (list 10 28.2 -3.16666667)
           (cons 40 0)
           (cons 41 0)
           (cons 42 0)
           (cons 91 0)
           (list 10 28.66666667 -3.32333333)
           (cons 40 0)
           (cons 41 0)
           (cons 42 0)
           (cons 91 0)
           (list 10 28.66666667 -3.84333333)
           (cons 40 0)
           (cons 41 0)
           (cons 42 0)
           (cons 91 0)
           (list 10 28.2 -4)
           (cons 40 0)
           (cons 41 0)
           (cons 42 0)
           (cons 91 0)
           (list 10 25.8 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 25.33333333 3.32333333)
           (cons 40 0)
           (cons 41 0)
           (cons 42 0)
           (cons 91 0)
           (list 10 25.33333333 3.84333333)
           (cons 40 0)
           (cons 41 0)
           (cons 42 0)
           (cons 91 0)
           (list 10 25.8 4)
           (cons 40 0)
           (cons 41 0)
           (cons 42 0)
           (cons 91 0)
           (list 10 28.2 4)
           (cons 40 0)
           (cons 41 0)
           (cons 42 0)
           (cons 91 0)
           (list 10 28.66666667 3.84333333)
           (cons 40 0)
           (cons 41 0)
           (cons 42 0)
           (cons 91 0)
           (list 10 28.66666667 3.32333333)
           (cons 40 0)
           (cons 41 0)
           (cons 42 0)
           (cons 91 0)
           (list 10 28.2 3.16666667)
           (cons 40 0)
           (cons 41 0)
           (cons 42 0)
           (cons 91 0)
           (list 10 25.8 3.16666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4 0)
           (cons 50 0)
          )
         )
         (entmake
          (list
           (cons 0 "POINT")
           (cons 100 "AcDbEntity")
           (cons 67 0)
           (cons 8 "0")
           (cons 100 "AcDbPoint")
           (list 10 7 -4 0)
           (cons 50 0)
          )
         )
         (entmake
          (list
           (cons 0 "POINT")
           (cons 100 "AcDbEntity")
           (cons 67 0)
           (cons 8 "0")
           (cons 100 "AcDbPoint")
           (list 10 27 -4 0)
           (cons 50 0)
          )
         )
         (entmake
          (list
           (cons 0 "POINT")
           (cons 100 "AcDbEntity")
           (cons 67 0)
           (cons 8 "0")
           (cons 100 "AcDbPoint")
           (list 10 39.99343832 -4 0)
           (cons 50 0)
          )
         )
         (entmake
          (list
           (cons 0 "POINT")
           (cons 100 "AcDbEntity")
           (cons 67 0)
           (cons 8 "0")
           (cons 100 "AcDbPoint")
           (list 10 39.99343832 4 0)
           (cons 50 0)
          )
         )
         (entmake
          (list
           (cons 0 "POINT")
           (cons 100 "AcDbEntity")
           (cons 67 0)
           (cons 8 "0")
           (cons 100 "AcDbPoint")
           (list 10 27 4 0)
           (cons 50 0)
          )
         )
         (entmake
          (list
           (cons 0 "POINT")
           (cons 100 "AcDbEntity")
           (cons 67 0)
           (cons 8 "0")
           (cons 100 "AcDbPoint")
           (list 10 7 4 0)
           (cons 50 0)
          )
         )
         (entmake
          (list
           (cons 0 "POINT")
           (cons 100 "AcDbEntity")
           (cons 67 0)
           (cons 8 "0")
           (cons 100 "AcDbPoint")
           (list 10 0 4 0)
           (cons 50 0)
          )
         )
         (entmake
          (list
           (cons 0 "POINT")
           (cons 100 "AcDbEntity")
           (cons 67 0)
           (cons 8 "0")
           (cons 100 "AcDbPoint")
           (list 10 7 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4)
           (cons 40 0)
           (cons 41 0)
           (cons 42 0)
           (cons 91 0)
           (list 10 39.99343832 -4)
           (cons 40 0)
           (cons 41 0)
           (cons 42 0)
           (cons 91 0)
           (list 10 39.99343832 4)
           (cons 40 0)
           (cons 41 0)
           (cons 42 0)
           (cons 91 0)
           (list 10 0 4)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelRight2")
           (list 10 7 3.16666667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeft2")
           (list 10 7 -3.16666667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 4.70341207 1.85914261 0)
           (cons 40 0.65616798)
           (cons 1 "7.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 4.70341207 0.76552931 0)
           (cons 40 0.65616798)
           (cons 1 "7.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 4.70341207 -0.32808399 0)
           (cons 40 0.65616798)
           (cons 1 "27.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 4.70341207 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 4.70341207 -2.51531059 0)
           (cons 40 0.65616798)
           (cons 1 "34.4")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-S-BUS-36"))
        (progn
         (entmake)
         (entmake
          (list
           (cons 0 "BLOCK")
           (cons 2 "AASHTO-2011-S-BUS-36")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4)
           (cons 40 0)
           (cons 41 0)
           (cons 42 0)
           (cons 91 0)
           (list 10 35.8 -4)
           (cons 40 0)
           (cons 41 0)
           (cons 42 0)
           (cons 91 0)
           (list 10 35.8 4)
           (cons 40 0)
           (cons 41 0)
           (cons 42 0)
           (cons 91 0)
           (list 10 0 4)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 35.8 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 35.8 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 22.13333333 -2.34333333)
           (cons 40 0)
           (cons 41 0)
           (cons 42 0)
           (cons 91 0)
           (list 10 22.13333333 -1.82333333)
           (cons 40 0)
           (cons 41 0)
           (cons 42 0)
           (cons 91 0)
           (list 10 22.6 -1.66666667)
           (cons 40 0)
           (cons 41 0)
           (cons 42 0)
           (cons 91 0)
           (list 10 25 -1.66666667)
           (cons 40 0)
           (cons 41 0)
           (cons 42 0)
           (cons 91 0)
           (list 10 25.46666667 -1.82333333)
           (cons 40 0)
           (cons 41 0)
           (cons 42 0)
           (cons 91 0)
           (list 10 25.46666667 -2.34333333)
           (cons 40 0)
           (cons 41 0)
           (cons 42 0)
           (cons 91 0)
           (list 10 25 -2.5)
           (cons 40 0)
           (cons 41 0)
           (cons 42 0)
           (cons 91 0)
           (list 10 22.6 -2.5)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 22.13333333 -3.84333333)
           (cons 40 0)
           (cons 41 0)
           (cons 42 0)
           (cons 91 0)
           (list 10 22.13333333 -3.32333333)
           (cons 40 0)
           (cons 41 0)
           (cons 42 0)
           (cons 91 0)
           (list 10 22.6 -3.16666667)
           (cons 40 0)
           (cons 41 0)
           (cons 42 0)
           (cons 91 0)
           (list 10 25 -3.16666667)
           (cons 40 0)
           (cons 41 0)
           (cons 42 0)
           (cons 91 0)
           (list 10 25.46666667 -3.32333333)
           (cons 40 0)
           (cons 41 0)
           (cons 42 0)
           (cons 91 0)
           (list 10 25.46666667 -3.84333333)
           (cons 40 0)
           (cons 41 0)
           (cons 42 0)
           (cons 91 0)
           (list 10 25 -4)
           (cons 40 0)
           (cons 41 0)
           (cons 42 0)
           (cons 91 0)
           (list 10 22.6 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 22.13333333 1.82333333)
           (cons 40 0)
           (cons 41 0)
           (cons 42 0)
           (cons 91 0)
           (list 10 22.13333333 2.34333333)
           (cons 40 0)
           (cons 41 0)
           (cons 42 0)
           (cons 91 0)
           (list 10 22.6 2.5)
           (cons 40 0)
           (cons 41 0)
           (cons 42 0)
           (cons 91 0)
           (list 10 25 2.5)
           (cons 40 0)
           (cons 41 0)
           (cons 42 0)
           (cons 91 0)
           (list 10 25.46666667 2.34333333)
           (cons 40 0)
           (cons 41 0)
           (cons 42 0)
           (cons 91 0)
           (list 10 25.46666667 1.82333333)
           (cons 40 0)
           (cons 41 0)
           (cons 42 0)
           (cons 91 0)
           (list 10 25 1.66666667)
           (cons 40 0)
           (cons 41 0)
           (cons 42 0)
           (cons 91 0)
           (list 10 22.6 1.66666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 22.13333333 3.32333333)
           (cons 40 0)
           (cons 41 0)
           (cons 42 0)
           (cons 91 0)
           (list 10 22.13333333 3.84333333)
           (cons 40 0)
           (cons 41 0)
           (cons 42 0)
           (cons 91 0)
           (list 10 22.6 4)
           (cons 40 0)
           (cons 41 0)
           (cons 42 0)
           (cons 91 0)
           (list 10 25 4)
           (cons 40 0)
           (cons 41 0)
           (cons 42 0)
           (cons 91 0)
           (list 10 25.46666667 3.84333333)
           (cons 40 0)
           (cons 41 0)
           (cons 42 0)
           (cons 91 0)
           (list 10 25.46666667 3.32333333)
           (cons 40 0)
           (cons 41 0)
           (cons 42 0)
           (cons 91 0)
           (list 10 25 3.16666667)
           (cons 40 0)
           (cons 41 0)
           (cons 42 0)
           (cons 91 0)
           (list 10 22.6 3.16666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4 0)
           (cons 50 0)
          )
         )
         (entmake
          (list
           (cons 0 "POINT")
           (cons 100 "AcDbEntity")
           (cons 67 0)
           (cons 8 "0")
           (cons 100 "AcDbPoint")
           (list 10 0 4 0)
           (cons 50 0)
          )
         )
         (entmake
          (list
           (cons 0 "POINT")
           (cons 100 "AcDbEntity")
           (cons 67 0)
           (cons 8 "0")
           (cons 100 "AcDbPoint")
           (list 10 35.8 4 0)
           (cons 50 0)
          )
         )
         (entmake
          (list
           (cons 0 "POINT")
           (cons 100 "AcDbEntity")
           (cons 67 0)
           (cons 8 "0")
           (cons 100 "AcDbPoint")
           (list 10 35.8 -4 0)
           (cons 50 0)
          )
         )
         (entmake
          (list
           (cons 0 "POINT")
           (cons 100 "AcDbEntity")
           (cons 67 0)
           (cons 8 "0")
           (cons 100 "AcDbPoint")
           (list 10 23.8 -4 0)
           (cons 50 0)
          )
         )
         (entmake
          (list
           (cons 0 "POINT")
           (cons 100 "AcDbEntity")
           (cons 67 0)
           (cons 8 "0")
           (cons 100 "AcDbPoint")
           (list 10 23.8 4 0)
           (cons 50 0)
          )
         )
         (entmake
          (list
           (cons 0 "POINT")
           (cons 100 "AcDbEntity")
           (cons 67 0)
           (cons 8 "0")
           (cons 100 "AcDbPoint")
           (list 10 2.5 0 0)
           (cons 50 0)
          )
         )
         (entmake
          (list
           (cons 0 "POINT")
           (cons 100 "AcDbEntity")
           (cons 67 0)
           (cons 8 "0")
           (cons 100 "AcDbPoint")
           (list 10 2.5 -4 0)
           (cons 50 0)
          )
         )
         (entmake
          (list
           (cons 0 "POINT")
           (cons 100 "AcDbEntity")
           (cons 67 0)
           (cons 8 "0")
           (cons 100 "AcDbPoint")
           (list 10 2.5 4 0)
           (cons 50 0)
          )
         )
         (entmake
          (list
           (cons 0 "INSERT")
           (cons 100 "AcDbEntity")
           (cons 67 0)
           (cons 8 "0")
           (cons 100 "AcDbBlockReference")
           (cons 2 "WheelRight2")
           (list 10 2.5 3.16666667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeft2")
           (list 10 2.5 -3.16666667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 0.20341207 1.85914261 0)
           (cons 40 0.65616798)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 0.76552931 0)
           (cons 40 0.65616798)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -0.32808399 0)
           (cons 40 0.65616798)
           (cons 1 "23.800")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -2.51531059 0)
           (cons 40 0.65616798)
           (cons 1 "37.6")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-T"))
        (progn
         (entmake)
         (entmake
          (list
           (cons 0 "BLOCK")
           (cons 2 "AASHTO-2011-T")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 5)
           (cons 70 129)
           (cons 43 0)
           (cons 38 0)
           (cons 39 0)
           (list 10 0 0)
           (cons 40 0)
           (cons 41 0)
           (cons 42 0)
           (cons 91 0)
           (list 10 3 4)
           (cons 40 0)
           (cons 41 0)
           (cons 42 0)
           (cons 91 0)
           (list 10 29.7 4)
           (cons 40 0)
           (cons 41 0)
           (cons 42 0)
           (cons 91 0)
           (list 10 29.7 -4)
           (cons 40 0)
           (cons 41 0)
           (cons 42 0)
           (cons 91 0)
           (list 10 3 -4)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 29.7 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 29.7 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 3 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.53333333)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.46666667 -3.90208333)
           (cons 40 0)
           (cons 41 0)
           (cons 42 0)
           (cons 91 0)
           (list 10 14.46666667 -3.57708333)
           (cons 40 0)
           (cons 41 0)
           (cons 42 0)
           (cons 91 0)
           (list 10 14.78866667 -3.47916667)
           (cons 40 0)
           (cons 41 0)
           (cons 42 0)
           (cons 91 0)
           (list 10 16.44466667 -3.47916667)
           (cons 40 0)
           (cons 41 0)
           (cons 42 0)
           (cons 91 0)
           (list 10 16.76666667 -3.57708333)
           (cons 40 0)
           (cons 41 0)
           (cons 42 0)
           (cons 91 0)
           (list 10 16.76666667 -3.90208333)
           (cons 40 0)
           (cons 41 0)
           (cons 42 0)
           (cons 91 0)
           (list 10 16.44466667 -4)
           (cons 40 0)
           (cons 41 0)
           (cons 42 0)
           (cons 91 0)
           (list 10 14.78866667 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.46666667 3.57708333)
           (cons 40 0)
           (cons 41 0)
           (cons 42 0)
           (cons 91 0)
           (list 10 14.46666667 3.90208333)
           (cons 40 0)
           (cons 41 0)
           (cons 42 0)
           (cons 91 0)
           (list 10 14.78866667 4)
           (cons 40 0)
           (cons 41 0)
           (cons 42 0)
           (cons 91 0)
           (list 10 16.44466667 4)
           (cons 40 0)
           (cons 41 0)
           (cons 42 0)
           (cons 91 0)
           (list 10 16.76666667 3.90208333)
           (cons 40 0)
           (cons 41 0)
           (cons 42 0)
           (cons 91 0)
           (list 10 16.76666667 3.57708333)
           (cons 40 0)
           (cons 41 0)
           (cons 42 0)
           (cons 91 0)
           (list 10 16.44466667 3.47916667)
           (cons 40 0)
           (cons 41 0)
           (cons 42 0)
           (cons 91 0)
           (list 10 14.78866667 3.47916667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 18.63333333 -3.90208333)
           (cons 40 0)
           (cons 41 0)
           (cons 42 0)
           (cons 91 0)
           (list 10 18.63333333 -3.57708333)
           (cons 40 0)
           (cons 41 0)
           (cons 42 0)
           (cons 91 0)
           (list 10 18.95533333 -3.47916667)
           (cons 40 0)
           (cons 41 0)
           (cons 42 0)
           (cons 91 0)
           (list 10 20.61133333 -3.47916667)
           (cons 40 0)
           (cons 41 0)
           (cons 42 0)
           (cons 91 0)
           (list 10 20.93333333 -3.57708333)
           (cons 40 0)
           (cons 41 0)
           (cons 42 0)
           (cons 91 0)
           (list 10 20.93333333 -3.90208333)
           (cons 40 0)
           (cons 41 0)
           (cons 42 0)
           (cons 91 0)
           (list 10 20.61133333 -4)
           (cons 40 0)
           (cons 41 0)
           (cons 42 0)
           (cons 91 0)
           (list 10 18.95533333 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 18.63333333 3.57708333)
           (cons 40 0)
           (cons 41 0)
           (cons 42 0)
           (cons 91 0)
           (list 10 18.63333333 3.90208333)
           (cons 40 0)
           (cons 41 0)
           (cons 42 0)
           (cons 91 0)
           (list 10 18.95533333 4)
           (cons 40 0)
           (cons 41 0)
           (cons 42 0)
           (cons 91 0)
           (list 10 20.61133333 4)
           (cons 40 0)
           (cons 41 0)
           (cons 42 0)
           (cons 91 0)
           (list 10 20.93333333 3.90208333)
           (cons 40 0)
           (cons 41 0)
           (cons 42 0)
           (cons 91 0)
           (list 10 20.93333333 3.57708333)
           (cons 40 0)
           (cons 41 0)
           (cons 42 0)
           (cons 91 0)
           (list 10 20.61133333 3.47916667)
           (cons 40 0)
           (cons 41 0)
           (cons 42 0)
           (cons 91 0)
           (list 10 18.95533333 3.47916667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 3 -4 0)
           (cons 50 0)
          )
         )
         (entmake
          (list
           (cons 0 "POINT")
           (cons 100 "AcDbEntity")
           (cons 67 0)
           (cons 8 "0")
           (cons 100 "AcDbPoint")
           (list 10 3 4 0)
           (cons 50 0)
          )
         )
         (entmake
          (list
           (cons 0 "POINT")
           (cons 100 "AcDbEntity")
           (cons 67 0)
           (cons 8 "0")
           (cons 100 "AcDbPoint")
           (list 10 29.7 4 0)
           (cons 50 0)
          )
         )
         (entmake
          (list
           (cons 0 "POINT")
           (cons 100 "AcDbEntity")
           (cons 67 0)
           (cons 8 "0")
           (cons 100 "AcDbPoint")
           (list 10 29.7 -4 0)
           (cons 50 0)
          )
         )
         (entmake
          (list
           (cons 0 "POINT")
           (cons 100 "AcDbEntity")
           (cons 67 0)
           (cons 8 "0")
           (cons 100 "AcDbPoint")
           (list 10 17.7 -4 0)
           (cons 50 0)
          )
         )
         (entmake
          (list
           (cons 0 "POINT")
           (cons 100 "AcDbEntity")
           (cons 67 0)
           (cons 8 "0")
           (cons 100 "AcDbPoint")
           (list 10 17.7 4 0)
           (cons 50 0)
          )
         )
         (entmake
          (list
           (cons 0 "ATTDEF")
           (cons 100 "AcDbEntity")
           (cons 67 0)
           (cons 8 "0")
           (cons 100 "AcDbText")
           (list 10 -2.29658793 1.85914261 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 0.76552931 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -0.32808399 0)
           (cons 40 0.65616798)
           (cons 1 "17.700")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-MH"))
        (progn
         (entmake)
         (entmake
          (list
           (cons 0 "BLOCK")
           (cons 2 "AASHTO-2011-MH")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 -4)
           (cons 40 0)
           (cons 41 0)
           (cons 42 0)
           (cons 91 0)
           (list 10 30 -4)
           (cons 40 0)
           (cons 41 0)
           (cons 42 0)
           (cons 91 0)
           (list 10 30 4)
           (cons 40 0)
           (cons 41 0)
           (cons 42 0)
           (cons 91 0)
           (list 10 0 4)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 30 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 30 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 22.33333333 -3.84333333)
           (cons 40 0)
           (cons 41 0)
           (cons 42 0)
           (cons 91 0)
           (list 10 22.33333333 -3.32333333)
           (cons 40 0)
           (cons 41 0)
           (cons 42 0)
           (cons 91 0)
           (list 10 22.8 -3.16666667)
           (cons 40 0)
           (cons 41 0)
           (cons 42 0)
           (cons 91 0)
           (list 10 25.2 -3.16666667)
           (cons 40 0)
           (cons 41 0)
           (cons 42 0)
           (cons 91 0)
           (list 10 25.66666667 -3.32333333)
           (cons 40 0)
           (cons 41 0)
           (cons 42 0)
           (cons 91 0)
           (list 10 25.66666667 -3.84333333)
           (cons 40 0)
           (cons 41 0)
           (cons 42 0)
           (cons 91 0)
           (list 10 25.2 -4)
           (cons 40 0)
           (cons 41 0)
           (cons 42 0)
           (cons 91 0)
           (list 10 22.8 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 22.33333333 3.32333333)
           (cons 40 0)
           (cons 41 0)
           (cons 42 0)
           (cons 91 0)
           (list 10 22.33333333 3.84333333)
           (cons 40 0)
           (cons 41 0)
           (cons 42 0)
           (cons 91 0)
           (list 10 22.8 4)
           (cons 40 0)
           (cons 41 0)
           (cons 42 0)
           (cons 91 0)
           (list 10 25.2 4)
           (cons 40 0)
           (cons 41 0)
           (cons 42 0)
           (cons 91 0)
           (list 10 25.66666667 3.84333333)
           (cons 40 0)
           (cons 41 0)
           (cons 42 0)
           (cons 91 0)
           (list 10 25.66666667 3.32333333)
           (cons 40 0)
           (cons 41 0)
           (cons 42 0)
           (cons 91 0)
           (list 10 25.2 3.16666667)
           (cons 40 0)
           (cons 41 0)
           (cons 42 0)
           (cons 91 0)
           (list 10 22.8 3.16666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4 0)
           (cons 50 0)
          )
         )
         (entmake
          (list
           (cons 0 "POINT")
           (cons 100 "AcDbEntity")
           (cons 67 0)
           (cons 8 "0")
           (cons 100 "AcDbPoint")
           (list 10 4 -4 0)
           (cons 50 0)
          )
         )
         (entmake
          (list
           (cons 0 "POINT")
           (cons 100 "AcDbEntity")
           (cons 67 0)
           (cons 8 "0")
           (cons 100 "AcDbPoint")
           (list 10 24 -4 0)
           (cons 50 0)
          )
         )
         (entmake
          (list
           (cons 0 "POINT")
           (cons 100 "AcDbEntity")
           (cons 67 0)
           (cons 8 "0")
           (cons 100 "AcDbPoint")
           (list 10 30 -4 0)
           (cons 50 0)
          )
         )
         (entmake
          (list
           (cons 0 "POINT")
           (cons 100 "AcDbEntity")
           (cons 67 0)
           (cons 8 "0")
           (cons 100 "AcDbPoint")
           (list 10 30 4 0)
           (cons 50 0)
          )
         )
         (entmake
          (list
           (cons 0 "POINT")
           (cons 100 "AcDbEntity")
           (cons 67 0)
           (cons 8 "0")
           (cons 100 "AcDbPoint")
           (list 10 24 4 0)
           (cons 50 0)
          )
         )
         (entmake
          (list
           (cons 0 "POINT")
           (cons 100 "AcDbEntity")
           (cons 67 0)
           (cons 8 "0")
           (cons 100 "AcDbPoint")
           (list 10 4 4 0)
           (cons 50 0)
          )
         )
         (entmake
          (list
           (cons 0 "POINT")
           (cons 100 "AcDbEntity")
           (cons 67 0)
           (cons 8 "0")
           (cons 100 "AcDbPoint")
           (list 10 0 4 0)
           (cons 50 0)
          )
         )
         (entmake
          (list
           (cons 0 "POINT")
           (cons 100 "AcDbEntity")
           (cons 67 0)
           (cons 8 "0")
           (cons 100 "AcDbPoint")
           (list 10 4 0 0)
           (cons 50 0)
          )
         )
         (entmake
          (list
           (cons 0 "POINT")
           (cons 100 "AcDbEntity")
           (cons 67 0)
           (cons 8 "0")
           (cons 100 "AcDbPoint")
           (list 10 29.98687664 0 0)
           (cons 50 0)
          )
         )
         (entmake
          (list
           (cons 0 "INSERT")
           (cons 100 "AcDbEntity")
           (cons 67 0)
           (cons 8 "0")
           (cons 100 "AcDbBlockReference")
           (cons 2 "WheelRight2")
           (list 10 4.0049 3.16666667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeft2")
           (list 10 4.0049 -3.16666667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 1.70341207 1.85914261 0)
           (cons 40 0.65616798)
           (cons 1 "4.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 0.76552931 0)
           (cons 40 0.65616798)
           (cons 1 "4.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -0.32808399 0)
           (cons 40 0.65616798)
           (cons 1 "24.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -1.42169729 0)
           (cons 40 0.65616798)
           (cons 1 "30.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -2.51531059 0)
           (cons 40 0.65616798)
           (cons 1 "25.8")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-B"))
        (progn
         (entmake)
         (entmake
          (list
           (cons 0 "BLOCK")
           (cons 2 "AASHTO-2011-B")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 5)
           (cons 70 129)
           (cons 43 0)
           (cons 38 0)
           (cons 39 0)
           (list 10 0 0)
           (cons 40 0)
           (cons 41 0)
           (cons 42 0)
           (cons 91 0)
           (list 10 3 4)
           (cons 40 0)
           (cons 41 0)
           (cons 42 0)
           (cons 91 0)
           (list 10 23 4)
           (cons 40 0)
           (cons 41 0)
           (cons 42 0)
           (cons 91 0)
           (list 10 23 -4)
           (cons 40 0)
           (cons 41 0)
           (cons 42 0)
           (cons 91 0)
           (list 10 3 -4)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 23 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 23 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 3 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.53333333)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.95833333 -3.90208333)
           (cons 40 0)
           (cons 41 0)
           (cons 42 0)
           (cons 91 0)
           (list 10 13.95833333 -3.57708333)
           (cons 40 0)
           (cons 41 0)
           (cons 42 0)
           (cons 91 0)
           (list 10 14.25 -3.47916667)
           (cons 40 0)
           (cons 41 0)
           (cons 42 0)
           (cons 91 0)
           (list 10 15.75 -3.47916667)
           (cons 40 0)
           (cons 41 0)
           (cons 42 0)
           (cons 91 0)
           (list 10 16.04166667 -3.57708333)
           (cons 40 0)
           (cons 41 0)
           (cons 42 0)
           (cons 91 0)
           (list 10 16.04166667 -3.90208333)
           (cons 40 0)
           (cons 41 0)
           (cons 42 0)
           (cons 91 0)
           (list 10 15.75 -4)
           (cons 40 0)
           (cons 41 0)
           (cons 42 0)
           (cons 91 0)
           (list 10 14.25 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.95833333 3.57708333)
           (cons 40 0)
           (cons 41 0)
           (cons 42 0)
           (cons 91 0)
           (list 10 13.95833333 3.90208333)
           (cons 40 0)
           (cons 41 0)
           (cons 42 0)
           (cons 91 0)
           (list 10 14.25 4)
           (cons 40 0)
           (cons 41 0)
           (cons 42 0)
           (cons 91 0)
           (list 10 15.75 4)
           (cons 40 0)
           (cons 41 0)
           (cons 42 0)
           (cons 91 0)
           (list 10 16.04166667 3.90208333)
           (cons 40 0)
           (cons 41 0)
           (cons 42 0)
           (cons 91 0)
           (list 10 16.04166667 3.57708333)
           (cons 40 0)
           (cons 41 0)
           (cons 42 0)
           (cons 91 0)
           (list 10 15.75 3.47916667)
           (cons 40 0)
           (cons 41 0)
           (cons 42 0)
           (cons 91 0)
           (list 10 14.25 3.47916667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 3 -4 0)
           (cons 50 0)
          )
         )
         (entmake
          (list
           (cons 0 "POINT")
           (cons 100 "AcDbEntity")
           (cons 67 0)
           (cons 8 "0")
           (cons 100 "AcDbPoint")
           (list 10 15 -4 0)
           (cons 50 0)
          )
         )
         (entmake
          (list
           (cons 0 "POINT")
           (cons 100 "AcDbEntity")
           (cons 67 0)
           (cons 8 "0")
           (cons 100 "AcDbPoint")
           (list 10 15 4 0)
           (cons 50 0)
          )
         )
         (entmake
          (list
           (cons 0 "POINT")
           (cons 100 "AcDbEntity")
           (cons 67 0)
           (cons 8 "0")
           (cons 100 "AcDbPoint")
           (list 10 23 4 0)
           (cons 50 0)
          )
         )
         (entmake
          (list
           (cons 0 "POINT")
           (cons 100 "AcDbEntity")
           (cons 67 0)
           (cons 8 "0")
           (cons 100 "AcDbPoint")
           (list 10 23 -4 0)
           (cons 50 0)
          )
         )
         (entmake
          (list
           (cons 0 "POINT")
           (cons 100 "AcDbEntity")
           (cons 67 0)
           (cons 8 "0")
           (cons 100 "AcDbPoint")
           (list 10 3 4 0)
           (cons 50 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "ATTDEF")
           (cons 100 "AcDbEntity")
           (cons 67 0)
           (cons 8 "0")
           (cons 100 "AcDbText")
           (list 10 -2.29658793 1.85914261 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 0.76552931 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -0.32808399 0)
           (cons 40 0.65616798)
           (cons 1 "15.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-MH"))
        (progn
         (entmake)
         (entmake
          (list
           (cons 0 "BLOCK")
           (cons 2 "AASHTO-2011-MH")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 -4)
           (cons 40 0)
           (cons 41 0)
           (cons 42 0)
           (cons 91 0)
           (list 10 30 -4)
           (cons 40 0)
           (cons 41 0)
           (cons 42 0)
           (cons 91 0)
           (list 10 30 4)
           (cons 40 0)
           (cons 41 0)
           (cons 42 0)
           (cons 91 0)
           (list 10 0 4)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 30 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 30 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 22.33333333 -3.84333333)
           (cons 40 0)
           (cons 41 0)
           (cons 42 0)
           (cons 91 0)
           (list 10 22.33333333 -3.32333333)
           (cons 40 0)
           (cons 41 0)
           (cons 42 0)
           (cons 91 0)
           (list 10 22.8 -3.16666667)
           (cons 40 0)
           (cons 41 0)
           (cons 42 0)
           (cons 91 0)
           (list 10 25.2 -3.16666667)
           (cons 40 0)
           (cons 41 0)
           (cons 42 0)
           (cons 91 0)
           (list 10 25.66666667 -3.32333333)
           (cons 40 0)
           (cons 41 0)
           (cons 42 0)
           (cons 91 0)
           (list 10 25.66666667 -3.84333333)
           (cons 40 0)
           (cons 41 0)
           (cons 42 0)
           (cons 91 0)
           (list 10 25.2 -4)
           (cons 40 0)
           (cons 41 0)
           (cons 42 0)
           (cons 91 0)
           (list 10 22.8 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 22.33333333 3.32333333)
           (cons 40 0)
           (cons 41 0)
           (cons 42 0)
           (cons 91 0)
           (list 10 22.33333333 3.84333333)
           (cons 40 0)
           (cons 41 0)
           (cons 42 0)
           (cons 91 0)
           (list 10 22.8 4)
           (cons 40 0)
           (cons 41 0)
           (cons 42 0)
           (cons 91 0)
           (list 10 25.2 4)
           (cons 40 0)
           (cons 41 0)
           (cons 42 0)
           (cons 91 0)
           (list 10 25.66666667 3.84333333)
           (cons 40 0)
           (cons 41 0)
           (cons 42 0)
           (cons 91 0)
           (list 10 25.66666667 3.32333333)
           (cons 40 0)
           (cons 41 0)
           (cons 42 0)
           (cons 91 0)
           (list 10 25.2 3.16666667)
           (cons 40 0)
           (cons 41 0)
           (cons 42 0)
           (cons 91 0)
           (list 10 22.8 3.16666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4 0)
           (cons 50 0)
          )
         )
         (entmake
          (list
           (cons 0 "POINT")
           (cons 100 "AcDbEntity")
           (cons 67 0)
           (cons 8 "0")
           (cons 100 "AcDbPoint")
           (list 10 4 -4 0)
           (cons 50 0)
          )
         )
         (entmake
          (list
           (cons 0 "POINT")
           (cons 100 "AcDbEntity")
           (cons 67 0)
           (cons 8 "0")
           (cons 100 "AcDbPoint")
           (list 10 24 -4 0)
           (cons 50 0)
          )
         )
         (entmake
          (list
           (cons 0 "POINT")
           (cons 100 "AcDbEntity")
           (cons 67 0)
           (cons 8 "0")
           (cons 100 "AcDbPoint")
           (list 10 30 -4 0)
           (cons 50 0)
          )
         )
         (entmake
          (list
           (cons 0 "POINT")
           (cons 100 "AcDbEntity")
           (cons 67 0)
           (cons 8 "0")
           (cons 100 "AcDbPoint")
           (list 10 30 4 0)
           (cons 50 0)
          )
         )
         (entmake
          (list
           (cons 0 "POINT")
           (cons 100 "AcDbEntity")
           (cons 67 0)
           (cons 8 "0")
           (cons 100 "AcDbPoint")
           (list 10 24 4 0)
           (cons 50 0)
          )
         )
         (entmake
          (list
           (cons 0 "POINT")
           (cons 100 "AcDbEntity")
           (cons 67 0)
           (cons 8 "0")
           (cons 100 "AcDbPoint")
           (list 10 4 4 0)
           (cons 50 0)
          )
         )
         (entmake
          (list
           (cons 0 "POINT")
           (cons 100 "AcDbEntity")
           (cons 67 0)
           (cons 8 "0")
           (cons 100 "AcDbPoint")
           (list 10 0 4 0)
           (cons 50 0)
          )
         )
         (entmake
          (list
           (cons 0 "POINT")
           (cons 100 "AcDbEntity")
           (cons 67 0)
           (cons 8 "0")
           (cons 100 "AcDbPoint")
           (list 10 4 0 0)
           (cons 50 0)
          )
         )
         (entmake
          (list
           (cons 0 "POINT")
           (cons 100 "AcDbEntity")
           (cons 67 0)
           (cons 8 "0")
           (cons 100 "AcDbPoint")
           (list 10 29.98687664 0 0)
           (cons 50 0)
          )
         )
         (entmake
          (list
           (cons 0 "INSERT")
           (cons 100 "AcDbEntity")
           (cons 67 0)
           (cons 8 "0")
           (cons 100 "AcDbBlockReference")
           (cons 2 "WheelRight2")
           (list 10 4.0049 3.16666667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeft2")
           (list 10 4.0049 -3.16666667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 1.70341207 1.85914261 0)
           (cons 40 0.65616798)
           (cons 1 "4.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 0.76552931 0)
           (cons 40 0.65616798)
           (cons 1 "4.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -0.32808399 0)
           (cons 40 0.65616798)
           (cons 1 "24.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -1.42169729 0)
           (cons 40 0.65616798)
           (cons 1 "30.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -2.51531059 0)
           (cons 40 0.65616798)
           (cons 1 "25.8")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-MH"))
        (progn
         (entmake)
         (entmake
          (list
           (cons 0 "BLOCK")
           (cons 2 "AASHTO-2011-MH")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 -4)
           (cons 40 0)
           (cons 41 0)
           (cons 42 0)
           (cons 91 0)
           (list 10 30 -4)
           (cons 40 0)
           (cons 41 0)
           (cons 42 0)
           (cons 91 0)
           (list 10 30 4)
           (cons 40 0)
           (cons 41 0)
           (cons 42 0)
           (cons 91 0)
           (list 10 0 4)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 30 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 30 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 22.33333333 -3.84333333)
           (cons 40 0)
           (cons 41 0)
           (cons 42 0)
           (cons 91 0)
           (list 10 22.33333333 -3.32333333)
           (cons 40 0)
           (cons 41 0)
           (cons 42 0)
           (cons 91 0)
           (list 10 22.8 -3.16666667)
           (cons 40 0)
           (cons 41 0)
           (cons 42 0)
           (cons 91 0)
           (list 10 25.2 -3.16666667)
           (cons 40 0)
           (cons 41 0)
           (cons 42 0)
           (cons 91 0)
           (list 10 25.66666667 -3.32333333)
           (cons 40 0)
           (cons 41 0)
           (cons 42 0)
           (cons 91 0)
           (list 10 25.66666667 -3.84333333)
           (cons 40 0)
           (cons 41 0)
           (cons 42 0)
           (cons 91 0)
           (list 10 25.2 -4)
           (cons 40 0)
           (cons 41 0)
           (cons 42 0)
           (cons 91 0)
           (list 10 22.8 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 22.33333333 3.32333333)
           (cons 40 0)
           (cons 41 0)
           (cons 42 0)
           (cons 91 0)
           (list 10 22.33333333 3.84333333)
           (cons 40 0)
           (cons 41 0)
           (cons 42 0)
           (cons 91 0)
           (list 10 22.8 4)
           (cons 40 0)
           (cons 41 0)
           (cons 42 0)
           (cons 91 0)
           (list 10 25.2 4)
           (cons 40 0)
           (cons 41 0)
           (cons 42 0)
           (cons 91 0)
           (list 10 25.66666667 3.84333333)
           (cons 40 0)
           (cons 41 0)
           (cons 42 0)
           (cons 91 0)
           (list 10 25.66666667 3.32333333)
           (cons 40 0)
           (cons 41 0)
           (cons 42 0)
           (cons 91 0)
           (list 10 25.2 3.16666667)
           (cons 40 0)
           (cons 41 0)
           (cons 42 0)
           (cons 91 0)
           (list 10 22.8 3.16666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4 0)
           (cons 50 0)
          )
         )
         (entmake
          (list
           (cons 0 "POINT")
           (cons 100 "AcDbEntity")
           (cons 67 0)
           (cons 8 "0")
           (cons 100 "AcDbPoint")
           (list 10 4 -4 0)
           (cons 50 0)
          )
         )
         (entmake
          (list
           (cons 0 "POINT")
           (cons 100 "AcDbEntity")
           (cons 67 0)
           (cons 8 "0")
           (cons 100 "AcDbPoint")
           (list 10 24 -4 0)
           (cons 50 0)
          )
         )
         (entmake
          (list
           (cons 0 "POINT")
           (cons 100 "AcDbEntity")
           (cons 67 0)
           (cons 8 "0")
           (cons 100 "AcDbPoint")
           (list 10 30 -4 0)
           (cons 50 0)
          )
         )
         (entmake
          (list
           (cons 0 "POINT")
           (cons 100 "AcDbEntity")
           (cons 67 0)
           (cons 8 "0")
           (cons 100 "AcDbPoint")
           (list 10 30 4 0)
           (cons 50 0)
          )
         )
         (entmake
          (list
           (cons 0 "POINT")
           (cons 100 "AcDbEntity")
           (cons 67 0)
           (cons 8 "0")
           (cons 100 "AcDbPoint")
           (list 10 24 4 0)
           (cons 50 0)
          )
         )
         (entmake
          (list
           (cons 0 "POINT")
           (cons 100 "AcDbEntity")
           (cons 67 0)
           (cons 8 "0")
           (cons 100 "AcDbPoint")
           (list 10 4 4 0)
           (cons 50 0)
          )
         )
         (entmake
          (list
           (cons 0 "POINT")
           (cons 100 "AcDbEntity")
           (cons 67 0)
           (cons 8 "0")
           (cons 100 "AcDbPoint")
           (list 10 0 4 0)
           (cons 50 0)
          )
         )
         (entmake
          (list
           (cons 0 "POINT")
           (cons 100 "AcDbEntity")
           (cons 67 0)
           (cons 8 "0")
           (cons 100 "AcDbPoint")
           (list 10 4 0 0)
           (cons 50 0)
          )
         )
         (entmake
          (list
           (cons 0 "POINT")
           (cons 100 "AcDbEntity")
           (cons 67 0)
           (cons 8 "0")
           (cons 100 "AcDbPoint")
           (list 10 29.98687664 0 0)
           (cons 50 0)
          )
         )
         (entmake
          (list
           (cons 0 "INSERT")
           (cons 100 "AcDbEntity")
           (cons 67 0)
           (cons 8 "0")
           (cons 100 "AcDbBlockReference")
           (cons 2 "WheelRight2")
           (list 10 4.0049 3.16666667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeft2")
           (list 10 4.0049 -3.16666667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 1.70341207 1.85914261 0)
           (cons 40 0.65616798)
           (cons 1 "4.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 0.76552931 0)
           (cons 40 0.65616798)
           (cons 1 "4.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -0.32808399 0)
           (cons 40 0.65616798)
           (cons 1 "24.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -1.42169729 0)
           (cons 40 0.65616798)
           (cons 1 "30.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -2.51531059 0)
           (cons 40 0.65616798)
           (cons 1 "25.8")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-T"))
        (progn
         (entmake)
         (entmake
          (list
           (cons 0 "BLOCK")
           (cons 2 "AASHTO-2011-T")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 5)
           (cons 70 129)
           (cons 43 0)
           (cons 38 0)
           (cons 39 0)
           (list 10 0 0)
           (cons 40 0)
           (cons 41 0)
           (cons 42 0)
           (cons 91 0)
           (list 10 3 4)
           (cons 40 0)
           (cons 41 0)
           (cons 42 0)
           (cons 91 0)
           (list 10 29.7 4)
           (cons 40 0)
           (cons 41 0)
           (cons 42 0)
           (cons 91 0)
           (list 10 29.7 -4)
           (cons 40 0)
           (cons 41 0)
           (cons 42 0)
           (cons 91 0)
           (list 10 3 -4)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 29.7 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 29.7 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 3 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.53333333)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.46666667 -3.90208333)
           (cons 40 0)
           (cons 41 0)
           (cons 42 0)
           (cons 91 0)
           (list 10 14.46666667 -3.57708333)
           (cons 40 0)
           (cons 41 0)
           (cons 42 0)
           (cons 91 0)
           (list 10 14.78866667 -3.47916667)
           (cons 40 0)
           (cons 41 0)
           (cons 42 0)
           (cons 91 0)
           (list 10 16.44466667 -3.47916667)
           (cons 40 0)
           (cons 41 0)
           (cons 42 0)
           (cons 91 0)
           (list 10 16.76666667 -3.57708333)
           (cons 40 0)
           (cons 41 0)
           (cons 42 0)
           (cons 91 0)
           (list 10 16.76666667 -3.90208333)
           (cons 40 0)
           (cons 41 0)
           (cons 42 0)
           (cons 91 0)
           (list 10 16.44466667 -4)
           (cons 40 0)
           (cons 41 0)
           (cons 42 0)
           (cons 91 0)
           (list 10 14.78866667 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.46666667 3.57708333)
           (cons 40 0)
           (cons 41 0)
           (cons 42 0)
           (cons 91 0)
           (list 10 14.46666667 3.90208333)
           (cons 40 0)
           (cons 41 0)
           (cons 42 0)
           (cons 91 0)
           (list 10 14.78866667 4)
           (cons 40 0)
           (cons 41 0)
           (cons 42 0)
           (cons 91 0)
           (list 10 16.44466667 4)
           (cons 40 0)
           (cons 41 0)
           (cons 42 0)
           (cons 91 0)
           (list 10 16.76666667 3.90208333)
           (cons 40 0)
           (cons 41 0)
           (cons 42 0)
           (cons 91 0)
           (list 10 16.76666667 3.57708333)
           (cons 40 0)
           (cons 41 0)
           (cons 42 0)
           (cons 91 0)
           (list 10 16.44466667 3.47916667)
           (cons 40 0)
           (cons 41 0)
           (cons 42 0)
           (cons 91 0)
           (list 10 14.78866667 3.47916667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 18.63333333 -3.90208333)
           (cons 40 0)
           (cons 41 0)
           (cons 42 0)
           (cons 91 0)
           (list 10 18.63333333 -3.57708333)
           (cons 40 0)
           (cons 41 0)
           (cons 42 0)
           (cons 91 0)
           (list 10 18.95533333 -3.47916667)
           (cons 40 0)
           (cons 41 0)
           (cons 42 0)
           (cons 91 0)
           (list 10 20.61133333 -3.47916667)
           (cons 40 0)
           (cons 41 0)
           (cons 42 0)
           (cons 91 0)
           (list 10 20.93333333 -3.57708333)
           (cons 40 0)
           (cons 41 0)
           (cons 42 0)
           (cons 91 0)
           (list 10 20.93333333 -3.90208333)
           (cons 40 0)
           (cons 41 0)
           (cons 42 0)
           (cons 91 0)
           (list 10 20.61133333 -4)
           (cons 40 0)
           (cons 41 0)
           (cons 42 0)
           (cons 91 0)
           (list 10 18.95533333 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 18.63333333 3.57708333)
           (cons 40 0)
           (cons 41 0)
           (cons 42 0)
           (cons 91 0)
           (list 10 18.63333333 3.90208333)
           (cons 40 0)
           (cons 41 0)
           (cons 42 0)
           (cons 91 0)
           (list 10 18.95533333 4)
           (cons 40 0)
           (cons 41 0)
           (cons 42 0)
           (cons 91 0)
           (list 10 20.61133333 4)
           (cons 40 0)
           (cons 41 0)
           (cons 42 0)
           (cons 91 0)
           (list 10 20.93333333 3.90208333)
           (cons 40 0)
           (cons 41 0)
           (cons 42 0)
           (cons 91 0)
           (list 10 20.93333333 3.57708333)
           (cons 40 0)
           (cons 41 0)
           (cons 42 0)
           (cons 91 0)
           (list 10 20.61133333 3.47916667)
           (cons 40 0)
           (cons 41 0)
           (cons 42 0)
           (cons 91 0)
           (list 10 18.95533333 3.47916667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 3 -4 0)
           (cons 50 0)
          )
         )
         (entmake
          (list
           (cons 0 "POINT")
           (cons 100 "AcDbEntity")
           (cons 67 0)
           (cons 8 "0")
           (cons 100 "AcDbPoint")
           (list 10 3 4 0)
           (cons 50 0)
          )
         )
         (entmake
          (list
           (cons 0 "POINT")
           (cons 100 "AcDbEntity")
           (cons 67 0)
           (cons 8 "0")
           (cons 100 "AcDbPoint")
           (list 10 29.7 4 0)
           (cons 50 0)
          )
         )
         (entmake
          (list
           (cons 0 "POINT")
           (cons 100 "AcDbEntity")
           (cons 67 0)
           (cons 8 "0")
           (cons 100 "AcDbPoint")
           (list 10 29.7 -4 0)
           (cons 50 0)
          )
         )
         (entmake
          (list
           (cons 0 "POINT")
           (cons 100 "AcDbEntity")
           (cons 67 0)
           (cons 8 "0")
           (cons 100 "AcDbPoint")
           (list 10 17.7 -4 0)
           (cons 50 0)
          )
         )
         (entmake
          (list
           (cons 0 "POINT")
           (cons 100 "AcDbEntity")
           (cons 67 0)
           (cons 8 "0")
           (cons 100 "AcDbPoint")
           (list 10 17.7 4 0)
           (cons 50 0)
          )
         )
         (entmake
          (list
           (cons 0 "ATTDEF")
           (cons 100 "AcDbEntity")
           (cons 67 0)
           (cons 8 "0")
           (cons 100 "AcDbText")
           (list 10 -2.29658793 1.85914261 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 0.76552931 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -0.32808399 0)
           (cons 40 0.65616798)
           (cons 1 "17.700")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-P"))
        (progn
         (entmake)
         (entmake
          (list
           (cons 0 "BLOCK")
           (cons 2 "AASHTO-2011-P")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 -3.5)
           (cons 40 0)
           (cons 41 0)
           (cons 42 0)
           (cons 91 0)
           (list 10 19 -3.5)
           (cons 40 0)
           (cons 41 0)
           (cons 42 0)
           (cons 91 0)
           (list 10 19 3.5)
           (cons 40 0)
           (cons 41 0)
           (cons 42 0)
           (cons 91 0)
           (list 10 0 3.5)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -3.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 19 -3.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 19 3.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 3.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -3.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -3.5 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.95833333 -2.90208333)
           (cons 40 0)
           (cons 41 0)
           (cons 42 0)
           (cons 91 0)
           (list 10 12.95833333 -2.57708333)
           (cons 40 0)
           (cons 41 0)
           (cons 42 0)
           (cons 91 0)
           (list 10 13.25 -2.47916667)
           (cons 40 0)
           (cons 41 0)
           (cons 42 0)
           (cons 91 0)
           (list 10 14.75 -2.47916667)
           (cons 40 0)
           (cons 41 0)
           (cons 42 0)
           (cons 91 0)
           (list 10 15.04166667 -2.57708333)
           (cons 40 0)
           (cons 41 0)
           (cons 42 0)
           (cons 91 0)
           (list 10 15.04166667 -2.90208333)
           (cons 40 0)
           (cons 41 0)
           (cons 42 0)
           (cons 91 0)
           (list 10 14.75 -3)
           (cons 40 0)
           (cons 41 0)
           (cons 42 0)
           (cons 91 0)
           (list 10 13.25 -3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.95833333 2.57708333)
           (cons 40 0)
           (cons 41 0)
           (cons 42 0)
           (cons 91 0)
           (list 10 12.95833333 2.90208333)
           (cons 40 0)
           (cons 41 0)
           (cons 42 0)
           (cons 91 0)
           (list 10 13.25 3)
           (cons 40 0)
           (cons 41 0)
           (cons 42 0)
           (cons 91 0)
           (list 10 14.75 3)
           (cons 40 0)
           (cons 41 0)
           (cons 42 0)
           (cons 91 0)
           (list 10 15.04166667 2.90208333)
           (cons 40 0)
           (cons 41 0)
           (cons 42 0)
           (cons 91 0)
           (list 10 15.04166667 2.57708333)
           (cons 40 0)
           (cons 41 0)
           (cons 42 0)
           (cons 91 0)
           (list 10 14.75 2.47916667)
           (cons 40 0)
           (cons 41 0)
           (cons 42 0)
           (cons 91 0)
           (list 10 13.25 2.47916667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 3 0 0)
           (cons 50 0)
          )
         )
         (entmake
          (list
           (cons 0 "POINT")
           (cons 100 "AcDbEntity")
           (cons 67 0)
           (cons 8 "0")
           (cons 100 "AcDbPoint")
           (list 10 3 3 0)
           (cons 50 0)
          )
         )
         (entmake
          (list
           (cons 0 "POINT")
           (cons 100 "AcDbEntity")
           (cons 67 0)
           (cons 8 "0")
           (cons 100 "AcDbPoint")
           (list 10 3 -3 0)
           (cons 50 0)
          )
         )
         (entmake
          (list
           (cons 0 "POINT")
           (cons 100 "AcDbEntity")
           (cons 67 0)
           (cons 8 "0")
           (cons 100 "AcDbPoint")
           (list 10 0 3.5 0)
           (cons 50 0)
          )
         )
         (entmake
          (list
           (cons 0 "POINT")
           (cons 100 "AcDbEntity")
           (cons 67 0)
           (cons 8 "0")
           (cons 100 "AcDbPoint")
           (list 10 0 -3.5 0)
           (cons 50 0)
          )
         )
         (entmake
          (list
           (cons 0 "POINT")
           (cons 100 "AcDbEntity")
           (cons 67 0)
           (cons 8 "0")
           (cons 100 "AcDbPoint")
           (list 10 14 -3 0)
           (cons 50 0)
          )
         )
         (entmake
          (list
           (cons 0 "POINT")
           (cons 100 "AcDbEntity")
           (cons 67 0)
           (cons 8 "0")
           (cons 100 "AcDbPoint")
           (list 10 14 3 0)
           (cons 50 0)
          )
         )
         (entmake
          (list
           (cons 0 "POINT")
           (cons 100 "AcDbEntity")
           (cons 67 0)
           (cons 8 "0")
           (cons 100 "AcDbPoint")
           (list 10 19 3.5 0)
           (cons 50 0)
          )
         )
         (entmake
          (list
           (cons 0 "POINT")
           (cons 100 "AcDbEntity")
           (cons 67 0)
           (cons 8 "0")
           (cons 100 "AcDbPoint")
           (list 10 19 -3.5 0)
           (cons 50 0)
          )
         )
         (entmake
          (list
           (cons 0 "POINT")
           (cons 100 "AcDbEntity")
           (cons 67 0)
           (cons 8 "0")
           (cons 100 "AcDbPoint")
           (list 10 19 0 0)
           (cons 50 0)
          )
         )
         (entmake
          (list
           (cons 0 "INSERT")
           (cons 100 "AcDbEntity")
           (cons 67 0)
           (cons 8 "0")
           (cons 100 "AcDbBlockReference")
           (cons 2 "WheelLeft4")
           (list 10 3 -2.47916667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRight4")
           (list 10 3 2.47916667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 0.70341207 1.85914261 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 0.76552931 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -0.32808399 0)
           (cons 40 0.65616798)
           (cons 1 "14.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -1.42169729 0)
           (cons 40 0.65616798)
           (cons 1 "19.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -2.51531059 0)
           (cons 40 0.65616798)
           (cons 1 "31.6")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-B"))
        (progn
         (entmake)
         (entmake
          (list
           (cons 0 "BLOCK")
           (cons 2 "AASHTO-2011-B")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 5)
           (cons 70 129)
           (cons 43 0)
           (cons 38 0)
           (cons 39 0)
           (list 10 0 0)
           (cons 40 0)
           (cons 41 0)
           (cons 42 0)
           (cons 91 0)
           (list 10 3 4)
           (cons 40 0)
           (cons 41 0)
           (cons 42 0)
           (cons 91 0)
           (list 10 23 4)
           (cons 40 0)
           (cons 41 0)
           (cons 42 0)
           (cons 91 0)
           (list 10 23 -4)
           (cons 40 0)
           (cons 41 0)
           (cons 42 0)
           (cons 91 0)
           (list 10 3 -4)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 23 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 23 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 3 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.53333333)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.95833333 -3.90208333)
           (cons 40 0)
           (cons 41 0)
           (cons 42 0)
           (cons 91 0)
           (list 10 13.95833333 -3.57708333)
           (cons 40 0)
           (cons 41 0)
           (cons 42 0)
           (cons 91 0)
           (list 10 14.25 -3.47916667)
           (cons 40 0)
           (cons 41 0)
           (cons 42 0)
           (cons 91 0)
           (list 10 15.75 -3.47916667)
           (cons 40 0)
           (cons 41 0)
           (cons 42 0)
           (cons 91 0)
           (list 10 16.04166667 -3.57708333)
           (cons 40 0)
           (cons 41 0)
           (cons 42 0)
           (cons 91 0)
           (list 10 16.04166667 -3.90208333)
           (cons 40 0)
           (cons 41 0)
           (cons 42 0)
           (cons 91 0)
           (list 10 15.75 -4)
           (cons 40 0)
           (cons 41 0)
           (cons 42 0)
           (cons 91 0)
           (list 10 14.25 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.95833333 3.57708333)
           (cons 40 0)
           (cons 41 0)
           (cons 42 0)
           (cons 91 0)
           (list 10 13.95833333 3.90208333)
           (cons 40 0)
           (cons 41 0)
           (cons 42 0)
           (cons 91 0)
           (list 10 14.25 4)
           (cons 40 0)
           (cons 41 0)
           (cons 42 0)
           (cons 91 0)
           (list 10 15.75 4)
           (cons 40 0)
           (cons 41 0)
           (cons 42 0)
           (cons 91 0)
           (list 10 16.04166667 3.90208333)
           (cons 40 0)
           (cons 41 0)
           (cons 42 0)
           (cons 91 0)
           (list 10 16.04166667 3.57708333)
           (cons 40 0)
           (cons 41 0)
           (cons 42 0)
           (cons 91 0)
           (list 10 15.75 3.47916667)
           (cons 40 0)
           (cons 41 0)
           (cons 42 0)
           (cons 91 0)
           (list 10 14.25 3.47916667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 3 -4 0)
           (cons 50 0)
          )
         )
         (entmake
          (list
           (cons 0 "POINT")
           (cons 100 "AcDbEntity")
           (cons 67 0)
           (cons 8 "0")
           (cons 100 "AcDbPoint")
           (list 10 15 -4 0)
           (cons 50 0)
          )
         )
         (entmake
          (list
           (cons 0 "POINT")
           (cons 100 "AcDbEntity")
           (cons 67 0)
           (cons 8 "0")
           (cons 100 "AcDbPoint")
           (list 10 15 4 0)
           (cons 50 0)
          )
         )
         (entmake
          (list
           (cons 0 "POINT")
           (cons 100 "AcDbEntity")
           (cons 67 0)
           (cons 8 "0")
           (cons 100 "AcDbPoint")
           (list 10 23 4 0)
           (cons 50 0)
          )
         )
         (entmake
          (list
           (cons 0 "POINT")
           (cons 100 "AcDbEntity")
           (cons 67 0)
           (cons 8 "0")
           (cons 100 "AcDbPoint")
           (list 10 23 -4 0)
           (cons 50 0)
          )
         )
         (entmake
          (list
           (cons 0 "POINT")
           (cons 100 "AcDbEntity")
           (cons 67 0)
           (cons 8 "0")
           (cons 100 "AcDbPoint")
           (list 10 3 4 0)
           (cons 50 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "ATTDEF")
           (cons 100 "AcDbEntity")
           (cons 67 0)
           (cons 8 "0")
           (cons 100 "AcDbText")
           (list 10 -2.29658793 1.85914261 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 0.76552931 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -0.32808399 0)
           (cons 40 0.65616798)
           (cons 1 "15.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-P"))
        (progn
         (entmake)
         (entmake
          (list
           (cons 0 "BLOCK")
           (cons 2 "AASHTO-2011-P")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 -3.5)
           (cons 40 0)
           (cons 41 0)
           (cons 42 0)
           (cons 91 0)
           (list 10 19 -3.5)
           (cons 40 0)
           (cons 41 0)
           (cons 42 0)
           (cons 91 0)
           (list 10 19 3.5)
           (cons 40 0)
           (cons 41 0)
           (cons 42 0)
           (cons 91 0)
           (list 10 0 3.5)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -3.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 19 -3.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 19 3.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 3.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -3.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -3.5 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.95833333 -2.90208333)
           (cons 40 0)
           (cons 41 0)
           (cons 42 0)
           (cons 91 0)
           (list 10 12.95833333 -2.57708333)
           (cons 40 0)
           (cons 41 0)
           (cons 42 0)
           (cons 91 0)
           (list 10 13.25 -2.47916667)
           (cons 40 0)
           (cons 41 0)
           (cons 42 0)
           (cons 91 0)
           (list 10 14.75 -2.47916667)
           (cons 40 0)
           (cons 41 0)
           (cons 42 0)
           (cons 91 0)
           (list 10 15.04166667 -2.57708333)
           (cons 40 0)
           (cons 41 0)
           (cons 42 0)
           (cons 91 0)
           (list 10 15.04166667 -2.90208333)
           (cons 40 0)
           (cons 41 0)
           (cons 42 0)
           (cons 91 0)
           (list 10 14.75 -3)
           (cons 40 0)
           (cons 41 0)
           (cons 42 0)
           (cons 91 0)
           (list 10 13.25 -3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.95833333 2.57708333)
           (cons 40 0)
           (cons 41 0)
           (cons 42 0)
           (cons 91 0)
           (list 10 12.95833333 2.90208333)
           (cons 40 0)
           (cons 41 0)
           (cons 42 0)
           (cons 91 0)
           (list 10 13.25 3)
           (cons 40 0)
           (cons 41 0)
           (cons 42 0)
           (cons 91 0)
           (list 10 14.75 3)
           (cons 40 0)
           (cons 41 0)
           (cons 42 0)
           (cons 91 0)
           (list 10 15.04166667 2.90208333)
           (cons 40 0)
           (cons 41 0)
           (cons 42 0)
           (cons 91 0)
           (list 10 15.04166667 2.57708333)
           (cons 40 0)
           (cons 41 0)
           (cons 42 0)
           (cons 91 0)
           (list 10 14.75 2.47916667)
           (cons 40 0)
           (cons 41 0)
           (cons 42 0)
           (cons 91 0)
           (list 10 13.25 2.47916667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 3 0 0)
           (cons 50 0)
          )
         )
         (entmake
          (list
           (cons 0 "POINT")
           (cons 100 "AcDbEntity")
           (cons 67 0)
           (cons 8 "0")
           (cons 100 "AcDbPoint")
           (list 10 3 3 0)
           (cons 50 0)
          )
         )
         (entmake
          (list
           (cons 0 "POINT")
           (cons 100 "AcDbEntity")
           (cons 67 0)
           (cons 8 "0")
           (cons 100 "AcDbPoint")
           (list 10 3 -3 0)
           (cons 50 0)
          )
         )
         (entmake
          (list
           (cons 0 "POINT")
           (cons 100 "AcDbEntity")
           (cons 67 0)
           (cons 8 "0")
           (cons 100 "AcDbPoint")
           (list 10 0 3.5 0)
           (cons 50 0)
          )
         )
         (entmake
          (list
           (cons 0 "POINT")
           (cons 100 "AcDbEntity")
           (cons 67 0)
           (cons 8 "0")
           (cons 100 "AcDbPoint")
           (list 10 0 -3.5 0)
           (cons 50 0)
          )
         )
         (entmake
          (list
           (cons 0 "POINT")
           (cons 100 "AcDbEntity")
           (cons 67 0)
           (cons 8 "0")
           (cons 100 "AcDbPoint")
           (list 10 14 -3 0)
           (cons 50 0)
          )
         )
         (entmake
          (list
           (cons 0 "POINT")
           (cons 100 "AcDbEntity")
           (cons 67 0)
           (cons 8 "0")
           (cons 100 "AcDbPoint")
           (list 10 14 3 0)
           (cons 50 0)
          )
         )
         (entmake
          (list
           (cons 0 "POINT")
           (cons 100 "AcDbEntity")
           (cons 67 0)
           (cons 8 "0")
           (cons 100 "AcDbPoint")
           (list 10 19 3.5 0)
           (cons 50 0)
          )
         )
         (entmake
          (list
           (cons 0 "POINT")
           (cons 100 "AcDbEntity")
           (cons 67 0)
           (cons 8 "0")
           (cons 100 "AcDbPoint")
           (list 10 19 -3.5 0)
           (cons 50 0)
          )
         )
         (entmake
          (list
           (cons 0 "POINT")
           (cons 100 "AcDbEntity")
           (cons 67 0)
           (cons 8 "0")
           (cons 100 "AcDbPoint")
           (list 10 19 0 0)
           (cons 50 0)
          )
         )
         (entmake
          (list
           (cons 0 "INSERT")
           (cons 100 "AcDbEntity")
           (cons 67 0)
           (cons 8 "0")
           (cons 100 "AcDbBlockReference")
           (cons 2 "WheelLeft4")
           (list 10 3 -2.47916667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRight4")
           (list 10 3 2.47916667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 0.70341207 1.85914261 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 0.76552931 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -0.32808399 0)
           (cons 40 0.65616798)
           (cons 1 "14.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -1.42169729 0)
           (cons 40 0.65616798)
           (cons 1 "19.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -2.51531059 0)
           (cons 40 0.65616798)
           (cons 1 "31.6")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-P"))
        (progn
         (entmake)
         (entmake
          (list
           (cons 0 "BLOCK")
           (cons 2 "AASHTO-2011-P")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 -3.5)
           (cons 40 0)
           (cons 41 0)
           (cons 42 0)
           (cons 91 0)
           (list 10 19 -3.5)
           (cons 40 0)
           (cons 41 0)
           (cons 42 0)
           (cons 91 0)
           (list 10 19 3.5)
           (cons 40 0)
           (cons 41 0)
           (cons 42 0)
           (cons 91 0)
           (list 10 0 3.5)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -3.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 19 -3.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 19 3.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 3.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -3.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -3.5 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.95833333 -2.90208333)
           (cons 40 0)
           (cons 41 0)
           (cons 42 0)
           (cons 91 0)
           (list 10 12.95833333 -2.57708333)
           (cons 40 0)
           (cons 41 0)
           (cons 42 0)
           (cons 91 0)
           (list 10 13.25 -2.47916667)
           (cons 40 0)
           (cons 41 0)
           (cons 42 0)
           (cons 91 0)
           (list 10 14.75 -2.47916667)
           (cons 40 0)
           (cons 41 0)
           (cons 42 0)
           (cons 91 0)
           (list 10 15.04166667 -2.57708333)
           (cons 40 0)
           (cons 41 0)
           (cons 42 0)
           (cons 91 0)
           (list 10 15.04166667 -2.90208333)
           (cons 40 0)
           (cons 41 0)
           (cons 42 0)
           (cons 91 0)
           (list 10 14.75 -3)
           (cons 40 0)
           (cons 41 0)
           (cons 42 0)
           (cons 91 0)
           (list 10 13.25 -3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.95833333 2.57708333)
           (cons 40 0)
           (cons 41 0)
           (cons 42 0)
           (cons 91 0)
           (list 10 12.95833333 2.90208333)
           (cons 40 0)
           (cons 41 0)
           (cons 42 0)
           (cons 91 0)
           (list 10 13.25 3)
           (cons 40 0)
           (cons 41 0)
           (cons 42 0)
           (cons 91 0)
           (list 10 14.75 3)
           (cons 40 0)
           (cons 41 0)
           (cons 42 0)
           (cons 91 0)
           (list 10 15.04166667 2.90208333)
           (cons 40 0)
           (cons 41 0)
           (cons 42 0)
           (cons 91 0)
           (list 10 15.04166667 2.57708333)
           (cons 40 0)
           (cons 41 0)
           (cons 42 0)
           (cons 91 0)
           (list 10 14.75 2.47916667)
           (cons 40 0)
           (cons 41 0)
           (cons 42 0)
           (cons 91 0)
           (list 10 13.25 2.47916667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 3 0 0)
           (cons 50 0)
          )
         )
         (entmake
          (list
           (cons 0 "POINT")
           (cons 100 "AcDbEntity")
           (cons 67 0)
           (cons 8 "0")
           (cons 100 "AcDbPoint")
           (list 10 3 3 0)
           (cons 50 0)
          )
         )
         (entmake
          (list
           (cons 0 "POINT")
           (cons 100 "AcDbEntity")
           (cons 67 0)
           (cons 8 "0")
           (cons 100 "AcDbPoint")
           (list 10 3 -3 0)
           (cons 50 0)
          )
         )
         (entmake
          (list
           (cons 0 "POINT")
           (cons 100 "AcDbEntity")
           (cons 67 0)
           (cons 8 "0")
           (cons 100 "AcDbPoint")
           (list 10 0 3.5 0)
           (cons 50 0)
          )
         )
         (entmake
          (list
           (cons 0 "POINT")
           (cons 100 "AcDbEntity")
           (cons 67 0)
           (cons 8 "0")
           (cons 100 "AcDbPoint")
           (list 10 0 -3.5 0)
           (cons 50 0)
          )
         )
         (entmake
          (list
           (cons 0 "POINT")
           (cons 100 "AcDbEntity")
           (cons 67 0)
           (cons 8 "0")
           (cons 100 "AcDbPoint")
           (list 10 14 -3 0)
           (cons 50 0)
          )
         )
         (entmake
          (list
           (cons 0 "POINT")
           (cons 100 "AcDbEntity")
           (cons 67 0)
           (cons 8 "0")
           (cons 100 "AcDbPoint")
           (list 10 14 3 0)
           (cons 50 0)
          )
         )
         (entmake
          (list
           (cons 0 "POINT")
           (cons 100 "AcDbEntity")
           (cons 67 0)
           (cons 8 "0")
           (cons 100 "AcDbPoint")
           (list 10 19 3.5 0)
           (cons 50 0)
          )
         )
         (entmake
          (list
           (cons 0 "POINT")
           (cons 100 "AcDbEntity")
           (cons 67 0)
           (cons 8 "0")
           (cons 100 "AcDbPoint")
           (list 10 19 -3.5 0)
           (cons 50 0)
          )
         )
         (entmake
          (list
           (cons 0 "POINT")
           (cons 100 "AcDbEntity")
           (cons 67 0)
           (cons 8 "0")
           (cons 100 "AcDbPoint")
           (list 10 19 0 0)
           (cons 50 0)
          )
         )
         (entmake
          (list
           (cons 0 "INSERT")
           (cons 100 "AcDbEntity")
           (cons 67 0)
           (cons 8 "0")
           (cons 100 "AcDbBlockReference")
           (cons 2 "WheelLeft4")
           (list 10 3 -2.47916667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRight4")
           (list 10 3 2.47916667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 0.70341207 1.85914261 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 0.76552931 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -0.32808399 0)
           (cons 40 0.65616798)
           (cons 1 "14.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -1.42169729 0)
           (cons 40 0.65616798)
           (cons 1 "19.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -2.51531059 0)
           (cons 40 0.65616798)
           (cons 1 "31.6")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-CITY-BUS"))
        (progn
         (entmake)
         (entmake
          (list
           (cons 0 "BLOCK")
           (cons 2 "AASHTO-2011-CITY-BUS")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 -4.25)
           (cons 40 0)
           (cons 41 0)
           (cons 42 0)
           (cons 91 0)
           (list 10 40 -4.25)
           (cons 40 0)
           (cons 41 0)
           (cons 42 0)
           (cons 91 0)
           (list 10 40 4.25)
           (cons 40 0)
           (cons 41 0)
           (cons 42 0)
           (cons 91 0)
           (list 10 0 4.25)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 40 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 40 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 30.33333333 -4.09333333)
           (cons 40 0)
           (cons 41 0)
           (cons 42 0)
           (cons 91 0)
           (list 10 30.33333333 -3.57333333)
           (cons 40 0)
           (cons 41 0)
           (cons 42 0)
           (cons 91 0)
           (list 10 30.8 -3.41666667)
           (cons 40 0)
           (cons 41 0)
           (cons 42 0)
           (cons 91 0)
           (list 10 33.2 -3.41666667)
           (cons 40 0)
           (cons 41 0)
           (cons 42 0)
           (cons 91 0)
           (list 10 33.66666667 -3.57333333)
           (cons 40 0)
           (cons 41 0)
           (cons 42 0)
           (cons 91 0)
           (list 10 33.66666667 -4.09333333)
           (cons 40 0)
           (cons 41 0)
           (cons 42 0)
           (cons 91 0)
           (list 10 33.2 -4.25)
           (cons 40 0)
           (cons 41 0)
           (cons 42 0)
           (cons 91 0)
           (list 10 30.8 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 30.33333333 3.57333333)
           (cons 40 0)
           (cons 41 0)
           (cons 42 0)
           (cons 91 0)
           (list 10 30.33333333 4.09333333)
           (cons 40 0)
           (cons 41 0)
           (cons 42 0)
           (cons 91 0)
           (list 10 30.8 4.25)
           (cons 40 0)
           (cons 41 0)
           (cons 42 0)
           (cons 91 0)
           (list 10 33.2 4.25)
           (cons 40 0)
           (cons 41 0)
           (cons 42 0)
           (cons 91 0)
           (list 10 33.66666667 4.09333333)
           (cons 40 0)
           (cons 41 0)
           (cons 42 0)
           (cons 91 0)
           (list 10 33.66666667 3.57333333)
           (cons 40 0)
           (cons 41 0)
           (cons 42 0)
           (cons 91 0)
           (list 10 33.2 3.41666667)
           (cons 40 0)
           (cons 41 0)
           (cons 42 0)
           (cons 91 0)
           (list 10 30.8 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4.25 0)
           (cons 50 0)
          )
         )
         (entmake
          (list
           (cons 0 "POINT")
           (cons 100 "AcDbEntity")
           (cons 67 0)
           (cons 8 "0")
           (cons 100 "AcDbPoint")
           (list 10 40 -4.25 0)
           (cons 50 0)
          )
         )
         (entmake
          (list
           (cons 0 "POINT")
           (cons 100 "AcDbEntity")
           (cons 67 0)
           (cons 8 "0")
           (cons 100 "AcDbPoint")
           (list 10 0 4.25 0)
           (cons 50 0)
          )
         )
         (entmake
          (list
           (cons 0 "POINT")
           (cons 100 "AcDbEntity")
           (cons 67 0)
           (cons 8 "0")
           (cons 100 "AcDbPoint")
           (list 10 40 4.25 0)
           (cons 50 0)
          )
         )
         (entmake
          (list
           (cons 0 "POINT")
           (cons 100 "AcDbEntity")
           (cons 67 0)
           (cons 8 "0")
           (cons 100 "AcDbPoint")
           (list 10 7 4.25 0)
           (cons 50 0)
          )
         )
         (entmake
          (list
           (cons 0 "POINT")
           (cons 100 "AcDbEntity")
           (cons 67 0)
           (cons 8 "0")
           (cons 100 "AcDbPoint")
           (list 10 32 4.25 0)
           (cons 50 0)
          )
         )
         (entmake
          (list
           (cons 0 "POINT")
           (cons 100 "AcDbEntity")
           (cons 67 0)
           (cons 8 "0")
           (cons 100 "AcDbPoint")
           (list 10 32 -4.25 0)
           (cons 50 0)
          )
         )
         (entmake
          (list
           (cons 0 "POINT")
           (cons 100 "AcDbEntity")
           (cons 67 0)
           (cons 8 "0")
           (cons 100 "AcDbPoint")
           (list 10 7 -4.25 0)
           (cons 50 0)
          )
         )
         (entmake
          (list
           (cons 0 "POINT")
           (cons 100 "AcDbEntity")
           (cons 67 0)
           (cons 8 "0")
           (cons 100 "AcDbPoint")
           (list 10 7 0 0)
           (cons 50 0)
          )
         )
         (entmake
          (list
           (cons 0 "INSERT")
           (cons 100 "AcDbEntity")
           (cons 67 0)
           (cons 8 "0")
           (cons 100 "AcDbBlockReference")
           (cons 2 "WheelLeft2")
           (list 10 7 -3.41666667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRight2")
           (list 10 7 3.41666667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 4.70341207 1.85914261 0)
           (cons 40 0.65616798)
           (cons 1 "7.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 4.70341207 0.76552931 0)
           (cons 40 0.65616798)
           (cons 1 "7.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 4.70341207 -0.32808399 0)
           (cons 40 0.65616798)
           (cons 1 "32.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 4.70341207 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 4.70341207 -2.51531059 0)
           (cons 40 0.65616798)
           (cons 1 "41.4")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-BUS-45"))
        (progn
         (entmake)
         (entmake
          (list
           (cons 0 "BLOCK")
           (cons 2 "AASHTO-2011-BUS-45")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 -4.25)
           (cons 40 0)
           (cons 41 0)
           (cons 42 0)
           (cons 91 0)
           (list 10 45.5 -4.25)
           (cons 40 0)
           (cons 41 0)
           (cons 42 0)
           (cons 91 0)
           (list 10 45.5 4.25)
           (cons 40 0)
           (cons 41 0)
           (cons 42 0)
           (cons 91 0)
           (list 10 0 4.25)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 45.5 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 45.5 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 30.83333333 -4.09333333)
           (cons 40 0)
           (cons 41 0)
           (cons 42 0)
           (cons 91 0)
           (list 10 30.83333333 -3.57333333)
           (cons 40 0)
           (cons 41 0)
           (cons 42 0)
           (cons 91 0)
           (list 10 31.3 -3.41666667)
           (cons 40 0)
           (cons 41 0)
           (cons 42 0)
           (cons 91 0)
           (list 10 33.7 -3.41666667)
           (cons 40 0)
           (cons 41 0)
           (cons 42 0)
           (cons 91 0)
           (list 10 34.16666667 -3.57333333)
           (cons 40 0)
           (cons 41 0)
           (cons 42 0)
           (cons 91 0)
           (list 10 34.16666667 -4.09333333)
           (cons 40 0)
           (cons 41 0)
           (cons 42 0)
           (cons 91 0)
           (list 10 33.7 -4.25)
           (cons 40 0)
           (cons 41 0)
           (cons 42 0)
           (cons 91 0)
           (list 10 31.3 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 30.83333333 3.57333333)
           (cons 40 0)
           (cons 41 0)
           (cons 42 0)
           (cons 91 0)
           (list 10 30.83333333 4.09333333)
           (cons 40 0)
           (cons 41 0)
           (cons 42 0)
           (cons 91 0)
           (list 10 31.3 4.25)
           (cons 40 0)
           (cons 41 0)
           (cons 42 0)
           (cons 91 0)
           (list 10 33.7 4.25)
           (cons 40 0)
           (cons 41 0)
           (cons 42 0)
           (cons 91 0)
           (list 10 34.16666667 4.09333333)
           (cons 40 0)
           (cons 41 0)
           (cons 42 0)
           (cons 91 0)
           (list 10 34.16666667 3.57333333)
           (cons 40 0)
           (cons 41 0)
           (cons 42 0)
           (cons 91 0)
           (list 10 33.7 3.41666667)
           (cons 40 0)
           (cons 41 0)
           (cons 42 0)
           (cons 91 0)
           (list 10 31.3 3.41666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 34.83333333 -4.09333333)
           (cons 40 0)
           (cons 41 0)
           (cons 42 0)
           (cons 91 0)
           (list 10 34.83333333 -3.57333333)
           (cons 40 0)
           (cons 41 0)
           (cons 42 0)
           (cons 91 0)
           (list 10 35.3 -3.41666667)
           (cons 40 0)
           (cons 41 0)
           (cons 42 0)
           (cons 91 0)
           (list 10 37.7 -3.41666667)
           (cons 40 0)
           (cons 41 0)
           (cons 42 0)
           (cons 91 0)
           (list 10 38.16666667 -3.57333333)
           (cons 40 0)
           (cons 41 0)
           (cons 42 0)
           (cons 91 0)
           (list 10 38.16666667 -4.09333333)
           (cons 40 0)
           (cons 41 0)
           (cons 42 0)
           (cons 91 0)
           (list 10 37.7 -4.25)
           (cons 40 0)
           (cons 41 0)
           (cons 42 0)
           (cons 91 0)
           (list 10 35.3 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 34.83333333 3.57333333)
           (cons 40 0)
           (cons 41 0)
           (cons 42 0)
           (cons 91 0)
           (list 10 34.83333333 4.09333333)
           (cons 40 0)
           (cons 41 0)
           (cons 42 0)
           (cons 91 0)
           (list 10 35.3 4.25)
           (cons 40 0)
           (cons 41 0)
           (cons 42 0)
           (cons 91 0)
           (list 10 37.7 4.25)
           (cons 40 0)
           (cons 41 0)
           (cons 42 0)
           (cons 91 0)
           (list 10 38.16666667 4.09333333)
           (cons 40 0)
           (cons 41 0)
           (cons 42 0)
           (cons 91 0)
           (list 10 38.16666667 3.57333333)
           (cons 40 0)
           (cons 41 0)
           (cons 42 0)
           (cons 91 0)
           (list 10 37.7 3.41666667)
           (cons 40 0)
           (cons 41 0)
           (cons 42 0)
           (cons 91 0)
           (list 10 35.3 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4.25 0)
           (cons 50 0)
          )
         )
         (entmake
          (list
           (cons 0 "POINT")
           (cons 100 "AcDbEntity")
           (cons 67 0)
           (cons 8 "0")
           (cons 100 "AcDbPoint")
           (list 10 0 4.25 0)
           (cons 50 0)
          )
         )
         (entmake
          (list
           (cons 0 "POINT")
           (cons 100 "AcDbEntity")
           (cons 67 0)
           (cons 8 "0")
           (cons 100 "AcDbPoint")
           (list 10 6.2 4.25 0)
           (cons 50 0)
          )
         )
         (entmake
          (list
           (cons 0 "POINT")
           (cons 100 "AcDbEntity")
           (cons 67 0)
           (cons 8 "0")
           (cons 100 "AcDbPoint")
           (list 10 6.2 -4.25 0)
           (cons 50 0)
          )
         )
         (entmake
          (list
           (cons 0 "POINT")
           (cons 100 "AcDbEntity")
           (cons 67 0)
           (cons 8 "0")
           (cons 100 "AcDbPoint")
           (list 10 45.5 4.25 0)
           (cons 50 0)
          )
         )
         (entmake
          (list
           (cons 0 "POINT")
           (cons 100 "AcDbEntity")
           (cons 67 0)
           (cons 8 "0")
           (cons 100 "AcDbPoint")
           (list 10 45.5 -4.25 0)
           (cons 50 0)
          )
         )
         (entmake
          (list
           (cons 0 "POINT")
           (cons 100 "AcDbEntity")
           (cons 67 0)
           (cons 8 "0")
           (cons 100 "AcDbPoint")
           (list 10 6.2 0 0)
           (cons 50 0)
          )
         )
         (entmake
          (list
           (cons 0 "POINT")
           (cons 100 "AcDbEntity")
           (cons 67 0)
           (cons 8 "0")
           (cons 100 "AcDbPoint")
           (list 10 34.5 -4.25 0)
           (cons 50 0)
          )
         )
         (entmake
          (list
           (cons 0 "POINT")
           (cons 100 "AcDbEntity")
           (cons 67 0)
           (cons 8 "0")
           (cons 100 "AcDbPoint")
           (list 10 34.5 4.25 0)
           (cons 50 0)
          )
         )
         (entmake
          (list
           (cons 0 "INSERT")
           (cons 100 "AcDbEntity")
           (cons 67 0)
           (cons 8 "0")
           (cons 100 "AcDbBlockReference")
           (cons 2 "WheelRight2")
           (list 10 6.2 3.41666667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeft2")
           (list 10 6.2 -3.41666667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 3.90341207 1.85914261 0)
           (cons 40 0.65616798)
           (cons 1 "6.200")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 3.90341207 0.76552931 0)
           (cons 40 0.65616798)
           (cons 1 "6.200")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 3.90341207 -0.32808399 0)
           (cons 40 0.65616798)
           (cons 1 "34.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 3.90341207 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 3.90341207 -2.51531059 0)
           (cons 40 0.65616798)
           (cons 1 "45.2")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-BUS-40"))
        (progn
         (entmake)
         (entmake
          (list
           (cons 0 "BLOCK")
           (cons 2 "AASHTO-2011-BUS-40")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 -4.25)
           (cons 40 0)
           (cons 41 0)
           (cons 42 0)
           (cons 91 0)
           (list 10 40.5 -4.25)
           (cons 40 0)
           (cons 41 0)
           (cons 42 0)
           (cons 91 0)
           (list 10 40.5 4.25)
           (cons 40 0)
           (cons 41 0)
           (cons 42 0)
           (cons 91 0)
           (list 10 0 4.25)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 40.5 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 40.5 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 27.83333333 -2.59333333)
           (cons 40 0)
           (cons 41 0)
           (cons 42 0)
           (cons 91 0)
           (list 10 27.83333333 -2.07333333)
           (cons 40 0)
           (cons 41 0)
           (cons 42 0)
           (cons 91 0)
           (list 10 28.3 -1.91666667)
           (cons 40 0)
           (cons 41 0)
           (cons 42 0)
           (cons 91 0)
           (list 10 30.7 -1.91666667)
           (cons 40 0)
           (cons 41 0)
           (cons 42 0)
           (cons 91 0)
           (list 10 31.16666667 -2.07333333)
           (cons 40 0)
           (cons 41 0)
           (cons 42 0)
           (cons 91 0)
           (list 10 31.16666667 -2.59333333)
           (cons 40 0)
           (cons 41 0)
           (cons 42 0)
           (cons 91 0)
           (list 10 30.7 -2.75)
           (cons 40 0)
           (cons 41 0)
           (cons 42 0)
           (cons 91 0)
           (list 10 28.3 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 27.83333333 -4.09333333)
           (cons 40 0)
           (cons 41 0)
           (cons 42 0)
           (cons 91 0)
           (list 10 27.83333333 -3.57333333)
           (cons 40 0)
           (cons 41 0)
           (cons 42 0)
           (cons 91 0)
           (list 10 28.3 -3.41666667)
           (cons 40 0)
           (cons 41 0)
           (cons 42 0)
           (cons 91 0)
           (list 10 30.7 -3.41666667)
           (cons 40 0)
           (cons 41 0)
           (cons 42 0)
           (cons 91 0)
           (list 10 31.16666667 -3.57333333)
           (cons 40 0)
           (cons 41 0)
           (cons 42 0)
           (cons 91 0)
           (list 10 31.16666667 -4.09333333)
           (cons 40 0)
           (cons 41 0)
           (cons 42 0)
           (cons 91 0)
           (list 10 30.7 -4.25)
           (cons 40 0)
           (cons 41 0)
           (cons 42 0)
           (cons 91 0)
           (list 10 28.3 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 27.83333333 2.07333333)
           (cons 40 0)
           (cons 41 0)
           (cons 42 0)
           (cons 91 0)
           (list 10 27.83333333 2.59333333)
           (cons 40 0)
           (cons 41 0)
           (cons 42 0)
           (cons 91 0)
           (list 10 28.3 2.75)
           (cons 40 0)
           (cons 41 0)
           (cons 42 0)
           (cons 91 0)
           (list 10 30.7 2.75)
           (cons 40 0)
           (cons 41 0)
           (cons 42 0)
           (cons 91 0)
           (list 10 31.16666667 2.59333333)
           (cons 40 0)
           (cons 41 0)
           (cons 42 0)
           (cons 91 0)
           (list 10 31.16666667 2.07333333)
           (cons 40 0)
           (cons 41 0)
           (cons 42 0)
           (cons 91 0)
           (list 10 30.7 1.91666667)
           (cons 40 0)
           (cons 41 0)
           (cons 42 0)
           (cons 91 0)
           (list 10 28.3 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 27.83333333 3.57333333)
           (cons 40 0)
           (cons 41 0)
           (cons 42 0)
           (cons 91 0)
           (list 10 27.83333333 4.09333333)
           (cons 40 0)
           (cons 41 0)
           (cons 42 0)
           (cons 91 0)
           (list 10 28.3 4.25)
           (cons 40 0)
           (cons 41 0)
           (cons 42 0)
           (cons 91 0)
           (list 10 30.7 4.25)
           (cons 40 0)
           (cons 41 0)
           (cons 42 0)
           (cons 91 0)
           (list 10 31.16666667 4.09333333)
           (cons 40 0)
           (cons 41 0)
           (cons 42 0)
           (cons 91 0)
           (list 10 31.16666667 3.57333333)
           (cons 40 0)
           (cons 41 0)
           (cons 42 0)
           (cons 91 0)
           (list 10 30.7 3.41666667)
           (cons 40 0)
           (cons 41 0)
           (cons 42 0)
           (cons 91 0)
           (list 10 28.3 3.41666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 31.83333333 -2.59333333)
           (cons 40 0)
           (cons 41 0)
           (cons 42 0)
           (cons 91 0)
           (list 10 31.83333333 -2.07333333)
           (cons 40 0)
           (cons 41 0)
           (cons 42 0)
           (cons 91 0)
           (list 10 32.3 -1.91666667)
           (cons 40 0)
           (cons 41 0)
           (cons 42 0)
           (cons 91 0)
           (list 10 34.7 -1.91666667)
           (cons 40 0)
           (cons 41 0)
           (cons 42 0)
           (cons 91 0)
           (list 10 35.16666667 -2.07333333)
           (cons 40 0)
           (cons 41 0)
           (cons 42 0)
           (cons 91 0)
           (list 10 35.16666667 -2.59333333)
           (cons 40 0)
           (cons 41 0)
           (cons 42 0)
           (cons 91 0)
           (list 10 34.7 -2.75)
           (cons 40 0)
           (cons 41 0)
           (cons 42 0)
           (cons 91 0)
           (list 10 32.3 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 31.83333333 -4.09333333)
           (cons 40 0)
           (cons 41 0)
           (cons 42 0)
           (cons 91 0)
           (list 10 31.83333333 -3.57333333)
           (cons 40 0)
           (cons 41 0)
           (cons 42 0)
           (cons 91 0)
           (list 10 32.3 -3.41666667)
           (cons 40 0)
           (cons 41 0)
           (cons 42 0)
           (cons 91 0)
           (list 10 34.7 -3.41666667)
           (cons 40 0)
           (cons 41 0)
           (cons 42 0)
           (cons 91 0)
           (list 10 35.16666667 -3.57333333)
           (cons 40 0)
           (cons 41 0)
           (cons 42 0)
           (cons 91 0)
           (list 10 35.16666667 -4.09333333)
           (cons 40 0)
           (cons 41 0)
           (cons 42 0)
           (cons 91 0)
           (list 10 34.7 -4.25)
           (cons 40 0)
           (cons 41 0)
           (cons 42 0)
           (cons 91 0)
           (list 10 32.3 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 31.83333333 2.07333333)
           (cons 40 0)
           (cons 41 0)
           (cons 42 0)
           (cons 91 0)
           (list 10 31.83333333 2.59333333)
           (cons 40 0)
           (cons 41 0)
           (cons 42 0)
           (cons 91 0)
           (list 10 32.3 2.75)
           (cons 40 0)
           (cons 41 0)
           (cons 42 0)
           (cons 91 0)
           (list 10 34.7 2.75)
           (cons 40 0)
           (cons 41 0)
           (cons 42 0)
           (cons 91 0)
           (list 10 35.16666667 2.59333333)
           (cons 40 0)
           (cons 41 0)
           (cons 42 0)
           (cons 91 0)
           (list 10 35.16666667 2.07333333)
           (cons 40 0)
           (cons 41 0)
           (cons 42 0)
           (cons 91 0)
           (list 10 34.7 1.91666667)
           (cons 40 0)
           (cons 41 0)
           (cons 42 0)
           (cons 91 0)
           (list 10 32.3 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 31.83333333 3.57333333)
           (cons 40 0)
           (cons 41 0)
           (cons 42 0)
           (cons 91 0)
           (list 10 31.83333333 4.09333333)
           (cons 40 0)
           (cons 41 0)
           (cons 42 0)
           (cons 91 0)
           (list 10 32.3 4.25)
           (cons 40 0)
           (cons 41 0)
           (cons 42 0)
           (cons 91 0)
           (list 10 34.7 4.25)
           (cons 40 0)
           (cons 41 0)
           (cons 42 0)
           (cons 91 0)
           (list 10 35.16666667 4.09333333)
           (cons 40 0)
           (cons 41 0)
           (cons 42 0)
           (cons 91 0)
           (list 10 35.16666667 3.57333333)
           (cons 40 0)
           (cons 41 0)
           (cons 42 0)
           (cons 91 0)
           (list 10 34.7 3.41666667)
           (cons 40 0)
           (cons 41 0)
           (cons 42 0)
           (cons 91 0)
           (list 10 32.3 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4.25 0)
           (cons 50 0)
          )
         )
         (entmake
          (list
           (cons 0 "POINT")
           (cons 100 "AcDbEntity")
           (cons 67 0)
           (cons 8 "0")
           (cons 100 "AcDbPoint")
           (list 10 0 4.25 0)
           (cons 50 0)
          )
         )
         (entmake
          (list
           (cons 0 "POINT")
           (cons 100 "AcDbEntity")
           (cons 67 0)
           (cons 8 "0")
           (cons 100 "AcDbPoint")
           (list 10 40.5 4.25 0)
           (cons 50 0)
          )
         )
         (entmake
          (list
           (cons 0 "POINT")
           (cons 100 "AcDbEntity")
           (cons 67 0)
           (cons 8 "0")
           (cons 100 "AcDbPoint")
           (list 10 40.5 -4.25 0)
           (cons 50 0)
          )
         )
         (entmake
          (list
           (cons 0 "POINT")
           (cons 100 "AcDbEntity")
           (cons 67 0)
           (cons 8 "0")
           (cons 100 "AcDbPoint")
           (list 10 6.3 -4.25 0)
           (cons 50 0)
          )
         )
         (entmake
          (list
           (cons 0 "POINT")
           (cons 100 "AcDbEntity")
           (cons 67 0)
           (cons 8 "0")
           (cons 100 "AcDbPoint")
           (list 10 6.3 4.25 0)
           (cons 50 0)
          )
         )
         (entmake
          (list
           (cons 0 "POINT")
           (cons 100 "AcDbEntity")
           (cons 67 0)
           (cons 8 "0")
           (cons 100 "AcDbPoint")
           (list 10 6.3 0 0)
           (cons 50 0)
          )
         )
         (entmake
          (list
           (cons 0 "POINT")
           (cons 100 "AcDbEntity")
           (cons 67 0)
           (cons 8 "0")
           (cons 100 "AcDbPoint")
           (list 10 31.5 -4.25 0)
           (cons 50 0)
          )
         )
         (entmake
          (list
           (cons 0 "POINT")
           (cons 100 "AcDbEntity")
           (cons 67 0)
           (cons 8 "0")
           (cons 100 "AcDbPoint")
           (list 10 31.5 4.25 0)
           (cons 50 0)
          )
         )
         (entmake
          (list
           (cons 0 "INSERT")
           (cons 100 "AcDbEntity")
           (cons 67 0)
           (cons 8 "0")
           (cons 100 "AcDbBlockReference")
           (cons 2 "WheelLeft2")
           (list 10 6.3 -3.41666667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRight2")
           (list 10 6.3 3.41666667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 4.00341207 1.85914261 0)
           (cons 40 0.65616798)
           (cons 1 "6.300")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 4.00341207 0.76552931 0)
           (cons 40 0.65616798)
           (cons 1 "6.300")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 4.00341207 -0.32808399 0)
           (cons 40 0.65616798)
           (cons 1 "31.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 4.00341207 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 4.00341207 -2.51531059 0)
           (cons 40 0.65616798)
           (cons 1 "41.9")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-A-BUS-REAR"))
        (progn
         (entmake)
         (entmake
          (list
           (cons 0 "BLOCK")
           (cons 2 "AASHTO-2011-A-BUS-REAR")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 5)
           (cons 70 129)
           (cons 43 0)
           (cons 38 0)
           (cons 39 0)
           (list 10 0 0)
           (cons 40 0)
           (cons 41 0)
           (cons 42 0)
           (cons 91 0)
           (list 10 2 4.25)
           (cons 40 0)
           (cons 41 0)
           (cons 42 0)
           (cons 91 0)
           (list 10 23.2 4.25)
           (cons 40 0)
           (cons 41 0)
           (cons 42 0)
           (cons 91 0)
           (list 10 23.2 -4.25)
           (cons 40 0)
           (cons 41 0)
           (cons 42 0)
           (cons 91 0)
           (list 10 2 -4.25)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 23.2 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 23.2 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2 -4.25 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 2 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.56666667)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.53333333 -4.09333333)
           (cons 40 0)
           (cons 41 0)
           (cons 42 0)
           (cons 91 0)
           (list 10 11.53333333 -3.57333333)
           (cons 40 0)
           (cons 41 0)
           (cons 42 0)
           (cons 91 0)
           (list 10 12 -3.41666667)
           (cons 40 0)
           (cons 41 0)
           (cons 42 0)
           (cons 91 0)
           (list 10 14.4 -3.41666667)
           (cons 40 0)
           (cons 41 0)
           (cons 42 0)
           (cons 91 0)
           (list 10 14.86666667 -3.57333333)
           (cons 40 0)
           (cons 41 0)
           (cons 42 0)
           (cons 91 0)
           (list 10 14.86666667 -4.09333333)
           (cons 40 0)
           (cons 41 0)
           (cons 42 0)
           (cons 91 0)
           (list 10 14.4 -4.25)
           (cons 40 0)
           (cons 41 0)
           (cons 42 0)
           (cons 91 0)
           (list 10 12 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.53333333 3.57333333)
           (cons 40 0)
           (cons 41 0)
           (cons 42 0)
           (cons 91 0)
           (list 10 11.53333333 4.09333333)
           (cons 40 0)
           (cons 41 0)
           (cons 42 0)
           (cons 91 0)
           (list 10 12 4.25)
           (cons 40 0)
           (cons 41 0)
           (cons 42 0)
           (cons 91 0)
           (list 10 14.4 4.25)
           (cons 40 0)
           (cons 41 0)
           (cons 42 0)
           (cons 91 0)
           (list 10 14.86666667 4.09333333)
           (cons 40 0)
           (cons 41 0)
           (cons 42 0)
           (cons 91 0)
           (list 10 14.86666667 3.57333333)
           (cons 40 0)
           (cons 41 0)
           (cons 42 0)
           (cons 91 0)
           (list 10 14.4 3.41666667)
           (cons 40 0)
           (cons 41 0)
           (cons 42 0)
           (cons 91 0)
           (list 10 12 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 13.2 -4.25 0)
           (cons 50 0)
          )
         )
         (entmake
          (list
           (cons 0 "POINT")
           (cons 100 "AcDbEntity")
           (cons 67 0)
           (cons 8 "0")
           (cons 100 "AcDbPoint")
           (list 10 13.2 4.25 0)
           (cons 50 0)
          )
         )
         (entmake
          (list
           (cons 0 "POINT")
           (cons 100 "AcDbEntity")
           (cons 67 0)
           (cons 8 "0")
           (cons 100 "AcDbPoint")
           (list 10 2 4.25 0)
           (cons 50 0)
          )
         )
         (entmake
          (list
           (cons 0 "POINT")
           (cons 100 "AcDbEntity")
           (cons 67 0)
           (cons 8 "0")
           (cons 100 "AcDbPoint")
           (list 10 23.2 4.25 0)
           (cons 50 0)
          )
         )
         (entmake
          (list
           (cons 0 "POINT")
           (cons 100 "AcDbEntity")
           (cons 67 0)
           (cons 8 "0")
           (cons 100 "AcDbPoint")
           (list 10 23.2 -4.25 0)
           (cons 50 0)
          )
         )
         (entmake
          (list
           (cons 0 "POINT")
           (cons 100 "AcDbEntity")
           (cons 67 0)
           (cons 8 "0")
           (cons 100 "AcDbPoint")
           (list 10 2 -4.25 0)
           (cons 50 0)
          )
         )
         (entmake
          (list
           (cons 0 "ATTDEF")
           (cons 100 "AcDbEntity")
           (cons 67 0)
           (cons 8 "0")
           (cons 100 "AcDbText")
           (list 10 -2.29658793 1.85914261 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 0.76552931 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -0.32808399 0)
           (cons 40 0.65616798)
           (cons 1 "13.200")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-A-BUS-FRONT"))
        (progn
         (entmake)
         (entmake
          (list
           (cons 0 "BLOCK")
           (cons 2 "AASHTO-2011-A-BUS-FRONT")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 5)
           (cons 70 129)
           (cons 43 0)
           (cons 38 0)
           (cons 39 0)
           (list 10 0 4.25)
           (cons 40 0)
           (cons 41 0)
           (cons 42 0)
           (cons 91 0)
           (list 10 34.8 4.25)
           (cons 40 0)
           (cons 41 0)
           (cons 42 0)
           (cons 91 0)
           (list 10 36.8 0)
           (cons 40 0)
           (cons 41 0)
           (cons 42 0)
           (cons 91 0)
           (list 10 34.8 -4.25)
           (cons 40 0)
           (cons 41 0)
           (cons 42 0)
           (cons 91 0)
           (list 10 0 -4.25)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 34.8 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 34.8 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 34.8 0 0)
           (list 11 36.8 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 36.8 0 0)
           (cons 40 0.33333333)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 28.93333333 -4.09333333)
           (cons 40 0)
           (cons 41 0)
           (cons 42 0)
           (cons 91 0)
           (list 10 28.93333333 -3.57333333)
           (cons 40 0)
           (cons 41 0)
           (cons 42 0)
           (cons 91 0)
           (list 10 29.4 -3.41666667)
           (cons 40 0)
           (cons 41 0)
           (cons 42 0)
           (cons 91 0)
           (list 10 31.8 -3.41666667)
           (cons 40 0)
           (cons 41 0)
           (cons 42 0)
           (cons 91 0)
           (list 10 32.26666667 -3.57333333)
           (cons 40 0)
           (cons 41 0)
           (cons 42 0)
           (cons 91 0)
           (list 10 32.26666667 -4.09333333)
           (cons 40 0)
           (cons 41 0)
           (cons 42 0)
           (cons 91 0)
           (list 10 31.8 -4.25)
           (cons 40 0)
           (cons 41 0)
           (cons 42 0)
           (cons 91 0)
           (list 10 29.4 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 28.93333333 3.57333333)
           (cons 40 0)
           (cons 41 0)
           (cons 42 0)
           (cons 91 0)
           (list 10 28.93333333 4.09333333)
           (cons 40 0)
           (cons 41 0)
           (cons 42 0)
           (cons 91 0)
           (list 10 29.4 4.25)
           (cons 40 0)
           (cons 41 0)
           (cons 42 0)
           (cons 91 0)
           (list 10 31.8 4.25)
           (cons 40 0)
           (cons 41 0)
           (cons 42 0)
           (cons 91 0)
           (list 10 32.26666667 4.09333333)
           (cons 40 0)
           (cons 41 0)
           (cons 42 0)
           (cons 91 0)
           (list 10 32.26666667 3.57333333)
           (cons 40 0)
           (cons 41 0)
           (cons 42 0)
           (cons 91 0)
           (list 10 31.8 3.41666667)
           (cons 40 0)
           (cons 41 0)
           (cons 42 0)
           (cons 91 0)
           (list 10 29.4 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 8.6 0 0)
           (cons 50 0)
          )
         )
         (entmake
          (list
           (cons 0 "POINT")
           (cons 100 "AcDbEntity")
           (cons 67 0)
           (cons 8 "0")
           (cons 100 "AcDbPoint")
           (list 10 0 -4.25 0)
           (cons 50 0)
          )
         )
         (entmake
          (list
           (cons 0 "POINT")
           (cons 100 "AcDbEntity")
           (cons 67 0)
           (cons 8 "0")
           (cons 100 "AcDbPoint")
           (list 10 0 4.25 0)
           (cons 50 0)
          )
         )
         (entmake
          (list
           (cons 0 "POINT")
           (cons 100 "AcDbEntity")
           (cons 67 0)
           (cons 8 "0")
           (cons 100 "AcDbPoint")
           (list 10 30.6 4.25 0)
           (cons 50 0)
          )
         )
         (entmake
          (list
           (cons 0 "POINT")
           (cons 100 "AcDbEntity")
           (cons 67 0)
           (cons 8 "0")
           (cons 100 "AcDbPoint")
           (list 10 30.6 -4.25 0)
           (cons 50 0)
          )
         )
         (entmake
          (list
           (cons 0 "POINT")
           (cons 100 "AcDbEntity")
           (cons 67 0)
           (cons 8 "0")
           (cons 100 "AcDbPoint")
           (list 10 8.6 -4.25 0)
           (cons 50 0)
          )
         )
         (entmake
          (list
           (cons 0 "POINT")
           (cons 100 "AcDbEntity")
           (cons 67 0)
           (cons 8 "0")
           (cons 100 "AcDbPoint")
           (list 10 8.6 4.25 0)
           (cons 50 0)
          )
         )
         (entmake
          (list
           (cons 0 "POINT")
           (cons 100 "AcDbEntity")
           (cons 67 0)
           (cons 8 "0")
           (cons 100 "AcDbPoint")
           (list 10 36.8 0 0)
           (cons 50 0)
          )
         )
         (entmake
          (list
           (cons 0 "INSERT")
           (cons 100 "AcDbEntity")
           (cons 67 0)
           (cons 8 "0")
           (cons 100 "AcDbBlockReference")
           (cons 2 "WheelLeft2")
           (list 10 8.6 -3.41666667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRight2")
           (list 10 8.6 3.41666667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 6.30341207 1.85914261 0)
           (cons 40 0.65616798)
           (cons 1 "8.500")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 6.30341207 0.76552931 0)
           (cons 40 0.65616798)
           (cons 1 "8.500")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 6.30341207 -0.32808399 0)
           (cons 40 0.65616798)
           (cons 1 "30.600")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 6.30341207 -1.42169729 0)
           (cons 40 0.65616798)
           (cons 1 "36.800")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 6.30341207 -2.51531059 0)
           (cons 40 0.65616798)
           (cons 1 "38.3")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-36-TRAILER2"))
        (progn
         (entmake)
         (entmake
          (list
           (cons 0 "BLOCK")
           (cons 2 "AB_INF-WB-36-TRAILER2")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 -1.3)
           (cons 40 0)
           (cons 41 0)
           (cons 42 0)
           (cons 91 0)
           (list 10 16.2 -1.3)
           (cons 40 0)
           (cons 41 0)
           (cons 42 0)
           (cons 91 0)
           (list 10 16.2 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 16.2 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 16.2 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.3062 -0.7445528)
           (cons 40 0)
           (cons 41 0)
           (cons 42 0)
           (cons 91 0)
           (list 10 13.3062 -0.5702072)
           (cons 40 0)
           (cons 41 0)
           (cons 42 0)
           (cons 91 0)
           (list 10 13.462664 -0.51768)
           (cons 40 0)
           (cons 41 0)
           (cons 42 0)
           (cons 91 0)
           (list 10 14.267336 -0.51768)
           (cons 40 0)
           (cons 41 0)
           (cons 42 0)
           (cons 91 0)
           (list 10 14.4238 -0.5702072)
           (cons 40 0)
           (cons 41 0)
           (cons 42 0)
           (cons 91 0)
           (list 10 14.4238 -0.7445528)
           (cons 40 0)
           (cons 41 0)
           (cons 42 0)
           (cons 91 0)
           (list 10 14.267336 -0.79708)
           (cons 40 0)
           (cons 41 0)
           (cons 42 0)
           (cons 91 0)
           (list 10 13.462664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.3062 -1.2474728)
           (cons 40 0)
           (cons 41 0)
           (cons 42 0)
           (cons 91 0)
           (list 10 13.3062 -1.0731272)
           (cons 40 0)
           (cons 41 0)
           (cons 42 0)
           (cons 91 0)
           (list 10 13.462664 -1.0206)
           (cons 40 0)
           (cons 41 0)
           (cons 42 0)
           (cons 91 0)
           (list 10 14.267336 -1.0206)
           (cons 40 0)
           (cons 41 0)
           (cons 42 0)
           (cons 91 0)
           (list 10 14.4238 -1.0731272)
           (cons 40 0)
           (cons 41 0)
           (cons 42 0)
           (cons 91 0)
           (list 10 14.4238 -1.2474728)
           (cons 40 0)
           (cons 41 0)
           (cons 42 0)
           (cons 91 0)
           (list 10 14.267336 -1.3)
           (cons 40 0)
           (cons 41 0)
           (cons 42 0)
           (cons 91 0)
           (list 10 13.462664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.3062 0.5702072)
           (cons 40 0)
           (cons 41 0)
           (cons 42 0)
           (cons 91 0)
           (list 10 13.3062 0.7445528)
           (cons 40 0)
           (cons 41 0)
           (cons 42 0)
           (cons 91 0)
           (list 10 13.462664 0.79708)
           (cons 40 0)
           (cons 41 0)
           (cons 42 0)
           (cons 91 0)
           (list 10 14.267336 0.79708)
           (cons 40 0)
           (cons 41 0)
           (cons 42 0)
           (cons 91 0)
           (list 10 14.4238 0.7445528)
           (cons 40 0)
           (cons 41 0)
           (cons 42 0)
           (cons 91 0)
           (list 10 14.4238 0.5702072)
           (cons 40 0)
           (cons 41 0)
           (cons 42 0)
           (cons 91 0)
           (list 10 14.267336 0.51768)
           (cons 40 0)
           (cons 41 0)
           (cons 42 0)
           (cons 91 0)
           (list 10 13.462664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.3062 1.0731272)
           (cons 40 0)
           (cons 41 0)
           (cons 42 0)
           (cons 91 0)
           (list 10 13.3062 1.2474728)
           (cons 40 0)
           (cons 41 0)
           (cons 42 0)
           (cons 91 0)
           (list 10 13.462664 1.3)
           (cons 40 0)
           (cons 41 0)
           (cons 42 0)
           (cons 91 0)
           (list 10 14.267336 1.3)
           (cons 40 0)
           (cons 41 0)
           (cons 42 0)
           (cons 91 0)
           (list 10 14.4238 1.2474728)
           (cons 40 0)
           (cons 41 0)
           (cons 42 0)
           (cons 91 0)
           (list 10 14.4238 1.0731272)
           (cons 40 0)
           (cons 41 0)
           (cons 42 0)
           (cons 91 0)
           (list 10 14.267336 1.0206)
           (cons 40 0)
           (cons 41 0)
           (cons 42 0)
           (cons 91 0)
           (list 10 13.462664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.5762 -0.7445528)
           (cons 40 0)
           (cons 41 0)
           (cons 42 0)
           (cons 91 0)
           (list 10 14.5762 -0.5702072)
           (cons 40 0)
           (cons 41 0)
           (cons 42 0)
           (cons 91 0)
           (list 10 14.732664 -0.51768)
           (cons 40 0)
           (cons 41 0)
           (cons 42 0)
           (cons 91 0)
           (list 10 15.537336 -0.51768)
           (cons 40 0)
           (cons 41 0)
           (cons 42 0)
           (cons 91 0)
           (list 10 15.6938 -0.5702072)
           (cons 40 0)
           (cons 41 0)
           (cons 42 0)
           (cons 91 0)
           (list 10 15.6938 -0.7445528)
           (cons 40 0)
           (cons 41 0)
           (cons 42 0)
           (cons 91 0)
           (list 10 15.537336 -0.79708)
           (cons 40 0)
           (cons 41 0)
           (cons 42 0)
           (cons 91 0)
           (list 10 14.732664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.5762 -1.2474728)
           (cons 40 0)
           (cons 41 0)
           (cons 42 0)
           (cons 91 0)
           (list 10 14.5762 -1.0731272)
           (cons 40 0)
           (cons 41 0)
           (cons 42 0)
           (cons 91 0)
           (list 10 14.732664 -1.0206)
           (cons 40 0)
           (cons 41 0)
           (cons 42 0)
           (cons 91 0)
           (list 10 15.537336 -1.0206)
           (cons 40 0)
           (cons 41 0)
           (cons 42 0)
           (cons 91 0)
           (list 10 15.6938 -1.0731272)
           (cons 40 0)
           (cons 41 0)
           (cons 42 0)
           (cons 91 0)
           (list 10 15.6938 -1.2474728)
           (cons 40 0)
           (cons 41 0)
           (cons 42 0)
           (cons 91 0)
           (list 10 15.537336 -1.3)
           (cons 40 0)
           (cons 41 0)
           (cons 42 0)
           (cons 91 0)
           (list 10 14.732664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.5762 0.5702072)
           (cons 40 0)
           (cons 41 0)
           (cons 42 0)
           (cons 91 0)
           (list 10 14.5762 0.7445528)
           (cons 40 0)
           (cons 41 0)
           (cons 42 0)
           (cons 91 0)
           (list 10 14.732664 0.79708)
           (cons 40 0)
           (cons 41 0)
           (cons 42 0)
           (cons 91 0)
           (list 10 15.537336 0.79708)
           (cons 40 0)
           (cons 41 0)
           (cons 42 0)
           (cons 91 0)
           (list 10 15.6938 0.7445528)
           (cons 40 0)
           (cons 41 0)
           (cons 42 0)
           (cons 91 0)
           (list 10 15.6938 0.5702072)
           (cons 40 0)
           (cons 41 0)
           (cons 42 0)
           (cons 91 0)
           (list 10 15.537336 0.51768)
           (cons 40 0)
           (cons 41 0)
           (cons 42 0)
           (cons 91 0)
           (list 10 14.732664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.5762 1.0731272)
           (cons 40 0)
           (cons 41 0)
           (cons 42 0)
           (cons 91 0)
           (list 10 14.5762 1.2474728)
           (cons 40 0)
           (cons 41 0)
           (cons 42 0)
           (cons 91 0)
           (list 10 14.732664 1.3)
           (cons 40 0)
           (cons 41 0)
           (cons 42 0)
           (cons 91 0)
           (list 10 15.537336 1.3)
           (cons 40 0)
           (cons 41 0)
           (cons 42 0)
           (cons 91 0)
           (list 10 15.6938 1.2474728)
           (cons 40 0)
           (cons 41 0)
           (cons 42 0)
           (cons 91 0)
           (list 10 15.6938 1.0731272)
           (cons 40 0)
           (cons 41 0)
           (cons 42 0)
           (cons 91 0)
           (list 10 15.537336 1.0206)
           (cons 40 0)
           (cons 41 0)
           (cons 42 0)
           (cons 91 0)
           (list 10 14.732664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 2 0 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 16.2 -1.3 0)
           (cons 50 0)
          )
         )
         (entmake
          (list
           (cons 0 "POINT")
           (cons 100 "AcDbEntity")
           (cons 67 0)
           (cons 8 "0")
           (cons 100 "AcDbPoint")
           (list 10 16.2 1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 14.5 1.3 0)
           (cons 50 0)
          )
         )
         (entmake
          (list
           (cons 0 "POINT")
           (cons 100 "AcDbEntity")
           (cons 67 0)
           (cons 8 "0")
           (cons 100 "AcDbPoint")
           (list 10 14.5 -1.3 0)
           (cons 50 0)
          )
         )
         (entmake
          (list
           (cons 0 "ATTDEF")
           (cons 100 "AcDbEntity")
           (cons 67 0)
           (cons 8 "0")
           (cons 100 "AcDbText")
           (list 10 1.3 0.56666667 0)
           (cons 40 0.2)
           (cons 1 "2.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.3 0.23333333 0)
           (cons 40 0.2)
           (cons 1 "2.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.3 -0.1 0)
           (cons 40 0.2)
           (cons 1 "14.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.3 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.3 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-36-PUP"))
        (progn
         (entmake)
         (entmake
          (list
           (cons 0 "BLOCK")
           (cons 2 "AB_INF-WB-36-PUP")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 3)
           (cons 70 129)
           (cons 43 0)
           (cons 38 0)
           (cons 39 0)
           (list 10 0 0)
           (cons 40 0)
           (cons 41 0)
           (cons 42 0)
           (cons 91 0)
           (list 10 3.7 -1.3)
           (cons 40 0)
           (cons 41 0)
           (cons 42 0)
           (cons 91 0)
           (list 10 3.7 1.3)
           (cons 40 0)
           (cons 41 0)
           (cons 42 0)
           (cons 91 0)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 3.7 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.1412 -0.7445528)
           (cons 40 0)
           (cons 41 0)
           (cons 42 0)
           (cons 91 0)
           (list 10 3.1412 -0.5702072)
           (cons 40 0)
           (cons 41 0)
           (cons 42 0)
           (cons 91 0)
           (list 10 3.297664 -0.51768)
           (cons 40 0)
           (cons 41 0)
           (cons 42 0)
           (cons 91 0)
           (list 10 4.102336 -0.51768)
           (cons 40 0)
           (cons 41 0)
           (cons 42 0)
           (cons 91 0)
           (list 10 4.2588 -0.5702072)
           (cons 40 0)
           (cons 41 0)
           (cons 42 0)
           (cons 91 0)
           (list 10 4.2588 -0.7445528)
           (cons 40 0)
           (cons 41 0)
           (cons 42 0)
           (cons 91 0)
           (list 10 4.102336 -0.79708)
           (cons 40 0)
           (cons 41 0)
           (cons 42 0)
           (cons 91 0)
           (list 10 3.297664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.1412 -1.2474728)
           (cons 40 0)
           (cons 41 0)
           (cons 42 0)
           (cons 91 0)
           (list 10 3.1412 -1.0731272)
           (cons 40 0)
           (cons 41 0)
           (cons 42 0)
           (cons 91 0)
           (list 10 3.297664 -1.0206)
           (cons 40 0)
           (cons 41 0)
           (cons 42 0)
           (cons 91 0)
           (list 10 4.102336 -1.0206)
           (cons 40 0)
           (cons 41 0)
           (cons 42 0)
           (cons 91 0)
           (list 10 4.2588 -1.0731272)
           (cons 40 0)
           (cons 41 0)
           (cons 42 0)
           (cons 91 0)
           (list 10 4.2588 -1.2474728)
           (cons 40 0)
           (cons 41 0)
           (cons 42 0)
           (cons 91 0)
           (list 10 4.102336 -1.3)
           (cons 40 0)
           (cons 41 0)
           (cons 42 0)
           (cons 91 0)
           (list 10 3.297664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.1412 0.5702072)
           (cons 40 0)
           (cons 41 0)
           (cons 42 0)
           (cons 91 0)
           (list 10 3.1412 0.7445528)
           (cons 40 0)
           (cons 41 0)
           (cons 42 0)
           (cons 91 0)
           (list 10 3.297664 0.79708)
           (cons 40 0)
           (cons 41 0)
           (cons 42 0)
           (cons 91 0)
           (list 10 4.102336 0.79708)
           (cons 40 0)
           (cons 41 0)
           (cons 42 0)
           (cons 91 0)
           (list 10 4.2588 0.7445528)
           (cons 40 0)
           (cons 41 0)
           (cons 42 0)
           (cons 91 0)
           (list 10 4.2588 0.5702072)
           (cons 40 0)
           (cons 41 0)
           (cons 42 0)
           (cons 91 0)
           (list 10 4.102336 0.51768)
           (cons 40 0)
           (cons 41 0)
           (cons 42 0)
           (cons 91 0)
           (list 10 3.297664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.1412 1.0731272)
           (cons 40 0)
           (cons 41 0)
           (cons 42 0)
           (cons 91 0)
           (list 10 3.1412 1.2474728)
           (cons 40 0)
           (cons 41 0)
           (cons 42 0)
           (cons 91 0)
           (list 10 3.297664 1.3)
           (cons 40 0)
           (cons 41 0)
           (cons 42 0)
           (cons 91 0)
           (list 10 4.102336 1.3)
           (cons 40 0)
           (cons 41 0)
           (cons 42 0)
           (cons 91 0)
           (list 10 4.2588 1.2474728)
           (cons 40 0)
           (cons 41 0)
           (cons 42 0)
           (cons 91 0)
           (list 10 4.2588 1.0731272)
           (cons 40 0)
           (cons 41 0)
           (cons 42 0)
           (cons 91 0)
           (list 10 4.102336 1.0206)
           (cons 40 0)
           (cons 41 0)
           (cons 42 0)
           (cons 91 0)
           (list 10 3.297664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 3.7 -1.3 0)
           (cons 50 0)
          )
         )
         (entmake
          (list
           (cons 0 "POINT")
           (cons 100 "AcDbEntity")
           (cons 67 0)
           (cons 8 "0")
           (cons 100 "AcDbPoint")
           (list 10 3.7 1.3 0)
           (cons 50 0)
          )
         )
         (entmake
          (list
           (cons 0 "POINT")
           (cons 100 "AcDbEntity")
           (cons 67 0)
           (cons 8 "0")
           (cons 100 "AcDbPoint")
           (list 10 3.7 0 0)
           (cons 50 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "3.700")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "3.700")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-36-TRAILER1"))
        (progn
         (entmake)
         (entmake
          (list
           (cons 0 "BLOCK")
           (cons 2 "AB_INF-WB-36-TRAILER1")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 -1.3)
           (cons 40 0)
           (cons 41 0)
           (cons 42 0)
           (cons 91 0)
           (list 10 16.2 -1.3)
           (cons 40 0)
           (cons 41 0)
           (cons 42 0)
           (cons 91 0)
           (list 10 16.2 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 16.2 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 16.2 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.2062 -0.7445528)
           (cons 40 0)
           (cons 41 0)
           (cons 42 0)
           (cons 91 0)
           (list 10 13.2062 -0.5702072)
           (cons 40 0)
           (cons 41 0)
           (cons 42 0)
           (cons 91 0)
           (list 10 13.362664 -0.51768)
           (cons 40 0)
           (cons 41 0)
           (cons 42 0)
           (cons 91 0)
           (list 10 14.167336 -0.51768)
           (cons 40 0)
           (cons 41 0)
           (cons 42 0)
           (cons 91 0)
           (list 10 14.3238 -0.5702072)
           (cons 40 0)
           (cons 41 0)
           (cons 42 0)
           (cons 91 0)
           (list 10 14.3238 -0.7445528)
           (cons 40 0)
           (cons 41 0)
           (cons 42 0)
           (cons 91 0)
           (list 10 14.167336 -0.79708)
           (cons 40 0)
           (cons 41 0)
           (cons 42 0)
           (cons 91 0)
           (list 10 13.362664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.2062 -1.2474728)
           (cons 40 0)
           (cons 41 0)
           (cons 42 0)
           (cons 91 0)
           (list 10 13.2062 -1.0731272)
           (cons 40 0)
           (cons 41 0)
           (cons 42 0)
           (cons 91 0)
           (list 10 13.362664 -1.0206)
           (cons 40 0)
           (cons 41 0)
           (cons 42 0)
           (cons 91 0)
           (list 10 14.167336 -1.0206)
           (cons 40 0)
           (cons 41 0)
           (cons 42 0)
           (cons 91 0)
           (list 10 14.3238 -1.0731272)
           (cons 40 0)
           (cons 41 0)
           (cons 42 0)
           (cons 91 0)
           (list 10 14.3238 -1.2474728)
           (cons 40 0)
           (cons 41 0)
           (cons 42 0)
           (cons 91 0)
           (list 10 14.167336 -1.3)
           (cons 40 0)
           (cons 41 0)
           (cons 42 0)
           (cons 91 0)
           (list 10 13.362664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.2062 0.5702072)
           (cons 40 0)
           (cons 41 0)
           (cons 42 0)
           (cons 91 0)
           (list 10 13.2062 0.7445528)
           (cons 40 0)
           (cons 41 0)
           (cons 42 0)
           (cons 91 0)
           (list 10 13.362664 0.79708)
           (cons 40 0)
           (cons 41 0)
           (cons 42 0)
           (cons 91 0)
           (list 10 14.167336 0.79708)
           (cons 40 0)
           (cons 41 0)
           (cons 42 0)
           (cons 91 0)
           (list 10 14.3238 0.7445528)
           (cons 40 0)
           (cons 41 0)
           (cons 42 0)
           (cons 91 0)
           (list 10 14.3238 0.5702072)
           (cons 40 0)
           (cons 41 0)
           (cons 42 0)
           (cons 91 0)
           (list 10 14.167336 0.51768)
           (cons 40 0)
           (cons 41 0)
           (cons 42 0)
           (cons 91 0)
           (list 10 13.362664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.2062 1.0731272)
           (cons 40 0)
           (cons 41 0)
           (cons 42 0)
           (cons 91 0)
           (list 10 13.2062 1.2474728)
           (cons 40 0)
           (cons 41 0)
           (cons 42 0)
           (cons 91 0)
           (list 10 13.362664 1.3)
           (cons 40 0)
           (cons 41 0)
           (cons 42 0)
           (cons 91 0)
           (list 10 14.167336 1.3)
           (cons 40 0)
           (cons 41 0)
           (cons 42 0)
           (cons 91 0)
           (list 10 14.3238 1.2474728)
           (cons 40 0)
           (cons 41 0)
           (cons 42 0)
           (cons 91 0)
           (list 10 14.3238 1.0731272)
           (cons 40 0)
           (cons 41 0)
           (cons 42 0)
           (cons 91 0)
           (list 10 14.167336 1.0206)
           (cons 40 0)
           (cons 41 0)
           (cons 42 0)
           (cons 91 0)
           (list 10 13.362664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.4762 -0.7445528)
           (cons 40 0)
           (cons 41 0)
           (cons 42 0)
           (cons 91 0)
           (list 10 14.4762 -0.5702072)
           (cons 40 0)
           (cons 41 0)
           (cons 42 0)
           (cons 91 0)
           (list 10 14.632664 -0.51768)
           (cons 40 0)
           (cons 41 0)
           (cons 42 0)
           (cons 91 0)
           (list 10 15.437336 -0.51768)
           (cons 40 0)
           (cons 41 0)
           (cons 42 0)
           (cons 91 0)
           (list 10 15.5938 -0.5702072)
           (cons 40 0)
           (cons 41 0)
           (cons 42 0)
           (cons 91 0)
           (list 10 15.5938 -0.7445528)
           (cons 40 0)
           (cons 41 0)
           (cons 42 0)
           (cons 91 0)
           (list 10 15.437336 -0.79708)
           (cons 40 0)
           (cons 41 0)
           (cons 42 0)
           (cons 91 0)
           (list 10 14.632664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.4762 -1.2474728)
           (cons 40 0)
           (cons 41 0)
           (cons 42 0)
           (cons 91 0)
           (list 10 14.4762 -1.0731272)
           (cons 40 0)
           (cons 41 0)
           (cons 42 0)
           (cons 91 0)
           (list 10 14.632664 -1.0206)
           (cons 40 0)
           (cons 41 0)
           (cons 42 0)
           (cons 91 0)
           (list 10 15.437336 -1.0206)
           (cons 40 0)
           (cons 41 0)
           (cons 42 0)
           (cons 91 0)
           (list 10 15.5938 -1.0731272)
           (cons 40 0)
           (cons 41 0)
           (cons 42 0)
           (cons 91 0)
           (list 10 15.5938 -1.2474728)
           (cons 40 0)
           (cons 41 0)
           (cons 42 0)
           (cons 91 0)
           (list 10 15.437336 -1.3)
           (cons 40 0)
           (cons 41 0)
           (cons 42 0)
           (cons 91 0)
           (list 10 14.632664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.4762 0.5702072)
           (cons 40 0)
           (cons 41 0)
           (cons 42 0)
           (cons 91 0)
           (list 10 14.4762 0.7445528)
           (cons 40 0)
           (cons 41 0)
           (cons 42 0)
           (cons 91 0)
           (list 10 14.632664 0.79708)
           (cons 40 0)
           (cons 41 0)
           (cons 42 0)
           (cons 91 0)
           (list 10 15.437336 0.79708)
           (cons 40 0)
           (cons 41 0)
           (cons 42 0)
           (cons 91 0)
           (list 10 15.5938 0.7445528)
           (cons 40 0)
           (cons 41 0)
           (cons 42 0)
           (cons 91 0)
           (list 10 15.5938 0.5702072)
           (cons 40 0)
           (cons 41 0)
           (cons 42 0)
           (cons 91 0)
           (list 10 15.437336 0.51768)
           (cons 40 0)
           (cons 41 0)
           (cons 42 0)
           (cons 91 0)
           (list 10 14.632664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.4762 1.0731272)
           (cons 40 0)
           (cons 41 0)
           (cons 42 0)
           (cons 91 0)
           (list 10 14.4762 1.2474728)
           (cons 40 0)
           (cons 41 0)
           (cons 42 0)
           (cons 91 0)
           (list 10 14.632664 1.3)
           (cons 40 0)
           (cons 41 0)
           (cons 42 0)
           (cons 91 0)
           (list 10 15.437336 1.3)
           (cons 40 0)
           (cons 41 0)
           (cons 42 0)
           (cons 91 0)
           (list 10 15.5938 1.2474728)
           (cons 40 0)
           (cons 41 0)
           (cons 42 0)
           (cons 91 0)
           (list 10 15.5938 1.0731272)
           (cons 40 0)
           (cons 41 0)
           (cons 42 0)
           (cons 91 0)
           (list 10 15.437336 1.0206)
           (cons 40 0)
           (cons 41 0)
           (cons 42 0)
           (cons 91 0)
           (list 10 14.632664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 1.9 0 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 16.2 1.3 0)
           (cons 50 0)
          )
         )
         (entmake
          (list
           (cons 0 "POINT")
           (cons 100 "AcDbEntity")
           (cons 67 0)
           (cons 8 "0")
           (cons 100 "AcDbPoint")
           (list 10 16.2 0 0)
           (cons 50 0)
          )
         )
         (entmake
          (list
           (cons 0 "POINT")
           (cons 100 "AcDbEntity")
           (cons 67 0)
           (cons 8 "0")
           (cons 100 "AcDbPoint")
           (list 10 16.2 -1.3 0)
           (cons 50 0)
          )
         )
         (entmake
          (list
           (cons 0 "POINT")
           (cons 100 "AcDbEntity")
           (cons 67 0)
           (cons 8 "0")
           (cons 100 "AcDbPoint")
           (list 10 14.4 1.3 0)
           (cons 50 0)
          )
         )
         (entmake
          (list
           (cons 0 "POINT")
           (cons 100 "AcDbEntity")
           (cons 67 0)
           (cons 8 "0")
           (cons 100 "AcDbPoint")
           (list 10 14.4 -1.3 0)
           (cons 50 0)
          )
         )
         (entmake
          (list
           (cons 0 "ATTDEF")
           (cons 100 "AcDbEntity")
           (cons 67 0)
           (cons 8 "0")
           (cons 100 "AcDbText")
           (list 10 1.2 0.56666667 0)
           (cons 40 0.2)
           (cons 1 "1.900")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.2 0.23333333 0)
           (cons 40 0.2)
           (cons 1 "1.900")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.2 -0.1 0)
           (cons 40 0.2)
           (cons 1 "14.400")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.2 -0.43333333 0)
           (cons 40 0.2)
           (cons 1 "16.200")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.2 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-36-TRUCK"))
        (progn
         (entmake)
         (entmake
          (list
           (cons 0 "BLOCK")
           (cons 2 "AB_INF-WB-36-TRUCK")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 -1.3)
           (cons 40 0)
           (cons 41 0)
           (cons 42 0)
           (cons 91 0)
           (list 10 6.435 -1.3)
           (cons 40 0)
           (cons 41 0)
           (cons 42 0)
           (cons 91 0)
           (list 10 6.435 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.435 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.435 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 5.8 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 6.06263966 -0.26263966 0)
           (list 11 6.06263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.6062 -0.7445528)
           (cons 40 0)
           (cons 41 0)
           (cons 42 0)
           (cons 91 0)
           (list 10 4.6062 -0.5702072)
           (cons 40 0)
           (cons 41 0)
           (cons 42 0)
           (cons 91 0)
           (list 10 4.762664 -0.51768)
           (cons 40 0)
           (cons 41 0)
           (cons 42 0)
           (cons 91 0)
           (list 10 5.567336 -0.51768)
           (cons 40 0)
           (cons 41 0)
           (cons 42 0)
           (cons 91 0)
           (list 10 5.7238 -0.5702072)
           (cons 40 0)
           (cons 41 0)
           (cons 42 0)
           (cons 91 0)
           (list 10 5.7238 -0.7445528)
           (cons 40 0)
           (cons 41 0)
           (cons 42 0)
           (cons 91 0)
           (list 10 5.567336 -0.79708)
           (cons 40 0)
           (cons 41 0)
           (cons 42 0)
           (cons 91 0)
           (list 10 4.762664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.6062 -1.2474728)
           (cons 40 0)
           (cons 41 0)
           (cons 42 0)
           (cons 91 0)
           (list 10 4.6062 -1.0731272)
           (cons 40 0)
           (cons 41 0)
           (cons 42 0)
           (cons 91 0)
           (list 10 4.762664 -1.0206)
           (cons 40 0)
           (cons 41 0)
           (cons 42 0)
           (cons 91 0)
           (list 10 5.567336 -1.0206)
           (cons 40 0)
           (cons 41 0)
           (cons 42 0)
           (cons 91 0)
           (list 10 5.7238 -1.0731272)
           (cons 40 0)
           (cons 41 0)
           (cons 42 0)
           (cons 91 0)
           (list 10 5.7238 -1.2474728)
           (cons 40 0)
           (cons 41 0)
           (cons 42 0)
           (cons 91 0)
           (list 10 5.567336 -1.3)
           (cons 40 0)
           (cons 41 0)
           (cons 42 0)
           (cons 91 0)
           (list 10 4.762664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.6062 0.5702072)
           (cons 40 0)
           (cons 41 0)
           (cons 42 0)
           (cons 91 0)
           (list 10 4.6062 0.7445528)
           (cons 40 0)
           (cons 41 0)
           (cons 42 0)
           (cons 91 0)
           (list 10 4.762664 0.79708)
           (cons 40 0)
           (cons 41 0)
           (cons 42 0)
           (cons 91 0)
           (list 10 5.567336 0.79708)
           (cons 40 0)
           (cons 41 0)
           (cons 42 0)
           (cons 91 0)
           (list 10 5.7238 0.7445528)
           (cons 40 0)
           (cons 41 0)
           (cons 42 0)
           (cons 91 0)
           (list 10 5.7238 0.5702072)
           (cons 40 0)
           (cons 41 0)
           (cons 42 0)
           (cons 91 0)
           (list 10 5.567336 0.51768)
           (cons 40 0)
           (cons 41 0)
           (cons 42 0)
           (cons 91 0)
           (list 10 4.762664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.6062 1.0731272)
           (cons 40 0)
           (cons 41 0)
           (cons 42 0)
           (cons 91 0)
           (list 10 4.6062 1.2474728)
           (cons 40 0)
           (cons 41 0)
           (cons 42 0)
           (cons 91 0)
           (list 10 4.762664 1.3)
           (cons 40 0)
           (cons 41 0)
           (cons 42 0)
           (cons 91 0)
           (list 10 5.567336 1.3)
           (cons 40 0)
           (cons 41 0)
           (cons 42 0)
           (cons 91 0)
           (list 10 5.7238 1.2474728)
           (cons 40 0)
           (cons 41 0)
           (cons 42 0)
           (cons 91 0)
           (list 10 5.7238 1.0731272)
           (cons 40 0)
           (cons 41 0)
           (cons 42 0)
           (cons 91 0)
           (list 10 5.567336 1.0206)
           (cons 40 0)
           (cons 41 0)
           (cons 42 0)
           (cons 91 0)
           (list 10 4.762664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.8762 -0.7445528)
           (cons 40 0)
           (cons 41 0)
           (cons 42 0)
           (cons 91 0)
           (list 10 5.8762 -0.5702072)
           (cons 40 0)
           (cons 41 0)
           (cons 42 0)
           (cons 91 0)
           (list 10 6.032664 -0.51768)
           (cons 40 0)
           (cons 41 0)
           (cons 42 0)
           (cons 91 0)
           (list 10 6.837336 -0.51768)
           (cons 40 0)
           (cons 41 0)
           (cons 42 0)
           (cons 91 0)
           (list 10 6.9938 -0.5702072)
           (cons 40 0)
           (cons 41 0)
           (cons 42 0)
           (cons 91 0)
           (list 10 6.9938 -0.7445528)
           (cons 40 0)
           (cons 41 0)
           (cons 42 0)
           (cons 91 0)
           (list 10 6.837336 -0.79708)
           (cons 40 0)
           (cons 41 0)
           (cons 42 0)
           (cons 91 0)
           (list 10 6.032664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.8762 -1.2474728)
           (cons 40 0)
           (cons 41 0)
           (cons 42 0)
           (cons 91 0)
           (list 10 5.8762 -1.0731272)
           (cons 40 0)
           (cons 41 0)
           (cons 42 0)
           (cons 91 0)
           (list 10 6.032664 -1.0206)
           (cons 40 0)
           (cons 41 0)
           (cons 42 0)
           (cons 91 0)
           (list 10 6.837336 -1.0206)
           (cons 40 0)
           (cons 41 0)
           (cons 42 0)
           (cons 91 0)
           (list 10 6.9938 -1.0731272)
           (cons 40 0)
           (cons 41 0)
           (cons 42 0)
           (cons 91 0)
           (list 10 6.9938 -1.2474728)
           (cons 40 0)
           (cons 41 0)
           (cons 42 0)
           (cons 91 0)
           (list 10 6.837336 -1.3)
           (cons 40 0)
           (cons 41 0)
           (cons 42 0)
           (cons 91 0)
           (list 10 6.032664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.8762 0.5702072)
           (cons 40 0)
           (cons 41 0)
           (cons 42 0)
           (cons 91 0)
           (list 10 5.8762 0.7445528)
           (cons 40 0)
           (cons 41 0)
           (cons 42 0)
           (cons 91 0)
           (list 10 6.032664 0.79708)
           (cons 40 0)
           (cons 41 0)
           (cons 42 0)
           (cons 91 0)
           (list 10 6.837336 0.79708)
           (cons 40 0)
           (cons 41 0)
           (cons 42 0)
           (cons 91 0)
           (list 10 6.9938 0.7445528)
           (cons 40 0)
           (cons 41 0)
           (cons 42 0)
           (cons 91 0)
           (list 10 6.9938 0.5702072)
           (cons 40 0)
           (cons 41 0)
           (cons 42 0)
           (cons 91 0)
           (list 10 6.837336 0.51768)
           (cons 40 0)
           (cons 41 0)
           (cons 42 0)
           (cons 91 0)
           (list 10 6.032664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.8762 1.0731272)
           (cons 40 0)
           (cons 41 0)
           (cons 42 0)
           (cons 91 0)
           (list 10 5.8762 1.2474728)
           (cons 40 0)
           (cons 41 0)
           (cons 42 0)
           (cons 91 0)
           (list 10 6.032664 1.3)
           (cons 40 0)
           (cons 41 0)
           (cons 42 0)
           (cons 91 0)
           (list 10 6.837336 1.3)
           (cons 40 0)
           (cons 41 0)
           (cons 42 0)
           (cons 91 0)
           (list 10 6.9938 1.2474728)
           (cons 40 0)
           (cons 41 0)
           (cons 42 0)
           (cons 91 0)
           (list 10 6.9938 1.0731272)
           (cons 40 0)
           (cons 41 0)
           (cons 42 0)
           (cons 91 0)
           (list 10 6.837336 1.0206)
           (cons 40 0)
           (cons 41 0)
           (cons 42 0)
           (cons 91 0)
           (list 10 6.032664 1.0206)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelRightM1")
           (list 10 0.7 1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM1")
           (list 10 0.7 -1.0206 0)
           (cons 41 1)
           (cons 42 1)
           (cons 43 1)
           (cons 50 0)
           (cons 70 0)
           (cons 71 0)
           (cons 44 0)
           (cons 45 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0.7 1.3 0)
           (cons 50 0)
          )
         )
         (entmake
          (list
           (cons 0 "POINT")
           (cons 100 "AcDbEntity")
           (cons 67 0)
           (cons 8 "0")
           (cons 100 "AcDbPoint")
           (list 10 0.7 -1.3 0)
           (cons 50 0)
          )
         )
         (entmake
          (list
           (cons 0 "POINT")
           (cons 100 "AcDbEntity")
           (cons 67 0)
           (cons 8 "0")
           (cons 100 "AcDbPoint")
           (list 10 0.7 0 0)
           (cons 50 0)
          )
         )
         (entmake
          (list
           (cons 0 "POINT")
           (cons 100 "AcDbEntity")
           (cons 67 0)
           (cons 8 "0")
           (cons 100 "AcDbPoint")
           (list 10 5.8 1.3 0)
           (cons 50 0)
          )
         )
         (entmake
          (list
           (cons 0 "POINT")
           (cons 100 "AcDbEntity")
           (cons 67 0)
           (cons 8 "0")
           (cons 100 "AcDbPoint")
           (list 10 5.8 0 0)
           (cons 50 0)
          )
         )
         (entmake
          (list
           (cons 0 "POINT")
           (cons 100 "AcDbEntity")
           (cons 67 0)
           (cons 8 "0")
           (cons 100 "AcDbPoint")
           (list 10 5.8 -1.3 0)
           (cons 50 0)
          )
         )
         (entmake
          (list
           (cons 0 "ATTDEF")
           (cons 100 "AcDbEntity")
           (cons 67 0)
           (cons 8 "0")
           (cons 100 "AcDbText")
           (list 10 0 0.56666667 0)
           (cons 40 0.2)
           (cons 1 "0.700")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0 0.23333333 0)
           (cons 40 0.2)
           (cons 1 "0.700")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0 -0.1 0)
           (cons 40 0.2)
           (cons 1 "5.800")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0 -0.43333333 0)
           (cons 40 0.2)
           (cons 1 "5.800")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0 -0.76666667 0)
           (cons 40 0.2)
           (cons 1 "17.19")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-33-TRAILER2"))
        (progn
         (entmake)
         (entmake
          (list
           (cons 0 "BLOCK")
           (cons 2 "AB_INF-WB-33-TRAILER2")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 8.6 -1.3)
           (cons 40 0)
           (cons 41 0)
           (cons 42 0)
           (cons 91 0)
           (list 10 8.6 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.6 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.6 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9062 -0.7445528)
           (cons 40 0)
           (cons 41 0)
           (cons 42 0)
           (cons 91 0)
           (list 10 5.9062 -0.5702072)
           (cons 40 0)
           (cons 41 0)
           (cons 42 0)
           (cons 91 0)
           (list 10 6.062664 -0.51768)
           (cons 40 0)
           (cons 41 0)
           (cons 42 0)
           (cons 91 0)
           (list 10 6.867336 -0.51768)
           (cons 40 0)
           (cons 41 0)
           (cons 42 0)
           (cons 91 0)
           (list 10 7.0238 -0.5702072)
           (cons 40 0)
           (cons 41 0)
           (cons 42 0)
           (cons 91 0)
           (list 10 7.0238 -0.7445528)
           (cons 40 0)
           (cons 41 0)
           (cons 42 0)
           (cons 91 0)
           (list 10 6.867336 -0.79708)
           (cons 40 0)
           (cons 41 0)
           (cons 42 0)
           (cons 91 0)
           (list 10 6.062664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9062 -1.2474728)
           (cons 40 0)
           (cons 41 0)
           (cons 42 0)
           (cons 91 0)
           (list 10 5.9062 -1.0731272)
           (cons 40 0)
           (cons 41 0)
           (cons 42 0)
           (cons 91 0)
           (list 10 6.062664 -1.0206)
           (cons 40 0)
           (cons 41 0)
           (cons 42 0)
           (cons 91 0)
           (list 10 6.867336 -1.0206)
           (cons 40 0)
           (cons 41 0)
           (cons 42 0)
           (cons 91 0)
           (list 10 7.0238 -1.0731272)
           (cons 40 0)
           (cons 41 0)
           (cons 42 0)
           (cons 91 0)
           (list 10 7.0238 -1.2474728)
           (cons 40 0)
           (cons 41 0)
           (cons 42 0)
           (cons 91 0)
           (list 10 6.867336 -1.3)
           (cons 40 0)
           (cons 41 0)
           (cons 42 0)
           (cons 91 0)
           (list 10 6.062664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9062 0.5702072)
           (cons 40 0)
           (cons 41 0)
           (cons 42 0)
           (cons 91 0)
           (list 10 5.9062 0.7445528)
           (cons 40 0)
           (cons 41 0)
           (cons 42 0)
           (cons 91 0)
           (list 10 6.062664 0.79708)
           (cons 40 0)
           (cons 41 0)
           (cons 42 0)
           (cons 91 0)
           (list 10 6.867336 0.79708)
           (cons 40 0)
           (cons 41 0)
           (cons 42 0)
           (cons 91 0)
           (list 10 7.0238 0.7445528)
           (cons 40 0)
           (cons 41 0)
           (cons 42 0)
           (cons 91 0)
           (list 10 7.0238 0.5702072)
           (cons 40 0)
           (cons 41 0)
           (cons 42 0)
           (cons 91 0)
           (list 10 6.867336 0.51768)
           (cons 40 0)
           (cons 41 0)
           (cons 42 0)
           (cons 91 0)
           (list 10 6.062664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9062 1.0731272)
           (cons 40 0)
           (cons 41 0)
           (cons 42 0)
           (cons 91 0)
           (list 10 5.9062 1.2474728)
           (cons 40 0)
           (cons 41 0)
           (cons 42 0)
           (cons 91 0)
           (list 10 6.062664 1.3)
           (cons 40 0)
           (cons 41 0)
           (cons 42 0)
           (cons 91 0)
           (list 10 6.867336 1.3)
           (cons 40 0)
           (cons 41 0)
           (cons 42 0)
           (cons 91 0)
           (list 10 7.0238 1.2474728)
           (cons 40 0)
           (cons 41 0)
           (cons 42 0)
           (cons 91 0)
           (list 10 7.0238 1.0731272)
           (cons 40 0)
           (cons 41 0)
           (cons 42 0)
           (cons 91 0)
           (list 10 6.867336 1.0206)
           (cons 40 0)
           (cons 41 0)
           (cons 42 0)
           (cons 91 0)
           (list 10 6.062664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1762 -0.7445528)
           (cons 40 0)
           (cons 41 0)
           (cons 42 0)
           (cons 91 0)
           (list 10 7.1762 -0.5702072)
           (cons 40 0)
           (cons 41 0)
           (cons 42 0)
           (cons 91 0)
           (list 10 7.332664 -0.51768)
           (cons 40 0)
           (cons 41 0)
           (cons 42 0)
           (cons 91 0)
           (list 10 8.137336 -0.51768)
           (cons 40 0)
           (cons 41 0)
           (cons 42 0)
           (cons 91 0)
           (list 10 8.2938 -0.5702072)
           (cons 40 0)
           (cons 41 0)
           (cons 42 0)
           (cons 91 0)
           (list 10 8.2938 -0.7445528)
           (cons 40 0)
           (cons 41 0)
           (cons 42 0)
           (cons 91 0)
           (list 10 8.137336 -0.79708)
           (cons 40 0)
           (cons 41 0)
           (cons 42 0)
           (cons 91 0)
           (list 10 7.332664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1762 -1.2474728)
           (cons 40 0)
           (cons 41 0)
           (cons 42 0)
           (cons 91 0)
           (list 10 7.1762 -1.0731272)
           (cons 40 0)
           (cons 41 0)
           (cons 42 0)
           (cons 91 0)
           (list 10 7.332664 -1.0206)
           (cons 40 0)
           (cons 41 0)
           (cons 42 0)
           (cons 91 0)
           (list 10 8.137336 -1.0206)
           (cons 40 0)
           (cons 41 0)
           (cons 42 0)
           (cons 91 0)
           (list 10 8.2938 -1.0731272)
           (cons 40 0)
           (cons 41 0)
           (cons 42 0)
           (cons 91 0)
           (list 10 8.2938 -1.2474728)
           (cons 40 0)
           (cons 41 0)
           (cons 42 0)
           (cons 91 0)
           (list 10 8.137336 -1.3)
           (cons 40 0)
           (cons 41 0)
           (cons 42 0)
           (cons 91 0)
           (list 10 7.332664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1762 0.5702072)
           (cons 40 0)
           (cons 41 0)
           (cons 42 0)
           (cons 91 0)
           (list 10 7.1762 0.7445528)
           (cons 40 0)
           (cons 41 0)
           (cons 42 0)
           (cons 91 0)
           (list 10 7.332664 0.79708)
           (cons 40 0)
           (cons 41 0)
           (cons 42 0)
           (cons 91 0)
           (list 10 8.137336 0.79708)
           (cons 40 0)
           (cons 41 0)
           (cons 42 0)
           (cons 91 0)
           (list 10 8.2938 0.7445528)
           (cons 40 0)
           (cons 41 0)
           (cons 42 0)
           (cons 91 0)
           (list 10 8.2938 0.5702072)
           (cons 40 0)
           (cons 41 0)
           (cons 42 0)
           (cons 91 0)
           (list 10 8.137336 0.51768)
           (cons 40 0)
           (cons 41 0)
           (cons 42 0)
           (cons 91 0)
           (list 10 7.332664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1762 1.0731272)
           (cons 40 0)
           (cons 41 0)
           (cons 42 0)
           (cons 91 0)
           (list 10 7.1762 1.2474728)
           (cons 40 0)
           (cons 41 0)
           (cons 42 0)
           (cons 91 0)
           (list 10 7.332664 1.3)
           (cons 40 0)
           (cons 41 0)
           (cons 42 0)
           (cons 91 0)
           (list 10 8.137336 1.3)
           (cons 40 0)
           (cons 41 0)
           (cons 42 0)
           (cons 91 0)
           (list 10 8.2938 1.2474728)
           (cons 40 0)
           (cons 41 0)
           (cons 42 0)
           (cons 91 0)
           (list 10 8.2938 1.0731272)
           (cons 40 0)
           (cons 41 0)
           (cons 42 0)
           (cons 91 0)
           (list 10 8.137336 1.0206)
           (cons 40 0)
           (cons 41 0)
           (cons 42 0)
           (cons 91 0)
           (list 10 7.332664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0.6 0 0)
           (cons 50 0)
          )
         )
         (entmake
          (list
           (cons 0 "POINT")
           (cons 100 "AcDbEntity")
           (cons 67 0)
           (cons 8 "0")
           (cons 100 "AcDbPoint")
           (list 10 8.6 1.3 0)
           (cons 50 0)
          )
         )
         (entmake
          (list
           (cons 0 "POINT")
           (cons 100 "AcDbEntity")
           (cons 67 0)
           (cons 8 "0")
           (cons 100 "AcDbPoint")
           (list 10 8.6 -1.3 0)
           (cons 50 0)
          )
         )
         (entmake
          (list
           (cons 0 "POINT")
           (cons 100 "AcDbEntity")
           (cons 67 0)
           (cons 8 "0")
           (cons 100 "AcDbPoint")
           (list 10 7.1 1.3 0)
           (cons 50 0)
          )
         )
         (entmake
          (list
           (cons 0 "POINT")
           (cons 100 "AcDbEntity")
           (cons 67 0)
           (cons 8 "0")
           (cons 100 "AcDbPoint")
           (list 10 7.1 -1.3 0)
           (cons 50 0)
          )
         )
         (entmake
          (list
           (cons 0 "ATTDEF")
           (cons 100 "AcDbEntity")
           (cons 67 0)
           (cons 8 "0")
           (cons 100 "AcDbText")
           (list 10 -0.1 0.56666667 0)
           (cons 40 0.2)
           (cons 1 "0.600")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 0.23333333 0)
           (cons 40 0.2)
           (cons 1 "0.600")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 -0.1 0)
           (cons 40 0.2)
           (cons 1 "7.100")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-33-PUP"))
        (progn
         (entmake)
         (entmake
          (list
           (cons 0 "BLOCK")
           (cons 2 "AB_INF-WB-33-PUP")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 3)
           (cons 70 129)
           (cons 43 0)
           (cons 38 0)
           (cons 39 0)
           (list 10 0 0)
           (cons 40 0)
           (cons 41 0)
           (cons 42 0)
           (cons 91 0)
           (list 10 2.1 1.3)
           (cons 40 0)
           (cons 41 0)
           (cons 42 0)
           (cons 91 0)
           (list 10 2.1 -1.3)
           (cons 40 0)
           (cons 41 0)
           (cons 42 0)
           (cons 91 0)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 2.1 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 -0.7445528)
           (cons 40 0)
           (cons 41 0)
           (cons 42 0)
           (cons 91 0)
           (list 10 1.5412 -0.5702072)
           (cons 40 0)
           (cons 41 0)
           (cons 42 0)
           (cons 91 0)
           (list 10 1.697664 -0.51768)
           (cons 40 0)
           (cons 41 0)
           (cons 42 0)
           (cons 91 0)
           (list 10 2.502336 -0.51768)
           (cons 40 0)
           (cons 41 0)
           (cons 42 0)
           (cons 91 0)
           (list 10 2.6588 -0.5702072)
           (cons 40 0)
           (cons 41 0)
           (cons 42 0)
           (cons 91 0)
           (list 10 2.6588 -0.7445528)
           (cons 40 0)
           (cons 41 0)
           (cons 42 0)
           (cons 91 0)
           (list 10 2.502336 -0.79708)
           (cons 40 0)
           (cons 41 0)
           (cons 42 0)
           (cons 91 0)
           (list 10 1.697664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 -1.2474728)
           (cons 40 0)
           (cons 41 0)
           (cons 42 0)
           (cons 91 0)
           (list 10 1.5412 -1.0731272)
           (cons 40 0)
           (cons 41 0)
           (cons 42 0)
           (cons 91 0)
           (list 10 1.697664 -1.0206)
           (cons 40 0)
           (cons 41 0)
           (cons 42 0)
           (cons 91 0)
           (list 10 2.502336 -1.0206)
           (cons 40 0)
           (cons 41 0)
           (cons 42 0)
           (cons 91 0)
           (list 10 2.6588 -1.0731272)
           (cons 40 0)
           (cons 41 0)
           (cons 42 0)
           (cons 91 0)
           (list 10 2.6588 -1.2474728)
           (cons 40 0)
           (cons 41 0)
           (cons 42 0)
           (cons 91 0)
           (list 10 2.502336 -1.3)
           (cons 40 0)
           (cons 41 0)
           (cons 42 0)
           (cons 91 0)
           (list 10 1.697664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 0.5702072)
           (cons 40 0)
           (cons 41 0)
           (cons 42 0)
           (cons 91 0)
           (list 10 1.5412 0.7445528)
           (cons 40 0)
           (cons 41 0)
           (cons 42 0)
           (cons 91 0)
           (list 10 1.697664 0.79708)
           (cons 40 0)
           (cons 41 0)
           (cons 42 0)
           (cons 91 0)
           (list 10 2.502336 0.79708)
           (cons 40 0)
           (cons 41 0)
           (cons 42 0)
           (cons 91 0)
           (list 10 2.6588 0.7445528)
           (cons 40 0)
           (cons 41 0)
           (cons 42 0)
           (cons 91 0)
           (list 10 2.6588 0.5702072)
           (cons 40 0)
           (cons 41 0)
           (cons 42 0)
           (cons 91 0)
           (list 10 2.502336 0.51768)
           (cons 40 0)
           (cons 41 0)
           (cons 42 0)
           (cons 91 0)
           (list 10 1.697664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 1.0731272)
           (cons 40 0)
           (cons 41 0)
           (cons 42 0)
           (cons 91 0)
           (list 10 1.5412 1.2474728)
           (cons 40 0)
           (cons 41 0)
           (cons 42 0)
           (cons 91 0)
           (list 10 1.697664 1.3)
           (cons 40 0)
           (cons 41 0)
           (cons 42 0)
           (cons 91 0)
           (list 10 2.502336 1.3)
           (cons 40 0)
           (cons 41 0)
           (cons 42 0)
           (cons 91 0)
           (list 10 2.6588 1.2474728)
           (cons 40 0)
           (cons 41 0)
           (cons 42 0)
           (cons 91 0)
           (list 10 2.6588 1.0731272)
           (cons 40 0)
           (cons 41 0)
           (cons 42 0)
           (cons 91 0)
           (list 10 2.502336 1.0206)
           (cons 40 0)
           (cons 41 0)
           (cons 42 0)
           (cons 91 0)
           (list 10 1.697664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 2.1 1.3 0)
           (cons 50 0)
          )
         )
         (entmake
          (list
           (cons 0 "POINT")
           (cons 100 "AcDbEntity")
           (cons 67 0)
           (cons 8 "0")
           (cons 100 "AcDbPoint")
           (list 10 2.1 -1.3 0)
           (cons 50 0)
          )
         )
         (entmake
          (list
           (cons 0 "POINT")
           (cons 100 "AcDbEntity")
           (cons 67 0)
           (cons 8 "0")
           (cons 100 "AcDbPoint")
           (list 10 2.1 0 0)
           (cons 50 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "2.100")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "2.100")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-33-TRAILER1"))
        (progn
         (entmake)
         (entmake
          (list
           (cons 0 "BLOCK")
           (cons 2 "AB_INF-WB-33-TRAILER1")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 8.6 -1.3)
           (cons 40 0)
           (cons 41 0)
           (cons 42 0)
           (cons 91 0)
           (list 10 8.6 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.6 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.6 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9062 -0.7445528)
           (cons 40 0)
           (cons 41 0)
           (cons 42 0)
           (cons 91 0)
           (list 10 5.9062 -0.5702072)
           (cons 40 0)
           (cons 41 0)
           (cons 42 0)
           (cons 91 0)
           (list 10 6.062664 -0.51768)
           (cons 40 0)
           (cons 41 0)
           (cons 42 0)
           (cons 91 0)
           (list 10 6.867336 -0.51768)
           (cons 40 0)
           (cons 41 0)
           (cons 42 0)
           (cons 91 0)
           (list 10 7.0238 -0.5702072)
           (cons 40 0)
           (cons 41 0)
           (cons 42 0)
           (cons 91 0)
           (list 10 7.0238 -0.7445528)
           (cons 40 0)
           (cons 41 0)
           (cons 42 0)
           (cons 91 0)
           (list 10 6.867336 -0.79708)
           (cons 40 0)
           (cons 41 0)
           (cons 42 0)
           (cons 91 0)
           (list 10 6.062664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9062 -1.2474728)
           (cons 40 0)
           (cons 41 0)
           (cons 42 0)
           (cons 91 0)
           (list 10 5.9062 -1.0731272)
           (cons 40 0)
           (cons 41 0)
           (cons 42 0)
           (cons 91 0)
           (list 10 6.062664 -1.0206)
           (cons 40 0)
           (cons 41 0)
           (cons 42 0)
           (cons 91 0)
           (list 10 6.867336 -1.0206)
           (cons 40 0)
           (cons 41 0)
           (cons 42 0)
           (cons 91 0)
           (list 10 7.0238 -1.0731272)
           (cons 40 0)
           (cons 41 0)
           (cons 42 0)
           (cons 91 0)
           (list 10 7.0238 -1.2474728)
           (cons 40 0)
           (cons 41 0)
           (cons 42 0)
           (cons 91 0)
           (list 10 6.867336 -1.3)
           (cons 40 0)
           (cons 41 0)
           (cons 42 0)
           (cons 91 0)
           (list 10 6.062664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9062 0.5702072)
           (cons 40 0)
           (cons 41 0)
           (cons 42 0)
           (cons 91 0)
           (list 10 5.9062 0.7445528)
           (cons 40 0)
           (cons 41 0)
           (cons 42 0)
           (cons 91 0)
           (list 10 6.062664 0.79708)
           (cons 40 0)
           (cons 41 0)
           (cons 42 0)
           (cons 91 0)
           (list 10 6.867336 0.79708)
           (cons 40 0)
           (cons 41 0)
           (cons 42 0)
           (cons 91 0)
           (list 10 7.0238 0.7445528)
           (cons 40 0)
           (cons 41 0)
           (cons 42 0)
           (cons 91 0)
           (list 10 7.0238 0.5702072)
           (cons 40 0)
           (cons 41 0)
           (cons 42 0)
           (cons 91 0)
           (list 10 6.867336 0.51768)
           (cons 40 0)
           (cons 41 0)
           (cons 42 0)
           (cons 91 0)
           (list 10 6.062664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9062 1.0731272)
           (cons 40 0)
           (cons 41 0)
           (cons 42 0)
           (cons 91 0)
           (list 10 5.9062 1.2474728)
           (cons 40 0)
           (cons 41 0)
           (cons 42 0)
           (cons 91 0)
           (list 10 6.062664 1.3)
           (cons 40 0)
           (cons 41 0)
           (cons 42 0)
           (cons 91 0)
           (list 10 6.867336 1.3)
           (cons 40 0)
           (cons 41 0)
           (cons 42 0)
           (cons 91 0)
           (list 10 7.0238 1.2474728)
           (cons 40 0)
           (cons 41 0)
           (cons 42 0)
           (cons 91 0)
           (list 10 7.0238 1.0731272)
           (cons 40 0)
           (cons 41 0)
           (cons 42 0)
           (cons 91 0)
           (list 10 6.867336 1.0206)
           (cons 40 0)
           (cons 41 0)
           (cons 42 0)
           (cons 91 0)
           (list 10 6.062664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1762 -0.7445528)
           (cons 40 0)
           (cons 41 0)
           (cons 42 0)
           (cons 91 0)
           (list 10 7.1762 -0.5702072)
           (cons 40 0)
           (cons 41 0)
           (cons 42 0)
           (cons 91 0)
           (list 10 7.332664 -0.51768)
           (cons 40 0)
           (cons 41 0)
           (cons 42 0)
           (cons 91 0)
           (list 10 8.137336 -0.51768)
           (cons 40 0)
           (cons 41 0)
           (cons 42 0)
           (cons 91 0)
           (list 10 8.2938 -0.5702072)
           (cons 40 0)
           (cons 41 0)
           (cons 42 0)
           (cons 91 0)
           (list 10 8.2938 -0.7445528)
           (cons 40 0)
           (cons 41 0)
           (cons 42 0)
           (cons 91 0)
           (list 10 8.137336 -0.79708)
           (cons 40 0)
           (cons 41 0)
           (cons 42 0)
           (cons 91 0)
           (list 10 7.332664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1762 -1.2474728)
           (cons 40 0)
           (cons 41 0)
           (cons 42 0)
           (cons 91 0)
           (list 10 7.1762 -1.0731272)
           (cons 40 0)
           (cons 41 0)
           (cons 42 0)
           (cons 91 0)
           (list 10 7.332664 -1.0206)
           (cons 40 0)
           (cons 41 0)
           (cons 42 0)
           (cons 91 0)
           (list 10 8.137336 -1.0206)
           (cons 40 0)
           (cons 41 0)
           (cons 42 0)
           (cons 91 0)
           (list 10 8.2938 -1.0731272)
           (cons 40 0)
           (cons 41 0)
           (cons 42 0)
           (cons 91 0)
           (list 10 8.2938 -1.2474728)
           (cons 40 0)
           (cons 41 0)
           (cons 42 0)
           (cons 91 0)
           (list 10 8.137336 -1.3)
           (cons 40 0)
           (cons 41 0)
           (cons 42 0)
           (cons 91 0)
           (list 10 7.332664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1762 0.5702072)
           (cons 40 0)
           (cons 41 0)
           (cons 42 0)
           (cons 91 0)
           (list 10 7.1762 0.7445528)
           (cons 40 0)
           (cons 41 0)
           (cons 42 0)
           (cons 91 0)
           (list 10 7.332664 0.79708)
           (cons 40 0)
           (cons 41 0)
           (cons 42 0)
           (cons 91 0)
           (list 10 8.137336 0.79708)
           (cons 40 0)
           (cons 41 0)
           (cons 42 0)
           (cons 91 0)
           (list 10 8.2938 0.7445528)
           (cons 40 0)
           (cons 41 0)
           (cons 42 0)
           (cons 91 0)
           (list 10 8.2938 0.5702072)
           (cons 40 0)
           (cons 41 0)
           (cons 42 0)
           (cons 91 0)
           (list 10 8.137336 0.51768)
           (cons 40 0)
           (cons 41 0)
           (cons 42 0)
           (cons 91 0)
           (list 10 7.332664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1762 1.0731272)
           (cons 40 0)
           (cons 41 0)
           (cons 42 0)
           (cons 91 0)
           (list 10 7.1762 1.2474728)
           (cons 40 0)
           (cons 41 0)
           (cons 42 0)
           (cons 91 0)
           (list 10 7.332664 1.3)
           (cons 40 0)
           (cons 41 0)
           (cons 42 0)
           (cons 91 0)
           (list 10 8.137336 1.3)
           (cons 40 0)
           (cons 41 0)
           (cons 42 0)
           (cons 91 0)
           (list 10 8.2938 1.2474728)
           (cons 40 0)
           (cons 41 0)
           (cons 42 0)
           (cons 91 0)
           (list 10 8.2938 1.0731272)
           (cons 40 0)
           (cons 41 0)
           (cons 42 0)
           (cons 91 0)
           (list 10 8.137336 1.0206)
           (cons 40 0)
           (cons 41 0)
           (cons 42 0)
           (cons 91 0)
           (list 10 7.332664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0.6 0 0)
           (cons 50 0)
          )
         )
         (entmake
          (list
           (cons 0 "POINT")
           (cons 100 "AcDbEntity")
           (cons 67 0)
           (cons 8 "0")
           (cons 100 "AcDbPoint")
           (list 10 8.6 1.3 0)
           (cons 50 0)
          )
         )
         (entmake
          (list
           (cons 0 "POINT")
           (cons 100 "AcDbEntity")
           (cons 67 0)
           (cons 8 "0")
           (cons 100 "AcDbPoint")
           (list 10 8.6 -1.3 0)
           (cons 50 0)
          )
         )
         (entmake
          (list
           (cons 0 "POINT")
           (cons 100 "AcDbEntity")
           (cons 67 0)
           (cons 8 "0")
           (cons 100 "AcDbPoint")
           (list 10 7.1 1.3 0)
           (cons 50 0)
          )
         )
         (entmake
          (list
           (cons 0 "POINT")
           (cons 100 "AcDbEntity")
           (cons 67 0)
           (cons 8 "0")
           (cons 100 "AcDbPoint")
           (list 10 7.1 -1.3 0)
           (cons 50 0)
          )
         )
         (entmake
          (list
           (cons 0 "POINT")
           (cons 100 "AcDbEntity")
           (cons 67 0)
           (cons 8 "0")
           (cons 100 "AcDbPoint")
           (list 10 8.6 0 0)
           (cons 50 0)
          )
         )
         (entmake
          (list
           (cons 0 "ATTDEF")
           (cons 100 "AcDbEntity")
           (cons 67 0)
           (cons 8 "0")
           (cons 100 "AcDbText")
           (list 10 -0.1 0.56666667 0)
           (cons 40 0.2)
           (cons 1 "0.600")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 0.23333333 0)
           (cons 40 0.2)
           (cons 1 "0.600")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 -0.1 0)
           (cons 40 0.2)
           (cons 1 "7.100")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 -0.43333333 0)
           (cons 40 0.2)
           (cons 1 "8.600")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-33-PUP"))
        (progn
         (entmake)
         (entmake
          (list
           (cons 0 "BLOCK")
           (cons 2 "AB_INF-WB-33-PUP")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 3)
           (cons 70 129)
           (cons 43 0)
           (cons 38 0)
           (cons 39 0)
           (list 10 0 0)
           (cons 40 0)
           (cons 41 0)
           (cons 42 0)
           (cons 91 0)
           (list 10 2.1 1.3)
           (cons 40 0)
           (cons 41 0)
           (cons 42 0)
           (cons 91 0)
           (list 10 2.1 -1.3)
           (cons 40 0)
           (cons 41 0)
           (cons 42 0)
           (cons 91 0)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 2.1 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 -0.7445528)
           (cons 40 0)
           (cons 41 0)
           (cons 42 0)
           (cons 91 0)
           (list 10 1.5412 -0.5702072)
           (cons 40 0)
           (cons 41 0)
           (cons 42 0)
           (cons 91 0)
           (list 10 1.697664 -0.51768)
           (cons 40 0)
           (cons 41 0)
           (cons 42 0)
           (cons 91 0)
           (list 10 2.502336 -0.51768)
           (cons 40 0)
           (cons 41 0)
           (cons 42 0)
           (cons 91 0)
           (list 10 2.6588 -0.5702072)
           (cons 40 0)
           (cons 41 0)
           (cons 42 0)
           (cons 91 0)
           (list 10 2.6588 -0.7445528)
           (cons 40 0)
           (cons 41 0)
           (cons 42 0)
           (cons 91 0)
           (list 10 2.502336 -0.79708)
           (cons 40 0)
           (cons 41 0)
           (cons 42 0)
           (cons 91 0)
           (list 10 1.697664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 -1.2474728)
           (cons 40 0)
           (cons 41 0)
           (cons 42 0)
           (cons 91 0)
           (list 10 1.5412 -1.0731272)
           (cons 40 0)
           (cons 41 0)
           (cons 42 0)
           (cons 91 0)
           (list 10 1.697664 -1.0206)
           (cons 40 0)
           (cons 41 0)
           (cons 42 0)
           (cons 91 0)
           (list 10 2.502336 -1.0206)
           (cons 40 0)
           (cons 41 0)
           (cons 42 0)
           (cons 91 0)
           (list 10 2.6588 -1.0731272)
           (cons 40 0)
           (cons 41 0)
           (cons 42 0)
           (cons 91 0)
           (list 10 2.6588 -1.2474728)
           (cons 40 0)
           (cons 41 0)
           (cons 42 0)
           (cons 91 0)
           (list 10 2.502336 -1.3)
           (cons 40 0)
           (cons 41 0)
           (cons 42 0)
           (cons 91 0)
           (list 10 1.697664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 0.5702072)
           (cons 40 0)
           (cons 41 0)
           (cons 42 0)
           (cons 91 0)
           (list 10 1.5412 0.7445528)
           (cons 40 0)
           (cons 41 0)
           (cons 42 0)
           (cons 91 0)
           (list 10 1.697664 0.79708)
           (cons 40 0)
           (cons 41 0)
           (cons 42 0)
           (cons 91 0)
           (list 10 2.502336 0.79708)
           (cons 40 0)
           (cons 41 0)
           (cons 42 0)
           (cons 91 0)
           (list 10 2.6588 0.7445528)
           (cons 40 0)
           (cons 41 0)
           (cons 42 0)
           (cons 91 0)
           (list 10 2.6588 0.5702072)
           (cons 40 0)
           (cons 41 0)
           (cons 42 0)
           (cons 91 0)
           (list 10 2.502336 0.51768)
           (cons 40 0)
           (cons 41 0)
           (cons 42 0)
           (cons 91 0)
           (list 10 1.697664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 1.0731272)
           (cons 40 0)
           (cons 41 0)
           (cons 42 0)
           (cons 91 0)
           (list 10 1.5412 1.2474728)
           (cons 40 0)
           (cons 41 0)
           (cons 42 0)
           (cons 91 0)
           (list 10 1.697664 1.3)
           (cons 40 0)
           (cons 41 0)
           (cons 42 0)
           (cons 91 0)
           (list 10 2.502336 1.3)
           (cons 40 0)
           (cons 41 0)
           (cons 42 0)
           (cons 91 0)
           (list 10 2.6588 1.2474728)
           (cons 40 0)
           (cons 41 0)
           (cons 42 0)
           (cons 91 0)
           (list 10 2.6588 1.0731272)
           (cons 40 0)
           (cons 41 0)
           (cons 42 0)
           (cons 91 0)
           (list 10 2.502336 1.0206)
           (cons 40 0)
           (cons 41 0)
           (cons 42 0)
           (cons 91 0)
           (list 10 1.697664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 2.1 1.3 0)
           (cons 50 0)
          )
         )
         (entmake
          (list
           (cons 0 "POINT")
           (cons 100 "AcDbEntity")
           (cons 67 0)
           (cons 8 "0")
           (cons 100 "AcDbPoint")
           (list 10 2.1 -1.3 0)
           (cons 50 0)
          )
         )
         (entmake
          (list
           (cons 0 "POINT")
           (cons 100 "AcDbEntity")
           (cons 67 0)
           (cons 8 "0")
           (cons 100 "AcDbPoint")
           (list 10 2.1 0 0)
           (cons 50 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "2.100")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "2.100")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-33-TRAILER1"))
        (progn
         (entmake)
         (entmake
          (list
           (cons 0 "BLOCK")
           (cons 2 "AB_INF-WB-33-TRAILER1")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 8.6 -1.3)
           (cons 40 0)
           (cons 41 0)
           (cons 42 0)
           (cons 91 0)
           (list 10 8.6 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.6 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.6 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9062 -0.7445528)
           (cons 40 0)
           (cons 41 0)
           (cons 42 0)
           (cons 91 0)
           (list 10 5.9062 -0.5702072)
           (cons 40 0)
           (cons 41 0)
           (cons 42 0)
           (cons 91 0)
           (list 10 6.062664 -0.51768)
           (cons 40 0)
           (cons 41 0)
           (cons 42 0)
           (cons 91 0)
           (list 10 6.867336 -0.51768)
           (cons 40 0)
           (cons 41 0)
           (cons 42 0)
           (cons 91 0)
           (list 10 7.0238 -0.5702072)
           (cons 40 0)
           (cons 41 0)
           (cons 42 0)
           (cons 91 0)
           (list 10 7.0238 -0.7445528)
           (cons 40 0)
           (cons 41 0)
           (cons 42 0)
           (cons 91 0)
           (list 10 6.867336 -0.79708)
           (cons 40 0)
           (cons 41 0)
           (cons 42 0)
           (cons 91 0)
           (list 10 6.062664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9062 -1.2474728)
           (cons 40 0)
           (cons 41 0)
           (cons 42 0)
           (cons 91 0)
           (list 10 5.9062 -1.0731272)
           (cons 40 0)
           (cons 41 0)
           (cons 42 0)
           (cons 91 0)
           (list 10 6.062664 -1.0206)
           (cons 40 0)
           (cons 41 0)
           (cons 42 0)
           (cons 91 0)
           (list 10 6.867336 -1.0206)
           (cons 40 0)
           (cons 41 0)
           (cons 42 0)
           (cons 91 0)
           (list 10 7.0238 -1.0731272)
           (cons 40 0)
           (cons 41 0)
           (cons 42 0)
           (cons 91 0)
           (list 10 7.0238 -1.2474728)
           (cons 40 0)
           (cons 41 0)
           (cons 42 0)
           (cons 91 0)
           (list 10 6.867336 -1.3)
           (cons 40 0)
           (cons 41 0)
           (cons 42 0)
           (cons 91 0)
           (list 10 6.062664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9062 0.5702072)
           (cons 40 0)
           (cons 41 0)
           (cons 42 0)
           (cons 91 0)
           (list 10 5.9062 0.7445528)
           (cons 40 0)
           (cons 41 0)
           (cons 42 0)
           (cons 91 0)
           (list 10 6.062664 0.79708)
           (cons 40 0)
           (cons 41 0)
           (cons 42 0)
           (cons 91 0)
           (list 10 6.867336 0.79708)
           (cons 40 0)
           (cons 41 0)
           (cons 42 0)
           (cons 91 0)
           (list 10 7.0238 0.7445528)
           (cons 40 0)
           (cons 41 0)
           (cons 42 0)
           (cons 91 0)
           (list 10 7.0238 0.5702072)
           (cons 40 0)
           (cons 41 0)
           (cons 42 0)
           (cons 91 0)
           (list 10 6.867336 0.51768)
           (cons 40 0)
           (cons 41 0)
           (cons 42 0)
           (cons 91 0)
           (list 10 6.062664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9062 1.0731272)
           (cons 40 0)
           (cons 41 0)
           (cons 42 0)
           (cons 91 0)
           (list 10 5.9062 1.2474728)
           (cons 40 0)
           (cons 41 0)
           (cons 42 0)
           (cons 91 0)
           (list 10 6.062664 1.3)
           (cons 40 0)
           (cons 41 0)
           (cons 42 0)
           (cons 91 0)
           (list 10 6.867336 1.3)
           (cons 40 0)
           (cons 41 0)
           (cons 42 0)
           (cons 91 0)
           (list 10 7.0238 1.2474728)
           (cons 40 0)
           (cons 41 0)
           (cons 42 0)
           (cons 91 0)
           (list 10 7.0238 1.0731272)
           (cons 40 0)
           (cons 41 0)
           (cons 42 0)
           (cons 91 0)
           (list 10 6.867336 1.0206)
           (cons 40 0)
           (cons 41 0)
           (cons 42 0)
           (cons 91 0)
           (list 10 6.062664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1762 -0.7445528)
           (cons 40 0)
           (cons 41 0)
           (cons 42 0)
           (cons 91 0)
           (list 10 7.1762 -0.5702072)
           (cons 40 0)
           (cons 41 0)
           (cons 42 0)
           (cons 91 0)
           (list 10 7.332664 -0.51768)
           (cons 40 0)
           (cons 41 0)
           (cons 42 0)
           (cons 91 0)
           (list 10 8.137336 -0.51768)
           (cons 40 0)
           (cons 41 0)
           (cons 42 0)
           (cons 91 0)
           (list 10 8.2938 -0.5702072)
           (cons 40 0)
           (cons 41 0)
           (cons 42 0)
           (cons 91 0)
           (list 10 8.2938 -0.7445528)
           (cons 40 0)
           (cons 41 0)
           (cons 42 0)
           (cons 91 0)
           (list 10 8.137336 -0.79708)
           (cons 40 0)
           (cons 41 0)
           (cons 42 0)
           (cons 91 0)
           (list 10 7.332664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1762 -1.2474728)
           (cons 40 0)
           (cons 41 0)
           (cons 42 0)
           (cons 91 0)
           (list 10 7.1762 -1.0731272)
           (cons 40 0)
           (cons 41 0)
           (cons 42 0)
           (cons 91 0)
           (list 10 7.332664 -1.0206)
           (cons 40 0)
           (cons 41 0)
           (cons 42 0)
           (cons 91 0)
           (list 10 8.137336 -1.0206)
           (cons 40 0)
           (cons 41 0)
           (cons 42 0)
           (cons 91 0)
           (list 10 8.2938 -1.0731272)
           (cons 40 0)
           (cons 41 0)
           (cons 42 0)
           (cons 91 0)
           (list 10 8.2938 -1.2474728)
           (cons 40 0)
           (cons 41 0)
           (cons 42 0)
           (cons 91 0)
           (list 10 8.137336 -1.3)
           (cons 40 0)
           (cons 41 0)
           (cons 42 0)
           (cons 91 0)
           (list 10 7.332664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1762 0.5702072)
           (cons 40 0)
           (cons 41 0)
           (cons 42 0)
           (cons 91 0)
           (list 10 7.1762 0.7445528)
           (cons 40 0)
           (cons 41 0)
           (cons 42 0)
           (cons 91 0)
           (list 10 7.332664 0.79708)
           (cons 40 0)
           (cons 41 0)
           (cons 42 0)
           (cons 91 0)
           (list 10 8.137336 0.79708)
           (cons 40 0)
           (cons 41 0)
           (cons 42 0)
           (cons 91 0)
           (list 10 8.2938 0.7445528)
           (cons 40 0)
           (cons 41 0)
           (cons 42 0)
           (cons 91 0)
           (list 10 8.2938 0.5702072)
           (cons 40 0)
           (cons 41 0)
           (cons 42 0)
           (cons 91 0)
           (list 10 8.137336 0.51768)
           (cons 40 0)
           (cons 41 0)
           (cons 42 0)
           (cons 91 0)
           (list 10 7.332664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1762 1.0731272)
           (cons 40 0)
           (cons 41 0)
           (cons 42 0)
           (cons 91 0)
           (list 10 7.1762 1.2474728)
           (cons 40 0)
           (cons 41 0)
           (cons 42 0)
           (cons 91 0)
           (list 10 7.332664 1.3)
           (cons 40 0)
           (cons 41 0)
           (cons 42 0)
           (cons 91 0)
           (list 10 8.137336 1.3)
           (cons 40 0)
           (cons 41 0)
           (cons 42 0)
           (cons 91 0)
           (list 10 8.2938 1.2474728)
           (cons 40 0)
           (cons 41 0)
           (cons 42 0)
           (cons 91 0)
           (list 10 8.2938 1.0731272)
           (cons 40 0)
           (cons 41 0)
           (cons 42 0)
           (cons 91 0)
           (list 10 8.137336 1.0206)
           (cons 40 0)
           (cons 41 0)
           (cons 42 0)
           (cons 91 0)
           (list 10 7.332664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0.6 0 0)
           (cons 50 0)
          )
         )
         (entmake
          (list
           (cons 0 "POINT")
           (cons 100 "AcDbEntity")
           (cons 67 0)
           (cons 8 "0")
           (cons 100 "AcDbPoint")
           (list 10 8.6 1.3 0)
           (cons 50 0)
          )
         )
         (entmake
          (list
           (cons 0 "POINT")
           (cons 100 "AcDbEntity")
           (cons 67 0)
           (cons 8 "0")
           (cons 100 "AcDbPoint")
           (list 10 8.6 -1.3 0)
           (cons 50 0)
          )
         )
         (entmake
          (list
           (cons 0 "POINT")
           (cons 100 "AcDbEntity")
           (cons 67 0)
           (cons 8 "0")
           (cons 100 "AcDbPoint")
           (list 10 7.1 1.3 0)
           (cons 50 0)
          )
         )
         (entmake
          (list
           (cons 0 "POINT")
           (cons 100 "AcDbEntity")
           (cons 67 0)
           (cons 8 "0")
           (cons 100 "AcDbPoint")
           (list 10 7.1 -1.3 0)
           (cons 50 0)
          )
         )
         (entmake
          (list
           (cons 0 "POINT")
           (cons 100 "AcDbEntity")
           (cons 67 0)
           (cons 8 "0")
           (cons 100 "AcDbPoint")
           (list 10 8.6 0 0)
           (cons 50 0)
          )
         )
         (entmake
          (list
           (cons 0 "ATTDEF")
           (cons 100 "AcDbEntity")
           (cons 67 0)
           (cons 8 "0")
           (cons 100 "AcDbText")
           (list 10 -0.1 0.56666667 0)
           (cons 40 0.2)
           (cons 1 "0.600")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 0.23333333 0)
           (cons 40 0.2)
           (cons 1 "0.600")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 -0.1 0)
           (cons 40 0.2)
           (cons 1 "7.100")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 -0.43333333 0)
           (cons 40 0.2)
           (cons 1 "8.600")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-33-TRUCK"))
        (progn
         (entmake)
         (entmake
          (list
           (cons 0 "BLOCK")
           (cons 2 "AB_INF-WB-33-TRUCK")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 7.435 -1.3)
           (cons 40 0)
           (cons 41 0)
           (cons 42 0)
           (cons 91 0)
           (list 10 7.435 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.435 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.435 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 6.8 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 7.06263966 -0.26263966 0)
           (list 11 7.06263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.6062 -0.7445528)
           (cons 40 0)
           (cons 41 0)
           (cons 42 0)
           (cons 91 0)
           (list 10 5.6062 -0.5702072)
           (cons 40 0)
           (cons 41 0)
           (cons 42 0)
           (cons 91 0)
           (list 10 5.762664 -0.51768)
           (cons 40 0)
           (cons 41 0)
           (cons 42 0)
           (cons 91 0)
           (list 10 6.567336 -0.51768)
           (cons 40 0)
           (cons 41 0)
           (cons 42 0)
           (cons 91 0)
           (list 10 6.7238 -0.5702072)
           (cons 40 0)
           (cons 41 0)
           (cons 42 0)
           (cons 91 0)
           (list 10 6.7238 -0.7445528)
           (cons 40 0)
           (cons 41 0)
           (cons 42 0)
           (cons 91 0)
           (list 10 6.567336 -0.79708)
           (cons 40 0)
           (cons 41 0)
           (cons 42 0)
           (cons 91 0)
           (list 10 5.762664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.6062 -1.2474728)
           (cons 40 0)
           (cons 41 0)
           (cons 42 0)
           (cons 91 0)
           (list 10 5.6062 -1.0731272)
           (cons 40 0)
           (cons 41 0)
           (cons 42 0)
           (cons 91 0)
           (list 10 5.762664 -1.0206)
           (cons 40 0)
           (cons 41 0)
           (cons 42 0)
           (cons 91 0)
           (list 10 6.567336 -1.0206)
           (cons 40 0)
           (cons 41 0)
           (cons 42 0)
           (cons 91 0)
           (list 10 6.7238 -1.0731272)
           (cons 40 0)
           (cons 41 0)
           (cons 42 0)
           (cons 91 0)
           (list 10 6.7238 -1.2474728)
           (cons 40 0)
           (cons 41 0)
           (cons 42 0)
           (cons 91 0)
           (list 10 6.567336 -1.3)
           (cons 40 0)
           (cons 41 0)
           (cons 42 0)
           (cons 91 0)
           (list 10 5.762664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.6062 0.5702072)
           (cons 40 0)
           (cons 41 0)
           (cons 42 0)
           (cons 91 0)
           (list 10 5.6062 0.7445528)
           (cons 40 0)
           (cons 41 0)
           (cons 42 0)
           (cons 91 0)
           (list 10 5.762664 0.79708)
           (cons 40 0)
           (cons 41 0)
           (cons 42 0)
           (cons 91 0)
           (list 10 6.567336 0.79708)
           (cons 40 0)
           (cons 41 0)
           (cons 42 0)
           (cons 91 0)
           (list 10 6.7238 0.7445528)
           (cons 40 0)
           (cons 41 0)
           (cons 42 0)
           (cons 91 0)
           (list 10 6.7238 0.5702072)
           (cons 40 0)
           (cons 41 0)
           (cons 42 0)
           (cons 91 0)
           (list 10 6.567336 0.51768)
           (cons 40 0)
           (cons 41 0)
           (cons 42 0)
           (cons 91 0)
           (list 10 5.762664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.6062 1.0731272)
           (cons 40 0)
           (cons 41 0)
           (cons 42 0)
           (cons 91 0)
           (list 10 5.6062 1.2474728)
           (cons 40 0)
           (cons 41 0)
           (cons 42 0)
           (cons 91 0)
           (list 10 5.762664 1.3)
           (cons 40 0)
           (cons 41 0)
           (cons 42 0)
           (cons 91 0)
           (list 10 6.567336 1.3)
           (cons 40 0)
           (cons 41 0)
           (cons 42 0)
           (cons 91 0)
           (list 10 6.7238 1.2474728)
           (cons 40 0)
           (cons 41 0)
           (cons 42 0)
           (cons 91 0)
           (list 10 6.7238 1.0731272)
           (cons 40 0)
           (cons 41 0)
           (cons 42 0)
           (cons 91 0)
           (list 10 6.567336 1.0206)
           (cons 40 0)
           (cons 41 0)
           (cons 42 0)
           (cons 91 0)
           (list 10 5.762664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.8762 -0.7445528)
           (cons 40 0)
           (cons 41 0)
           (cons 42 0)
           (cons 91 0)
           (list 10 6.8762 -0.5702072)
           (cons 40 0)
           (cons 41 0)
           (cons 42 0)
           (cons 91 0)
           (list 10 7.032664 -0.51768)
           (cons 40 0)
           (cons 41 0)
           (cons 42 0)
           (cons 91 0)
           (list 10 7.837336 -0.51768)
           (cons 40 0)
           (cons 41 0)
           (cons 42 0)
           (cons 91 0)
           (list 10 7.9938 -0.5702072)
           (cons 40 0)
           (cons 41 0)
           (cons 42 0)
           (cons 91 0)
           (list 10 7.9938 -0.7445528)
           (cons 40 0)
           (cons 41 0)
           (cons 42 0)
           (cons 91 0)
           (list 10 7.837336 -0.79708)
           (cons 40 0)
           (cons 41 0)
           (cons 42 0)
           (cons 91 0)
           (list 10 7.032664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.8762 -1.2474728)
           (cons 40 0)
           (cons 41 0)
           (cons 42 0)
           (cons 91 0)
           (list 10 6.8762 -1.0731272)
           (cons 40 0)
           (cons 41 0)
           (cons 42 0)
           (cons 91 0)
           (list 10 7.032664 -1.0206)
           (cons 40 0)
           (cons 41 0)
           (cons 42 0)
           (cons 91 0)
           (list 10 7.837336 -1.0206)
           (cons 40 0)
           (cons 41 0)
           (cons 42 0)
           (cons 91 0)
           (list 10 7.9938 -1.0731272)
           (cons 40 0)
           (cons 41 0)
           (cons 42 0)
           (cons 91 0)
           (list 10 7.9938 -1.2474728)
           (cons 40 0)
           (cons 41 0)
           (cons 42 0)
           (cons 91 0)
           (list 10 7.837336 -1.3)
           (cons 40 0)
           (cons 41 0)
           (cons 42 0)
           (cons 91 0)
           (list 10 7.032664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.8762 0.5702072)
           (cons 40 0)
           (cons 41 0)
           (cons 42 0)
           (cons 91 0)
           (list 10 6.8762 0.7445528)
           (cons 40 0)
           (cons 41 0)
           (cons 42 0)
           (cons 91 0)
           (list 10 7.032664 0.79708)
           (cons 40 0)
           (cons 41 0)
           (cons 42 0)
           (cons 91 0)
           (list 10 7.837336 0.79708)
           (cons 40 0)
           (cons 41 0)
           (cons 42 0)
           (cons 91 0)
           (list 10 7.9938 0.7445528)
           (cons 40 0)
           (cons 41 0)
           (cons 42 0)
           (cons 91 0)
           (list 10 7.9938 0.5702072)
           (cons 40 0)
           (cons 41 0)
           (cons 42 0)
           (cons 91 0)
           (list 10 7.837336 0.51768)
           (cons 40 0)
           (cons 41 0)
           (cons 42 0)
           (cons 91 0)
           (list 10 7.032664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.8762 1.0731272)
           (cons 40 0)
           (cons 41 0)
           (cons 42 0)
           (cons 91 0)
           (list 10 6.8762 1.2474728)
           (cons 40 0)
           (cons 41 0)
           (cons 42 0)
           (cons 91 0)
           (list 10 7.032664 1.3)
           (cons 40 0)
           (cons 41 0)
           (cons 42 0)
           (cons 91 0)
           (list 10 7.837336 1.3)
           (cons 40 0)
           (cons 41 0)
           (cons 42 0)
           (cons 91 0)
           (list 10 7.9938 1.2474728)
           (cons 40 0)
           (cons 41 0)
           (cons 42 0)
           (cons 91 0)
           (list 10 7.9938 1.0731272)
           (cons 40 0)
           (cons 41 0)
           (cons 42 0)
           (cons 91 0)
           (list 10 7.837336 1.0206)
           (cons 40 0)
           (cons 41 0)
           (cons 42 0)
           (cons 91 0)
           (list 10 7.032664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0.7 0 0)
           (cons 50 0)
          )
         )
         (entmake
          (list
           (cons 0 "INSERT")
           (cons 100 "AcDbEntity")
           (cons 67 0)
           (cons 8 "0")
           (cons 100 "AcDbBlockReference")
           (cons 2 "WheelRightM1")
           (list 10 0.7 -1.3 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM1")
           (list 10 0.7 1.3 0)
           (cons 41 1)
           (cons 42 1)
           (cons 43 1)
           (cons 50 0)
           (cons 70 0)
           (cons 71 0)
           (cons 44 0)
           (cons 45 0)
          )
         )
         (entmake
          (list
           (cons 0 "POINT")
           (cons 100 "AcDbEntity")
           (cons 67 0)
           (cons 8 "0")
           (cons 100 "AcDbPoint")
           (list 10 6.8 1.3 0)
           (cons 50 0)
          )
         )
         (entmake
          (list
           (cons 0 "POINT")
           (cons 100 "AcDbEntity")
           (cons 67 0)
           (cons 8 "0")
           (cons 100 "AcDbPoint")
           (list 10 6.8 -1.3 0)
           (cons 50 0)
          )
         )
         (entmake
          (list
           (cons 0 "POINT")
           (cons 100 "AcDbEntity")
           (cons 67 0)
           (cons 8 "0")
           (cons 100 "AcDbPoint")
           (list 10 6.8 0 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0.7 -1.3 0)
           (cons 50 0)
          )
         )
         (entmake
          (list
           (cons 0 "POINT")
           (cons 100 "AcDbEntity")
           (cons 67 0)
           (cons 8 "0")
           (cons 100 "AcDbPoint")
           (list 10 0.7 1.3 0)
           (cons 50 0)
          )
         )
         (entmake
          (list
           (cons 0 "ATTDEF")
           (cons 100 "AcDbEntity")
           (cons 67 0)
           (cons 8 "0")
           (cons 100 "AcDbText")
           (list 10 0 0.56666667 0)
           (cons 40 0.2)
           (cons 1 "0.700")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0 0.23333333 0)
           (cons 40 0.2)
           (cons 1 "0.700")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0 -0.1 0)
           (cons 40 0.2)
           (cons 1 "6.800")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0 -0.43333333 0)
           (cons 40 0.2)
           (cons 1 "6.800")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0 -0.76666667 0)
           (cons 40 0.2)
           (cons 1 "25.22")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-28-TRAILER2"))
        (progn
         (entmake)
         (entmake
          (list
           (cons 0 "BLOCK")
           (cons 2 "AB_INF-WB-28-TRAILER2")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 -1.3)
           (cons 40 0)
           (cons 41 0)
           (cons 42 0)
           (cons 91 0)
           (list 10 8.5 -1.3)
           (cons 40 0)
           (cons 41 0)
           (cons 42 0)
           (cons 91 0)
           (list 10 8.5 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.5 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.5 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9062 -0.7445528)
           (cons 40 0)
           (cons 41 0)
           (cons 42 0)
           (cons 91 0)
           (list 10 5.9062 -0.5702072)
           (cons 40 0)
           (cons 41 0)
           (cons 42 0)
           (cons 91 0)
           (list 10 6.062664 -0.51768)
           (cons 40 0)
           (cons 41 0)
           (cons 42 0)
           (cons 91 0)
           (list 10 6.867336 -0.51768)
           (cons 40 0)
           (cons 41 0)
           (cons 42 0)
           (cons 91 0)
           (list 10 7.0238 -0.5702072)
           (cons 40 0)
           (cons 41 0)
           (cons 42 0)
           (cons 91 0)
           (list 10 7.0238 -0.7445528)
           (cons 40 0)
           (cons 41 0)
           (cons 42 0)
           (cons 91 0)
           (list 10 6.867336 -0.79708)
           (cons 40 0)
           (cons 41 0)
           (cons 42 0)
           (cons 91 0)
           (list 10 6.062664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9062 -1.2474728)
           (cons 40 0)
           (cons 41 0)
           (cons 42 0)
           (cons 91 0)
           (list 10 5.9062 -1.0731272)
           (cons 40 0)
           (cons 41 0)
           (cons 42 0)
           (cons 91 0)
           (list 10 6.062664 -1.0206)
           (cons 40 0)
           (cons 41 0)
           (cons 42 0)
           (cons 91 0)
           (list 10 6.867336 -1.0206)
           (cons 40 0)
           (cons 41 0)
           (cons 42 0)
           (cons 91 0)
           (list 10 7.0238 -1.0731272)
           (cons 40 0)
           (cons 41 0)
           (cons 42 0)
           (cons 91 0)
           (list 10 7.0238 -1.2474728)
           (cons 40 0)
           (cons 41 0)
           (cons 42 0)
           (cons 91 0)
           (list 10 6.867336 -1.3)
           (cons 40 0)
           (cons 41 0)
           (cons 42 0)
           (cons 91 0)
           (list 10 6.062664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9062 0.5702072)
           (cons 40 0)
           (cons 41 0)
           (cons 42 0)
           (cons 91 0)
           (list 10 5.9062 0.7445528)
           (cons 40 0)
           (cons 41 0)
           (cons 42 0)
           (cons 91 0)
           (list 10 6.062664 0.79708)
           (cons 40 0)
           (cons 41 0)
           (cons 42 0)
           (cons 91 0)
           (list 10 6.867336 0.79708)
           (cons 40 0)
           (cons 41 0)
           (cons 42 0)
           (cons 91 0)
           (list 10 7.0238 0.7445528)
           (cons 40 0)
           (cons 41 0)
           (cons 42 0)
           (cons 91 0)
           (list 10 7.0238 0.5702072)
           (cons 40 0)
           (cons 41 0)
           (cons 42 0)
           (cons 91 0)
           (list 10 6.867336 0.51768)
           (cons 40 0)
           (cons 41 0)
           (cons 42 0)
           (cons 91 0)
           (list 10 6.062664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9062 1.0731272)
           (cons 40 0)
           (cons 41 0)
           (cons 42 0)
           (cons 91 0)
           (list 10 5.9062 1.2474728)
           (cons 40 0)
           (cons 41 0)
           (cons 42 0)
           (cons 91 0)
           (list 10 6.062664 1.3)
           (cons 40 0)
           (cons 41 0)
           (cons 42 0)
           (cons 91 0)
           (list 10 6.867336 1.3)
           (cons 40 0)
           (cons 41 0)
           (cons 42 0)
           (cons 91 0)
           (list 10 7.0238 1.2474728)
           (cons 40 0)
           (cons 41 0)
           (cons 42 0)
           (cons 91 0)
           (list 10 7.0238 1.0731272)
           (cons 40 0)
           (cons 41 0)
           (cons 42 0)
           (cons 91 0)
           (list 10 6.867336 1.0206)
           (cons 40 0)
           (cons 41 0)
           (cons 42 0)
           (cons 91 0)
           (list 10 6.062664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1762 -0.7445528)
           (cons 40 0)
           (cons 41 0)
           (cons 42 0)
           (cons 91 0)
           (list 10 7.1762 -0.5702072)
           (cons 40 0)
           (cons 41 0)
           (cons 42 0)
           (cons 91 0)
           (list 10 7.332664 -0.51768)
           (cons 40 0)
           (cons 41 0)
           (cons 42 0)
           (cons 91 0)
           (list 10 8.137336 -0.51768)
           (cons 40 0)
           (cons 41 0)
           (cons 42 0)
           (cons 91 0)
           (list 10 8.2938 -0.5702072)
           (cons 40 0)
           (cons 41 0)
           (cons 42 0)
           (cons 91 0)
           (list 10 8.2938 -0.7445528)
           (cons 40 0)
           (cons 41 0)
           (cons 42 0)
           (cons 91 0)
           (list 10 8.137336 -0.79708)
           (cons 40 0)
           (cons 41 0)
           (cons 42 0)
           (cons 91 0)
           (list 10 7.332664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1762 -1.2474728)
           (cons 40 0)
           (cons 41 0)
           (cons 42 0)
           (cons 91 0)
           (list 10 7.1762 -1.0731272)
           (cons 40 0)
           (cons 41 0)
           (cons 42 0)
           (cons 91 0)
           (list 10 7.332664 -1.0206)
           (cons 40 0)
           (cons 41 0)
           (cons 42 0)
           (cons 91 0)
           (list 10 8.137336 -1.0206)
           (cons 40 0)
           (cons 41 0)
           (cons 42 0)
           (cons 91 0)
           (list 10 8.2938 -1.0731272)
           (cons 40 0)
           (cons 41 0)
           (cons 42 0)
           (cons 91 0)
           (list 10 8.2938 -1.2474728)
           (cons 40 0)
           (cons 41 0)
           (cons 42 0)
           (cons 91 0)
           (list 10 8.137336 -1.3)
           (cons 40 0)
           (cons 41 0)
           (cons 42 0)
           (cons 91 0)
           (list 10 7.332664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1762 0.5702072)
           (cons 40 0)
           (cons 41 0)
           (cons 42 0)
           (cons 91 0)
           (list 10 7.1762 0.7445528)
           (cons 40 0)
           (cons 41 0)
           (cons 42 0)
           (cons 91 0)
           (list 10 7.332664 0.79708)
           (cons 40 0)
           (cons 41 0)
           (cons 42 0)
           (cons 91 0)
           (list 10 8.137336 0.79708)
           (cons 40 0)
           (cons 41 0)
           (cons 42 0)
           (cons 91 0)
           (list 10 8.2938 0.7445528)
           (cons 40 0)
           (cons 41 0)
           (cons 42 0)
           (cons 91 0)
           (list 10 8.2938 0.5702072)
           (cons 40 0)
           (cons 41 0)
           (cons 42 0)
           (cons 91 0)
           (list 10 8.137336 0.51768)
           (cons 40 0)
           (cons 41 0)
           (cons 42 0)
           (cons 91 0)
           (list 10 7.332664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1762 1.0731272)
           (cons 40 0)
           (cons 41 0)
           (cons 42 0)
           (cons 91 0)
           (list 10 7.1762 1.2474728)
           (cons 40 0)
           (cons 41 0)
           (cons 42 0)
           (cons 91 0)
           (list 10 7.332664 1.3)
           (cons 40 0)
           (cons 41 0)
           (cons 42 0)
           (cons 91 0)
           (list 10 8.137336 1.3)
           (cons 40 0)
           (cons 41 0)
           (cons 42 0)
           (cons 91 0)
           (list 10 8.2938 1.2474728)
           (cons 40 0)
           (cons 41 0)
           (cons 42 0)
           (cons 91 0)
           (list 10 8.2938 1.0731272)
           (cons 40 0)
           (cons 41 0)
           (cons 42 0)
           (cons 91 0)
           (list 10 8.137336 1.0206)
           (cons 40 0)
           (cons 41 0)
           (cons 42 0)
           (cons 91 0)
           (list 10 7.332664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0.6 0 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 8.5 1.3 0)
           (cons 50 0)
          )
         )
         (entmake
          (list
           (cons 0 "POINT")
           (cons 100 "AcDbEntity")
           (cons 67 0)
           (cons 8 "0")
           (cons 100 "AcDbPoint")
           (list 10 8.5 -1.3 0)
           (cons 50 0)
          )
         )
         (entmake
          (list
           (cons 0 "POINT")
           (cons 100 "AcDbEntity")
           (cons 67 0)
           (cons 8 "0")
           (cons 100 "AcDbPoint")
           (list 10 7.1 1.3 0)
           (cons 50 0)
          )
         )
         (entmake
          (list
           (cons 0 "POINT")
           (cons 100 "AcDbEntity")
           (cons 67 0)
           (cons 8 "0")
           (cons 100 "AcDbPoint")
           (list 10 7.1 -1.3 0)
           (cons 50 0)
          )
         )
         (entmake
          (list
           (cons 0 "ATTDEF")
           (cons 100 "AcDbEntity")
           (cons 67 0)
           (cons 8 "0")
           (cons 100 "AcDbText")
           (list 10 -0.1 0.56666667 0)
           (cons 40 0.2)
           (cons 1 "0.600")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 0.23333333 0)
           (cons 40 0.2)
           (cons 1 "0.600")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 -0.1 0)
           (cons 40 0.2)
           (cons 1 "7.100")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-28-PUP"))
        (progn
         (entmake)
         (entmake
          (list
           (cons 0 "BLOCK")
           (cons 2 "AB_INF-WB-28-PUP")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 3)
           (cons 70 129)
           (cons 43 0)
           (cons 38 0)
           (cons 39 0)
           (list 10 0 0)
           (cons 40 0)
           (cons 41 0)
           (cons 42 0)
           (cons 91 0)
           (list 10 2.1 1.3)
           (cons 40 0)
           (cons 41 0)
           (cons 42 0)
           (cons 91 0)
           (list 10 2.1 -1.3)
           (cons 40 0)
           (cons 41 0)
           (cons 42 0)
           (cons 91 0)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 2.1 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 -0.7445528)
           (cons 40 0)
           (cons 41 0)
           (cons 42 0)
           (cons 91 0)
           (list 10 1.5412 -0.5702072)
           (cons 40 0)
           (cons 41 0)
           (cons 42 0)
           (cons 91 0)
           (list 10 1.697664 -0.51768)
           (cons 40 0)
           (cons 41 0)
           (cons 42 0)
           (cons 91 0)
           (list 10 2.502336 -0.51768)
           (cons 40 0)
           (cons 41 0)
           (cons 42 0)
           (cons 91 0)
           (list 10 2.6588 -0.5702072)
           (cons 40 0)
           (cons 41 0)
           (cons 42 0)
           (cons 91 0)
           (list 10 2.6588 -0.7445528)
           (cons 40 0)
           (cons 41 0)
           (cons 42 0)
           (cons 91 0)
           (list 10 2.502336 -0.79708)
           (cons 40 0)
           (cons 41 0)
           (cons 42 0)
           (cons 91 0)
           (list 10 1.697664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 -1.2474728)
           (cons 40 0)
           (cons 41 0)
           (cons 42 0)
           (cons 91 0)
           (list 10 1.5412 -1.0731272)
           (cons 40 0)
           (cons 41 0)
           (cons 42 0)
           (cons 91 0)
           (list 10 1.697664 -1.0206)
           (cons 40 0)
           (cons 41 0)
           (cons 42 0)
           (cons 91 0)
           (list 10 2.502336 -1.0206)
           (cons 40 0)
           (cons 41 0)
           (cons 42 0)
           (cons 91 0)
           (list 10 2.6588 -1.0731272)
           (cons 40 0)
           (cons 41 0)
           (cons 42 0)
           (cons 91 0)
           (list 10 2.6588 -1.2474728)
           (cons 40 0)
           (cons 41 0)
           (cons 42 0)
           (cons 91 0)
           (list 10 2.502336 -1.3)
           (cons 40 0)
           (cons 41 0)
           (cons 42 0)
           (cons 91 0)
           (list 10 1.697664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 0.5702072)
           (cons 40 0)
           (cons 41 0)
           (cons 42 0)
           (cons 91 0)
           (list 10 1.5412 0.7445528)
           (cons 40 0)
           (cons 41 0)
           (cons 42 0)
           (cons 91 0)
           (list 10 1.697664 0.79708)
           (cons 40 0)
           (cons 41 0)
           (cons 42 0)
           (cons 91 0)
           (list 10 2.502336 0.79708)
           (cons 40 0)
           (cons 41 0)
           (cons 42 0)
           (cons 91 0)
           (list 10 2.6588 0.7445528)
           (cons 40 0)
           (cons 41 0)
           (cons 42 0)
           (cons 91 0)
           (list 10 2.6588 0.5702072)
           (cons 40 0)
           (cons 41 0)
           (cons 42 0)
           (cons 91 0)
           (list 10 2.502336 0.51768)
           (cons 40 0)
           (cons 41 0)
           (cons 42 0)
           (cons 91 0)
           (list 10 1.697664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 1.0731272)
           (cons 40 0)
           (cons 41 0)
           (cons 42 0)
           (cons 91 0)
           (list 10 1.5412 1.2474728)
           (cons 40 0)
           (cons 41 0)
           (cons 42 0)
           (cons 91 0)
           (list 10 1.697664 1.3)
           (cons 40 0)
           (cons 41 0)
           (cons 42 0)
           (cons 91 0)
           (list 10 2.502336 1.3)
           (cons 40 0)
           (cons 41 0)
           (cons 42 0)
           (cons 91 0)
           (list 10 2.6588 1.2474728)
           (cons 40 0)
           (cons 41 0)
           (cons 42 0)
           (cons 91 0)
           (list 10 2.6588 1.0731272)
           (cons 40 0)
           (cons 41 0)
           (cons 42 0)
           (cons 91 0)
           (list 10 2.502336 1.0206)
           (cons 40 0)
           (cons 41 0)
           (cons 42 0)
           (cons 91 0)
           (list 10 1.697664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 2.1 1.3 0)
           (cons 50 0)
          )
         )
         (entmake
          (list
           (cons 0 "POINT")
           (cons 100 "AcDbEntity")
           (cons 67 0)
           (cons 8 "0")
           (cons 100 "AcDbPoint")
           (list 10 2.1 -1.3 0)
           (cons 50 0)
          )
         )
         (entmake
          (list
           (cons 0 "POINT")
           (cons 100 "AcDbEntity")
           (cons 67 0)
           (cons 8 "0")
           (cons 100 "AcDbPoint")
           (list 10 2.1 0 0)
           (cons 50 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "2.100")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "2.100")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-28-TRAILER1"))
        (progn
         (entmake)
         (entmake
          (list
           (cons 0 "BLOCK")
           (cons 2 "AB_INF-WB-28-TRAILER1")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 -1.3)
           (cons 40 0)
           (cons 41 0)
           (cons 42 0)
           (cons 91 0)
           (list 10 16.2 -1.3)
           (cons 40 0)
           (cons 41 0)
           (cons 42 0)
           (cons 91 0)
           (list 10 16.2 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 16.2 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 16.2 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.2062 -0.7445528)
           (cons 40 0)
           (cons 41 0)
           (cons 42 0)
           (cons 91 0)
           (list 10 13.2062 -0.5702072)
           (cons 40 0)
           (cons 41 0)
           (cons 42 0)
           (cons 91 0)
           (list 10 13.362664 -0.51768)
           (cons 40 0)
           (cons 41 0)
           (cons 42 0)
           (cons 91 0)
           (list 10 14.167336 -0.51768)
           (cons 40 0)
           (cons 41 0)
           (cons 42 0)
           (cons 91 0)
           (list 10 14.3238 -0.5702072)
           (cons 40 0)
           (cons 41 0)
           (cons 42 0)
           (cons 91 0)
           (list 10 14.3238 -0.7445528)
           (cons 40 0)
           (cons 41 0)
           (cons 42 0)
           (cons 91 0)
           (list 10 14.167336 -0.79708)
           (cons 40 0)
           (cons 41 0)
           (cons 42 0)
           (cons 91 0)
           (list 10 13.362664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.2062 -1.2474728)
           (cons 40 0)
           (cons 41 0)
           (cons 42 0)
           (cons 91 0)
           (list 10 13.2062 -1.0731272)
           (cons 40 0)
           (cons 41 0)
           (cons 42 0)
           (cons 91 0)
           (list 10 13.362664 -1.0206)
           (cons 40 0)
           (cons 41 0)
           (cons 42 0)
           (cons 91 0)
           (list 10 14.167336 -1.0206)
           (cons 40 0)
           (cons 41 0)
           (cons 42 0)
           (cons 91 0)
           (list 10 14.3238 -1.0731272)
           (cons 40 0)
           (cons 41 0)
           (cons 42 0)
           (cons 91 0)
           (list 10 14.3238 -1.2474728)
           (cons 40 0)
           (cons 41 0)
           (cons 42 0)
           (cons 91 0)
           (list 10 14.167336 -1.3)
           (cons 40 0)
           (cons 41 0)
           (cons 42 0)
           (cons 91 0)
           (list 10 13.362664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.2062 0.5702072)
           (cons 40 0)
           (cons 41 0)
           (cons 42 0)
           (cons 91 0)
           (list 10 13.2062 0.7445528)
           (cons 40 0)
           (cons 41 0)
           (cons 42 0)
           (cons 91 0)
           (list 10 13.362664 0.79708)
           (cons 40 0)
           (cons 41 0)
           (cons 42 0)
           (cons 91 0)
           (list 10 14.167336 0.79708)
           (cons 40 0)
           (cons 41 0)
           (cons 42 0)
           (cons 91 0)
           (list 10 14.3238 0.7445528)
           (cons 40 0)
           (cons 41 0)
           (cons 42 0)
           (cons 91 0)
           (list 10 14.3238 0.5702072)
           (cons 40 0)
           (cons 41 0)
           (cons 42 0)
           (cons 91 0)
           (list 10 14.167336 0.51768)
           (cons 40 0)
           (cons 41 0)
           (cons 42 0)
           (cons 91 0)
           (list 10 13.362664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.2062 1.0731272)
           (cons 40 0)
           (cons 41 0)
           (cons 42 0)
           (cons 91 0)
           (list 10 13.2062 1.2474728)
           (cons 40 0)
           (cons 41 0)
           (cons 42 0)
           (cons 91 0)
           (list 10 13.362664 1.3)
           (cons 40 0)
           (cons 41 0)
           (cons 42 0)
           (cons 91 0)
           (list 10 14.167336 1.3)
           (cons 40 0)
           (cons 41 0)
           (cons 42 0)
           (cons 91 0)
           (list 10 14.3238 1.2474728)
           (cons 40 0)
           (cons 41 0)
           (cons 42 0)
           (cons 91 0)
           (list 10 14.3238 1.0731272)
           (cons 40 0)
           (cons 41 0)
           (cons 42 0)
           (cons 91 0)
           (list 10 14.167336 1.0206)
           (cons 40 0)
           (cons 41 0)
           (cons 42 0)
           (cons 91 0)
           (list 10 13.362664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.4762 -0.7445528)
           (cons 40 0)
           (cons 41 0)
           (cons 42 0)
           (cons 91 0)
           (list 10 14.4762 -0.5702072)
           (cons 40 0)
           (cons 41 0)
           (cons 42 0)
           (cons 91 0)
           (list 10 14.632664 -0.51768)
           (cons 40 0)
           (cons 41 0)
           (cons 42 0)
           (cons 91 0)
           (list 10 15.437336 -0.51768)
           (cons 40 0)
           (cons 41 0)
           (cons 42 0)
           (cons 91 0)
           (list 10 15.5938 -0.5702072)
           (cons 40 0)
           (cons 41 0)
           (cons 42 0)
           (cons 91 0)
           (list 10 15.5938 -0.7445528)
           (cons 40 0)
           (cons 41 0)
           (cons 42 0)
           (cons 91 0)
           (list 10 15.437336 -0.79708)
           (cons 40 0)
           (cons 41 0)
           (cons 42 0)
           (cons 91 0)
           (list 10 14.632664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.4762 -1.2474728)
           (cons 40 0)
           (cons 41 0)
           (cons 42 0)
           (cons 91 0)
           (list 10 14.4762 -1.0731272)
           (cons 40 0)
           (cons 41 0)
           (cons 42 0)
           (cons 91 0)
           (list 10 14.632664 -1.0206)
           (cons 40 0)
           (cons 41 0)
           (cons 42 0)
           (cons 91 0)
           (list 10 15.437336 -1.0206)
           (cons 40 0)
           (cons 41 0)
           (cons 42 0)
           (cons 91 0)
           (list 10 15.5938 -1.0731272)
           (cons 40 0)
           (cons 41 0)
           (cons 42 0)
           (cons 91 0)
           (list 10 15.5938 -1.2474728)
           (cons 40 0)
           (cons 41 0)
           (cons 42 0)
           (cons 91 0)
           (list 10 15.437336 -1.3)
           (cons 40 0)
           (cons 41 0)
           (cons 42 0)
           (cons 91 0)
           (list 10 14.632664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.4762 0.5702072)
           (cons 40 0)
           (cons 41 0)
           (cons 42 0)
           (cons 91 0)
           (list 10 14.4762 0.7445528)
           (cons 40 0)
           (cons 41 0)
           (cons 42 0)
           (cons 91 0)
           (list 10 14.632664 0.79708)
           (cons 40 0)
           (cons 41 0)
           (cons 42 0)
           (cons 91 0)
           (list 10 15.437336 0.79708)
           (cons 40 0)
           (cons 41 0)
           (cons 42 0)
           (cons 91 0)
           (list 10 15.5938 0.7445528)
           (cons 40 0)
           (cons 41 0)
           (cons 42 0)
           (cons 91 0)
           (list 10 15.5938 0.5702072)
           (cons 40 0)
           (cons 41 0)
           (cons 42 0)
           (cons 91 0)
           (list 10 15.437336 0.51768)
           (cons 40 0)
           (cons 41 0)
           (cons 42 0)
           (cons 91 0)
           (list 10 14.632664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.4762 1.0731272)
           (cons 40 0)
           (cons 41 0)
           (cons 42 0)
           (cons 91 0)
           (list 10 14.4762 1.2474728)
           (cons 40 0)
           (cons 41 0)
           (cons 42 0)
           (cons 91 0)
           (list 10 14.632664 1.3)
           (cons 40 0)
           (cons 41 0)
           (cons 42 0)
           (cons 91 0)
           (list 10 15.437336 1.3)
           (cons 40 0)
           (cons 41 0)
           (cons 42 0)
           (cons 91 0)
           (list 10 15.5938 1.2474728)
           (cons 40 0)
           (cons 41 0)
           (cons 42 0)
           (cons 91 0)
           (list 10 15.5938 1.0731272)
           (cons 40 0)
           (cons 41 0)
           (cons 42 0)
           (cons 91 0)
           (list 10 15.437336 1.0206)
           (cons 40 0)
           (cons 41 0)
           (cons 42 0)
           (cons 91 0)
           (list 10 14.632664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 1.9 0 0)
           (cons 50 0)
          )
         )
         (entmake
          (list
           (cons 0 "POINT")
           (cons 100 "AcDbEntity")
           (cons 67 0)
           (cons 8 "0")
           (cons 100 "AcDbPoint")
           (list 10 14.4 1.3 0)
           (cons 50 0)
          )
         )
         (entmake
          (list
           (cons 0 "POINT")
           (cons 100 "AcDbEntity")
           (cons 67 0)
           (cons 8 "0")
           (cons 100 "AcDbPoint")
           (list 10 14.4 -1.3 0)
           (cons 50 0)
          )
         )
         (entmake
          (list
           (cons 0 "POINT")
           (cons 100 "AcDbEntity")
           (cons 67 0)
           (cons 8 "0")
           (cons 100 "AcDbPoint")
           (list 10 16.2 -1.3 0)
           (cons 50 0)
          )
         )
         (entmake
          (list
           (cons 0 "POINT")
           (cons 100 "AcDbEntity")
           (cons 67 0)
           (cons 8 "0")
           (cons 100 "AcDbPoint")
           (list 10 16.2 1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 16.2 0 0)
           (cons 50 0)
          )
         )
         (entmake
          (list
           (cons 0 "ATTDEF")
           (cons 100 "AcDbEntity")
           (cons 67 0)
           (cons 8 "0")
           (cons 100 "AcDbText")
           (list 10 1.2 0.56666667 0)
           (cons 40 0.2)
           (cons 1 "1.900")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.2 0.23333333 0)
           (cons 40 0.2)
           (cons 1 "1.900")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.2 -0.1 0)
           (cons 40 0.2)
           (cons 1 "14.400")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.2 -0.43333333 0)
           (cons 40 0.2)
           (cons 1 "16.200")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.2 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-28-TRUCK"))
        (progn
         (entmake)
         (entmake
          (list
           (cons 0 "BLOCK")
           (cons 2 "AB_INF-WB-28-TRUCK")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 -1.3)
           (cons 40 0)
           (cons 41 0)
           (cons 42 0)
           (cons 91 0)
           (list 10 6.335 -1.3)
           (cons 40 0)
           (cons 41 0)
           (cons 42 0)
           (cons 91 0)
           (list 10 6.335 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.335 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.335 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 5.7 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 5.96263966 -0.26263966 0)
           (list 11 5.96263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.5062 -0.7445528)
           (cons 40 0)
           (cons 41 0)
           (cons 42 0)
           (cons 91 0)
           (list 10 4.5062 -0.5702072)
           (cons 40 0)
           (cons 41 0)
           (cons 42 0)
           (cons 91 0)
           (list 10 4.662664 -0.51768)
           (cons 40 0)
           (cons 41 0)
           (cons 42 0)
           (cons 91 0)
           (list 10 5.467336 -0.51768)
           (cons 40 0)
           (cons 41 0)
           (cons 42 0)
           (cons 91 0)
           (list 10 5.6238 -0.5702072)
           (cons 40 0)
           (cons 41 0)
           (cons 42 0)
           (cons 91 0)
           (list 10 5.6238 -0.7445528)
           (cons 40 0)
           (cons 41 0)
           (cons 42 0)
           (cons 91 0)
           (list 10 5.467336 -0.79708)
           (cons 40 0)
           (cons 41 0)
           (cons 42 0)
           (cons 91 0)
           (list 10 4.662664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.5062 -1.2474728)
           (cons 40 0)
           (cons 41 0)
           (cons 42 0)
           (cons 91 0)
           (list 10 4.5062 -1.0731272)
           (cons 40 0)
           (cons 41 0)
           (cons 42 0)
           (cons 91 0)
           (list 10 4.662664 -1.0206)
           (cons 40 0)
           (cons 41 0)
           (cons 42 0)
           (cons 91 0)
           (list 10 5.467336 -1.0206)
           (cons 40 0)
           (cons 41 0)
           (cons 42 0)
           (cons 91 0)
           (list 10 5.6238 -1.0731272)
           (cons 40 0)
           (cons 41 0)
           (cons 42 0)
           (cons 91 0)
           (list 10 5.6238 -1.2474728)
           (cons 40 0)
           (cons 41 0)
           (cons 42 0)
           (cons 91 0)
           (list 10 5.467336 -1.3)
           (cons 40 0)
           (cons 41 0)
           (cons 42 0)
           (cons 91 0)
           (list 10 4.662664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.5062 0.5702072)
           (cons 40 0)
           (cons 41 0)
           (cons 42 0)
           (cons 91 0)
           (list 10 4.5062 0.7445528)
           (cons 40 0)
           (cons 41 0)
           (cons 42 0)
           (cons 91 0)
           (list 10 4.662664 0.79708)
           (cons 40 0)
           (cons 41 0)
           (cons 42 0)
           (cons 91 0)
           (list 10 5.467336 0.79708)
           (cons 40 0)
           (cons 41 0)
           (cons 42 0)
           (cons 91 0)
           (list 10 5.6238 0.7445528)
           (cons 40 0)
           (cons 41 0)
           (cons 42 0)
           (cons 91 0)
           (list 10 5.6238 0.5702072)
           (cons 40 0)
           (cons 41 0)
           (cons 42 0)
           (cons 91 0)
           (list 10 5.467336 0.51768)
           (cons 40 0)
           (cons 41 0)
           (cons 42 0)
           (cons 91 0)
           (list 10 4.662664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.5062 1.0731272)
           (cons 40 0)
           (cons 41 0)
           (cons 42 0)
           (cons 91 0)
           (list 10 4.5062 1.2474728)
           (cons 40 0)
           (cons 41 0)
           (cons 42 0)
           (cons 91 0)
           (list 10 4.662664 1.3)
           (cons 40 0)
           (cons 41 0)
           (cons 42 0)
           (cons 91 0)
           (list 10 5.467336 1.3)
           (cons 40 0)
           (cons 41 0)
           (cons 42 0)
           (cons 91 0)
           (list 10 5.6238 1.2474728)
           (cons 40 0)
           (cons 41 0)
           (cons 42 0)
           (cons 91 0)
           (list 10 5.6238 1.0731272)
           (cons 40 0)
           (cons 41 0)
           (cons 42 0)
           (cons 91 0)
           (list 10 5.467336 1.0206)
           (cons 40 0)
           (cons 41 0)
           (cons 42 0)
           (cons 91 0)
           (list 10 4.662664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.7762 -0.7445528)
           (cons 40 0)
           (cons 41 0)
           (cons 42 0)
           (cons 91 0)
           (list 10 5.7762 -0.5702072)
           (cons 40 0)
           (cons 41 0)
           (cons 42 0)
           (cons 91 0)
           (list 10 5.932664 -0.51768)
           (cons 40 0)
           (cons 41 0)
           (cons 42 0)
           (cons 91 0)
           (list 10 6.737336 -0.51768)
           (cons 40 0)
           (cons 41 0)
           (cons 42 0)
           (cons 91 0)
           (list 10 6.8938 -0.5702072)
           (cons 40 0)
           (cons 41 0)
           (cons 42 0)
           (cons 91 0)
           (list 10 6.8938 -0.7445528)
           (cons 40 0)
           (cons 41 0)
           (cons 42 0)
           (cons 91 0)
           (list 10 6.737336 -0.79708)
           (cons 40 0)
           (cons 41 0)
           (cons 42 0)
           (cons 91 0)
           (list 10 5.932664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.7762 -1.2474728)
           (cons 40 0)
           (cons 41 0)
           (cons 42 0)
           (cons 91 0)
           (list 10 5.7762 -1.0731272)
           (cons 40 0)
           (cons 41 0)
           (cons 42 0)
           (cons 91 0)
           (list 10 5.932664 -1.0206)
           (cons 40 0)
           (cons 41 0)
           (cons 42 0)
           (cons 91 0)
           (list 10 6.737336 -1.0206)
           (cons 40 0)
           (cons 41 0)
           (cons 42 0)
           (cons 91 0)
           (list 10 6.8938 -1.0731272)
           (cons 40 0)
           (cons 41 0)
           (cons 42 0)
           (cons 91 0)
           (list 10 6.8938 -1.2474728)
           (cons 40 0)
           (cons 41 0)
           (cons 42 0)
           (cons 91 0)
           (list 10 6.737336 -1.3)
           (cons 40 0)
           (cons 41 0)
           (cons 42 0)
           (cons 91 0)
           (list 10 5.932664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.7762 0.5702072)
           (cons 40 0)
           (cons 41 0)
           (cons 42 0)
           (cons 91 0)
           (list 10 5.7762 0.7445528)
           (cons 40 0)
           (cons 41 0)
           (cons 42 0)
           (cons 91 0)
           (list 10 5.932664 0.79708)
           (cons 40 0)
           (cons 41 0)
           (cons 42 0)
           (cons 91 0)
           (list 10 6.737336 0.79708)
           (cons 40 0)
           (cons 41 0)
           (cons 42 0)
           (cons 91 0)
           (list 10 6.8938 0.7445528)
           (cons 40 0)
           (cons 41 0)
           (cons 42 0)
           (cons 91 0)
           (list 10 6.8938 0.5702072)
           (cons 40 0)
           (cons 41 0)
           (cons 42 0)
           (cons 91 0)
           (list 10 6.737336 0.51768)
           (cons 40 0)
           (cons 41 0)
           (cons 42 0)
           (cons 91 0)
           (list 10 5.932664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.7762 1.0731272)
           (cons 40 0)
           (cons 41 0)
           (cons 42 0)
           (cons 91 0)
           (list 10 5.7762 1.2474728)
           (cons 40 0)
           (cons 41 0)
           (cons 42 0)
           (cons 91 0)
           (list 10 5.932664 1.3)
           (cons 40 0)
           (cons 41 0)
           (cons 42 0)
           (cons 91 0)
           (list 10 6.737336 1.3)
           (cons 40 0)
           (cons 41 0)
           (cons 42 0)
           (cons 91 0)
           (list 10 6.8938 1.2474728)
           (cons 40 0)
           (cons 41 0)
           (cons 42 0)
           (cons 91 0)
           (list 10 6.8938 1.0731272)
           (cons 40 0)
           (cons 41 0)
           (cons 42 0)
           (cons 91 0)
           (list 10 6.737336 1.0206)
           (cons 40 0)
           (cons 41 0)
           (cons 42 0)
           (cons 91 0)
           (list 10 5.932664 1.0206)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelLeftM1")
           (list 10 0.7 -1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM1")
           (list 10 0.7 1.0206 0)
           (cons 41 1)
           (cons 42 1)
           (cons 43 1)
           (cons 50 0)
           (cons 70 0)
           (cons 71 0)
           (cons 44 0)
           (cons 45 0)
          )
         )
         (entmake
          (list
           (cons 0 "POINT")
           (cons 100 "AcDbEntity")
           (cons 67 0)
           (cons 8 "0")
           (cons 100 "AcDbPoint")
           (list 10 5.7 1.3 0)
           (cons 50 0)
          )
         )
         (entmake
          (list
           (cons 0 "POINT")
           (cons 100 "AcDbEntity")
           (cons 67 0)
           (cons 8 "0")
           (cons 100 "AcDbPoint")
           (list 10 5.7 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0.7 -1.3 0)
           (cons 50 0)
          )
         )
         (entmake
          (list
           (cons 0 "POINT")
           (cons 100 "AcDbEntity")
           (cons 67 0)
           (cons 8 "0")
           (cons 100 "AcDbPoint")
           (list 10 0.7 1.3 0)
           (cons 50 0)
          )
         )
         (entmake
          (list
           (cons 0 "POINT")
           (cons 100 "AcDbEntity")
           (cons 67 0)
           (cons 8 "0")
           (cons 100 "AcDbPoint")
           (list 10 0.7 0 0)
           (cons 50 0)
          )
         )
         (entmake
          (list
           (cons 0 "POINT")
           (cons 100 "AcDbEntity")
           (cons 67 0)
           (cons 8 "0")
           (cons 100 "AcDbPoint")
           (list 10 5.7 0 0)
           (cons 50 0)
          )
         )
         (entmake
          (list
           (cons 0 "ATTDEF")
           (cons 100 "AcDbEntity")
           (cons 67 0)
           (cons 8 "0")
           (cons 100 "AcDbText")
           (list 10 0 0.56666667 0)
           (cons 40 0.2)
           (cons 1 "0.700")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0 0.23333333 0)
           (cons 40 0.2)
           (cons 1 "0.700")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0 -0.1 0)
           (cons 40 0.2)
           (cons 1 "5.700")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0 -0.43333333 0)
           (cons 40 0.2)
           (cons 1 "5.700")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0 -0.76666667 0)
           (cons 40 0.2)
           (cons 1 "19.79")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-23-TRAILER2"))
        (progn
         (entmake)
         (entmake
          (list
           (cons 0 "BLOCK")
           (cons 2 "AB_INF-WB-23-TRAILER2")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 10.8 -1.3)
           (cons 40 0)
           (cons 41 0)
           (cons 42 0)
           (cons 91 0)
           (list 10 10.8 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 10.8 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 10.8 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.1062 -0.7445528)
           (cons 40 0)
           (cons 41 0)
           (cons 42 0)
           (cons 91 0)
           (list 10 8.1062 -0.5702072)
           (cons 40 0)
           (cons 41 0)
           (cons 42 0)
           (cons 91 0)
           (list 10 8.262664 -0.51768)
           (cons 40 0)
           (cons 41 0)
           (cons 42 0)
           (cons 91 0)
           (list 10 9.067336 -0.51768)
           (cons 40 0)
           (cons 41 0)
           (cons 42 0)
           (cons 91 0)
           (list 10 9.2238 -0.5702072)
           (cons 40 0)
           (cons 41 0)
           (cons 42 0)
           (cons 91 0)
           (list 10 9.2238 -0.7445528)
           (cons 40 0)
           (cons 41 0)
           (cons 42 0)
           (cons 91 0)
           (list 10 9.067336 -0.79708)
           (cons 40 0)
           (cons 41 0)
           (cons 42 0)
           (cons 91 0)
           (list 10 8.262664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.1062 -1.2474728)
           (cons 40 0)
           (cons 41 0)
           (cons 42 0)
           (cons 91 0)
           (list 10 8.1062 -1.0731272)
           (cons 40 0)
           (cons 41 0)
           (cons 42 0)
           (cons 91 0)
           (list 10 8.262664 -1.0206)
           (cons 40 0)
           (cons 41 0)
           (cons 42 0)
           (cons 91 0)
           (list 10 9.067336 -1.0206)
           (cons 40 0)
           (cons 41 0)
           (cons 42 0)
           (cons 91 0)
           (list 10 9.2238 -1.0731272)
           (cons 40 0)
           (cons 41 0)
           (cons 42 0)
           (cons 91 0)
           (list 10 9.2238 -1.2474728)
           (cons 40 0)
           (cons 41 0)
           (cons 42 0)
           (cons 91 0)
           (list 10 9.067336 -1.3)
           (cons 40 0)
           (cons 41 0)
           (cons 42 0)
           (cons 91 0)
           (list 10 8.262664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.1062 0.5702072)
           (cons 40 0)
           (cons 41 0)
           (cons 42 0)
           (cons 91 0)
           (list 10 8.1062 0.7445528)
           (cons 40 0)
           (cons 41 0)
           (cons 42 0)
           (cons 91 0)
           (list 10 8.262664 0.79708)
           (cons 40 0)
           (cons 41 0)
           (cons 42 0)
           (cons 91 0)
           (list 10 9.067336 0.79708)
           (cons 40 0)
           (cons 41 0)
           (cons 42 0)
           (cons 91 0)
           (list 10 9.2238 0.7445528)
           (cons 40 0)
           (cons 41 0)
           (cons 42 0)
           (cons 91 0)
           (list 10 9.2238 0.5702072)
           (cons 40 0)
           (cons 41 0)
           (cons 42 0)
           (cons 91 0)
           (list 10 9.067336 0.51768)
           (cons 40 0)
           (cons 41 0)
           (cons 42 0)
           (cons 91 0)
           (list 10 8.262664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.1062 1.0731272)
           (cons 40 0)
           (cons 41 0)
           (cons 42 0)
           (cons 91 0)
           (list 10 8.1062 1.2474728)
           (cons 40 0)
           (cons 41 0)
           (cons 42 0)
           (cons 91 0)
           (list 10 8.262664 1.3)
           (cons 40 0)
           (cons 41 0)
           (cons 42 0)
           (cons 91 0)
           (list 10 9.067336 1.3)
           (cons 40 0)
           (cons 41 0)
           (cons 42 0)
           (cons 91 0)
           (list 10 9.2238 1.2474728)
           (cons 40 0)
           (cons 41 0)
           (cons 42 0)
           (cons 91 0)
           (list 10 9.2238 1.0731272)
           (cons 40 0)
           (cons 41 0)
           (cons 42 0)
           (cons 91 0)
           (list 10 9.067336 1.0206)
           (cons 40 0)
           (cons 41 0)
           (cons 42 0)
           (cons 91 0)
           (list 10 8.262664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.3762 -0.7445528)
           (cons 40 0)
           (cons 41 0)
           (cons 42 0)
           (cons 91 0)
           (list 10 9.3762 -0.5702072)
           (cons 40 0)
           (cons 41 0)
           (cons 42 0)
           (cons 91 0)
           (list 10 9.532664 -0.51768)
           (cons 40 0)
           (cons 41 0)
           (cons 42 0)
           (cons 91 0)
           (list 10 10.337336 -0.51768)
           (cons 40 0)
           (cons 41 0)
           (cons 42 0)
           (cons 91 0)
           (list 10 10.4938 -0.5702072)
           (cons 40 0)
           (cons 41 0)
           (cons 42 0)
           (cons 91 0)
           (list 10 10.4938 -0.7445528)
           (cons 40 0)
           (cons 41 0)
           (cons 42 0)
           (cons 91 0)
           (list 10 10.337336 -0.79708)
           (cons 40 0)
           (cons 41 0)
           (cons 42 0)
           (cons 91 0)
           (list 10 9.532664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.3762 -1.2474728)
           (cons 40 0)
           (cons 41 0)
           (cons 42 0)
           (cons 91 0)
           (list 10 9.3762 -1.0731272)
           (cons 40 0)
           (cons 41 0)
           (cons 42 0)
           (cons 91 0)
           (list 10 9.532664 -1.0206)
           (cons 40 0)
           (cons 41 0)
           (cons 42 0)
           (cons 91 0)
           (list 10 10.337336 -1.0206)
           (cons 40 0)
           (cons 41 0)
           (cons 42 0)
           (cons 91 0)
           (list 10 10.4938 -1.0731272)
           (cons 40 0)
           (cons 41 0)
           (cons 42 0)
           (cons 91 0)
           (list 10 10.4938 -1.2474728)
           (cons 40 0)
           (cons 41 0)
           (cons 42 0)
           (cons 91 0)
           (list 10 10.337336 -1.3)
           (cons 40 0)
           (cons 41 0)
           (cons 42 0)
           (cons 91 0)
           (list 10 9.532664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.3762 0.5702072)
           (cons 40 0)
           (cons 41 0)
           (cons 42 0)
           (cons 91 0)
           (list 10 9.3762 0.7445528)
           (cons 40 0)
           (cons 41 0)
           (cons 42 0)
           (cons 91 0)
           (list 10 9.532664 0.79708)
           (cons 40 0)
           (cons 41 0)
           (cons 42 0)
           (cons 91 0)
           (list 10 10.337336 0.79708)
           (cons 40 0)
           (cons 41 0)
           (cons 42 0)
           (cons 91 0)
           (list 10 10.4938 0.7445528)
           (cons 40 0)
           (cons 41 0)
           (cons 42 0)
           (cons 91 0)
           (list 10 10.4938 0.5702072)
           (cons 40 0)
           (cons 41 0)
           (cons 42 0)
           (cons 91 0)
           (list 10 10.337336 0.51768)
           (cons 40 0)
           (cons 41 0)
           (cons 42 0)
           (cons 91 0)
           (list 10 9.532664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.3762 1.0731272)
           (cons 40 0)
           (cons 41 0)
           (cons 42 0)
           (cons 91 0)
           (list 10 9.3762 1.2474728)
           (cons 40 0)
           (cons 41 0)
           (cons 42 0)
           (cons 91 0)
           (list 10 9.532664 1.3)
           (cons 40 0)
           (cons 41 0)
           (cons 42 0)
           (cons 91 0)
           (list 10 10.337336 1.3)
           (cons 40 0)
           (cons 41 0)
           (cons 42 0)
           (cons 91 0)
           (list 10 10.4938 1.2474728)
           (cons 40 0)
           (cons 41 0)
           (cons 42 0)
           (cons 91 0)
           (list 10 10.4938 1.0731272)
           (cons 40 0)
           (cons 41 0)
           (cons 42 0)
           (cons 91 0)
           (list 10 10.337336 1.0206)
           (cons 40 0)
           (cons 41 0)
           (cons 42 0)
           (cons 91 0)
           (list 10 9.532664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 1.3 0 0)
           (cons 50 0)
          )
         )
         (entmake
          (list
           (cons 0 "POINT")
           (cons 100 "AcDbEntity")
           (cons 67 0)
           (cons 8 "0")
           (cons 100 "AcDbPoint")
           (list 10 9.3 1.3 0)
           (cons 50 0)
          )
         )
         (entmake
          (list
           (cons 0 "POINT")
           (cons 100 "AcDbEntity")
           (cons 67 0)
           (cons 8 "0")
           (cons 100 "AcDbPoint")
           (list 10 9.3 -1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 10.8 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 10.8 1.3 0)
           (cons 50 0)
          )
         )
         (entmake
          (list
           (cons 0 "ATTDEF")
           (cons 100 "AcDbEntity")
           (cons 67 0)
           (cons 8 "0")
           (cons 100 "AcDbText")
           (list 10 0.6 0.56666667 0)
           (cons 40 0.2)
           (cons 1 "1.300")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 0.23333333 0)
           (cons 40 0.2)
           (cons 1 "1.300")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.1 0)
           (cons 40 0.2)
           (cons 1 "9.300")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-23-TRAILER1"))
        (progn
         (entmake)
         (entmake
          (list
           (cons 0 "BLOCK")
           (cons 2 "AB_INF-WB-23-TRAILER1")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 10.57 -1.3)
           (cons 40 0)
           (cons 41 0)
           (cons 42 0)
           (cons 91 0)
           (list 10 10.57 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.6 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.6 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 10.57 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 10.57 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.6 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.6 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 10.57 0 0)
           (list 11 10.8 0 0)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 10.8 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 11.06263966 -0.26263966 0)
           (list 11 11.06263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.4712 -0.7445528)
           (cons 40 0)
           (cons 41 0)
           (cons 42 0)
           (cons 91 0)
           (list 10 7.4712 -0.5702072)
           (cons 40 0)
           (cons 41 0)
           (cons 42 0)
           (cons 91 0)
           (list 10 7.627664 -0.51768)
           (cons 40 0)
           (cons 41 0)
           (cons 42 0)
           (cons 91 0)
           (list 10 8.432336 -0.51768)
           (cons 40 0)
           (cons 41 0)
           (cons 42 0)
           (cons 91 0)
           (list 10 8.5888 -0.5702072)
           (cons 40 0)
           (cons 41 0)
           (cons 42 0)
           (cons 91 0)
           (list 10 8.5888 -0.7445528)
           (cons 40 0)
           (cons 41 0)
           (cons 42 0)
           (cons 91 0)
           (list 10 8.432336 -0.79708)
           (cons 40 0)
           (cons 41 0)
           (cons 42 0)
           (cons 91 0)
           (list 10 7.627664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.4712 -1.2474728)
           (cons 40 0)
           (cons 41 0)
           (cons 42 0)
           (cons 91 0)
           (list 10 7.4712 -1.0731272)
           (cons 40 0)
           (cons 41 0)
           (cons 42 0)
           (cons 91 0)
           (list 10 7.627664 -1.0206)
           (cons 40 0)
           (cons 41 0)
           (cons 42 0)
           (cons 91 0)
           (list 10 8.432336 -1.0206)
           (cons 40 0)
           (cons 41 0)
           (cons 42 0)
           (cons 91 0)
           (list 10 8.5888 -1.0731272)
           (cons 40 0)
           (cons 41 0)
           (cons 42 0)
           (cons 91 0)
           (list 10 8.5888 -1.2474728)
           (cons 40 0)
           (cons 41 0)
           (cons 42 0)
           (cons 91 0)
           (list 10 8.432336 -1.3)
           (cons 40 0)
           (cons 41 0)
           (cons 42 0)
           (cons 91 0)
           (list 10 7.627664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.4712 0.5702072)
           (cons 40 0)
           (cons 41 0)
           (cons 42 0)
           (cons 91 0)
           (list 10 7.4712 0.7445528)
           (cons 40 0)
           (cons 41 0)
           (cons 42 0)
           (cons 91 0)
           (list 10 7.627664 0.79708)
           (cons 40 0)
           (cons 41 0)
           (cons 42 0)
           (cons 91 0)
           (list 10 8.432336 0.79708)
           (cons 40 0)
           (cons 41 0)
           (cons 42 0)
           (cons 91 0)
           (list 10 8.5888 0.7445528)
           (cons 40 0)
           (cons 41 0)
           (cons 42 0)
           (cons 91 0)
           (list 10 8.5888 0.5702072)
           (cons 40 0)
           (cons 41 0)
           (cons 42 0)
           (cons 91 0)
           (list 10 8.432336 0.51768)
           (cons 40 0)
           (cons 41 0)
           (cons 42 0)
           (cons 91 0)
           (list 10 7.627664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.4712 1.0731272)
           (cons 40 0)
           (cons 41 0)
           (cons 42 0)
           (cons 91 0)
           (list 10 7.4712 1.2474728)
           (cons 40 0)
           (cons 41 0)
           (cons 42 0)
           (cons 91 0)
           (list 10 7.627664 1.3)
           (cons 40 0)
           (cons 41 0)
           (cons 42 0)
           (cons 91 0)
           (list 10 8.432336 1.3)
           (cons 40 0)
           (cons 41 0)
           (cons 42 0)
           (cons 91 0)
           (list 10 8.5888 1.2474728)
           (cons 40 0)
           (cons 41 0)
           (cons 42 0)
           (cons 91 0)
           (list 10 8.5888 1.0731272)
           (cons 40 0)
           (cons 41 0)
           (cons 42 0)
           (cons 91 0)
           (list 10 8.432336 1.0206)
           (cons 40 0)
           (cons 41 0)
           (cons 42 0)
           (cons 91 0)
           (list 10 7.627664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.7412 -0.7445528)
           (cons 40 0)
           (cons 41 0)
           (cons 42 0)
           (cons 91 0)
           (list 10 8.7412 -0.5702072)
           (cons 40 0)
           (cons 41 0)
           (cons 42 0)
           (cons 91 0)
           (list 10 8.897664 -0.51768)
           (cons 40 0)
           (cons 41 0)
           (cons 42 0)
           (cons 91 0)
           (list 10 9.702336 -0.51768)
           (cons 40 0)
           (cons 41 0)
           (cons 42 0)
           (cons 91 0)
           (list 10 9.8588 -0.5702072)
           (cons 40 0)
           (cons 41 0)
           (cons 42 0)
           (cons 91 0)
           (list 10 9.8588 -0.7445528)
           (cons 40 0)
           (cons 41 0)
           (cons 42 0)
           (cons 91 0)
           (list 10 9.702336 -0.79708)
           (cons 40 0)
           (cons 41 0)
           (cons 42 0)
           (cons 91 0)
           (list 10 8.897664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.7412 -1.2474728)
           (cons 40 0)
           (cons 41 0)
           (cons 42 0)
           (cons 91 0)
           (list 10 8.7412 -1.0731272)
           (cons 40 0)
           (cons 41 0)
           (cons 42 0)
           (cons 91 0)
           (list 10 8.897664 -1.0206)
           (cons 40 0)
           (cons 41 0)
           (cons 42 0)
           (cons 91 0)
           (list 10 9.702336 -1.0206)
           (cons 40 0)
           (cons 41 0)
           (cons 42 0)
           (cons 91 0)
           (list 10 9.8588 -1.0731272)
           (cons 40 0)
           (cons 41 0)
           (cons 42 0)
           (cons 91 0)
           (list 10 9.8588 -1.2474728)
           (cons 40 0)
           (cons 41 0)
           (cons 42 0)
           (cons 91 0)
           (list 10 9.702336 -1.3)
           (cons 40 0)
           (cons 41 0)
           (cons 42 0)
           (cons 91 0)
           (list 10 8.897664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.7412 0.5702072)
           (cons 40 0)
           (cons 41 0)
           (cons 42 0)
           (cons 91 0)
           (list 10 8.7412 0.7445528)
           (cons 40 0)
           (cons 41 0)
           (cons 42 0)
           (cons 91 0)
           (list 10 8.897664 0.79708)
           (cons 40 0)
           (cons 41 0)
           (cons 42 0)
           (cons 91 0)
           (list 10 9.702336 0.79708)
           (cons 40 0)
           (cons 41 0)
           (cons 42 0)
           (cons 91 0)
           (list 10 9.8588 0.7445528)
           (cons 40 0)
           (cons 41 0)
           (cons 42 0)
           (cons 91 0)
           (list 10 9.8588 0.5702072)
           (cons 40 0)
           (cons 41 0)
           (cons 42 0)
           (cons 91 0)
           (list 10 9.702336 0.51768)
           (cons 40 0)
           (cons 41 0)
           (cons 42 0)
           (cons 91 0)
           (list 10 8.897664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.7412 1.0731272)
           (cons 40 0)
           (cons 41 0)
           (cons 42 0)
           (cons 91 0)
           (list 10 8.7412 1.2474728)
           (cons 40 0)
           (cons 41 0)
           (cons 42 0)
           (cons 91 0)
           (list 10 8.897664 1.3)
           (cons 40 0)
           (cons 41 0)
           (cons 42 0)
           (cons 91 0)
           (list 10 9.702336 1.3)
           (cons 40 0)
           (cons 41 0)
           (cons 42 0)
           (cons 91 0)
           (list 10 9.8588 1.2474728)
           (cons 40 0)
           (cons 41 0)
           (cons 42 0)
           (cons 91 0)
           (list 10 9.8588 1.0731272)
           (cons 40 0)
           (cons 41 0)
           (cons 42 0)
           (cons 91 0)
           (list 10 9.702336 1.0206)
           (cons 40 0)
           (cons 41 0)
           (cons 42 0)
           (cons 91 0)
           (list 10 8.897664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.0112 -0.7445528)
           (cons 40 0)
           (cons 41 0)
           (cons 42 0)
           (cons 91 0)
           (list 10 10.0112 -0.5702072)
           (cons 40 0)
           (cons 41 0)
           (cons 42 0)
           (cons 91 0)
           (list 10 10.167664 -0.51768)
           (cons 40 0)
           (cons 41 0)
           (cons 42 0)
           (cons 91 0)
           (list 10 10.972336 -0.51768)
           (cons 40 0)
           (cons 41 0)
           (cons 42 0)
           (cons 91 0)
           (list 10 11.1288 -0.5702072)
           (cons 40 0)
           (cons 41 0)
           (cons 42 0)
           (cons 91 0)
           (list 10 11.1288 -0.7445528)
           (cons 40 0)
           (cons 41 0)
           (cons 42 0)
           (cons 91 0)
           (list 10 10.972336 -0.79708)
           (cons 40 0)
           (cons 41 0)
           (cons 42 0)
           (cons 91 0)
           (list 10 10.167664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.0112 -1.2474728)
           (cons 40 0)
           (cons 41 0)
           (cons 42 0)
           (cons 91 0)
           (list 10 10.0112 -1.0731272)
           (cons 40 0)
           (cons 41 0)
           (cons 42 0)
           (cons 91 0)
           (list 10 10.167664 -1.0206)
           (cons 40 0)
           (cons 41 0)
           (cons 42 0)
           (cons 91 0)
           (list 10 10.972336 -1.0206)
           (cons 40 0)
           (cons 41 0)
           (cons 42 0)
           (cons 91 0)
           (list 10 11.1288 -1.0731272)
           (cons 40 0)
           (cons 41 0)
           (cons 42 0)
           (cons 91 0)
           (list 10 11.1288 -1.2474728)
           (cons 40 0)
           (cons 41 0)
           (cons 42 0)
           (cons 91 0)
           (list 10 10.972336 -1.3)
           (cons 40 0)
           (cons 41 0)
           (cons 42 0)
           (cons 91 0)
           (list 10 10.167664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.0112 0.5702072)
           (cons 40 0)
           (cons 41 0)
           (cons 42 0)
           (cons 91 0)
           (list 10 10.0112 0.7445528)
           (cons 40 0)
           (cons 41 0)
           (cons 42 0)
           (cons 91 0)
           (list 10 10.167664 0.79708)
           (cons 40 0)
           (cons 41 0)
           (cons 42 0)
           (cons 91 0)
           (list 10 10.972336 0.79708)
           (cons 40 0)
           (cons 41 0)
           (cons 42 0)
           (cons 91 0)
           (list 10 11.1288 0.7445528)
           (cons 40 0)
           (cons 41 0)
           (cons 42 0)
           (cons 91 0)
           (list 10 11.1288 0.5702072)
           (cons 40 0)
           (cons 41 0)
           (cons 42 0)
           (cons 91 0)
           (list 10 10.972336 0.51768)
           (cons 40 0)
           (cons 41 0)
           (cons 42 0)
           (cons 91 0)
           (list 10 10.167664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.0112 1.0731272)
           (cons 40 0)
           (cons 41 0)
           (cons 42 0)
           (cons 91 0)
           (list 10 10.0112 1.2474728)
           (cons 40 0)
           (cons 41 0)
           (cons 42 0)
           (cons 91 0)
           (list 10 10.167664 1.3)
           (cons 40 0)
           (cons 41 0)
           (cons 42 0)
           (cons 91 0)
           (list 10 10.972336 1.3)
           (cons 40 0)
           (cons 41 0)
           (cons 42 0)
           (cons 91 0)
           (list 10 11.1288 1.2474728)
           (cons 40 0)
           (cons 41 0)
           (cons 42 0)
           (cons 91 0)
           (list 10 11.1288 1.0731272)
           (cons 40 0)
           (cons 41 0)
           (cons 42 0)
           (cons 91 0)
           (list 10 10.972336 1.0206)
           (cons 40 0)
           (cons 41 0)
           (cons 42 0)
           (cons 91 0)
           (list 10 10.167664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 9.3 1.3 0)
           (cons 50 0)
          )
         )
         (entmake
          (list
           (cons 0 "POINT")
           (cons 100 "AcDbEntity")
           (cons 67 0)
           (cons 8 "0")
           (cons 100 "AcDbPoint")
           (list 10 9.3 -1.3 0)
           (cons 50 0)
          )
         )
         (entmake
          (list
           (cons 0 "POINT")
           (cons 100 "AcDbEntity")
           (cons 67 0)
           (cons 8 "0")
           (cons 100 "AcDbPoint")
           (list 10 1.3 0 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 10.8 0 0)
           (cons 50 0)
          )
         )
         (entmake
          (list
           (cons 0 "ATTDEF")
           (cons 100 "AcDbEntity")
           (cons 67 0)
           (cons 8 "0")
           (cons 100 "AcDbText")
           (list 10 0.6 0.56666667 0)
           (cons 40 0.2)
           (cons 1 "1.300")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 0.23333333 0)
           (cons 40 0.2)
           (cons 1 "1.300")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.1 0)
           (cons 40 0.2)
           (cons 1 "9.300")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.43333333 0)
           (cons 40 0.2)
           (cons 1 "10.800")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-23-TRUCK"))
        (progn
         (entmake)
         (entmake
          (list
           (cons 0 "BLOCK")
           (cons 2 "AB_INF-WB-23-TRUCK")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 6.635 -1.3)
           (cons 40 0)
           (cons 41 0)
           (cons 42 0)
           (cons 91 0)
           (list 10 6.635 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.635 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.635 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 6 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 6.26263966 -0.26263966 0)
           (list 11 6.26263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.8062 -0.7445528)
           (cons 40 0)
           (cons 41 0)
           (cons 42 0)
           (cons 91 0)
           (list 10 4.8062 -0.5702072)
           (cons 40 0)
           (cons 41 0)
           (cons 42 0)
           (cons 91 0)
           (list 10 4.962664 -0.51768)
           (cons 40 0)
           (cons 41 0)
           (cons 42 0)
           (cons 91 0)
           (list 10 5.767336 -0.51768)
           (cons 40 0)
           (cons 41 0)
           (cons 42 0)
           (cons 91 0)
           (list 10 5.9238 -0.5702072)
           (cons 40 0)
           (cons 41 0)
           (cons 42 0)
           (cons 91 0)
           (list 10 5.9238 -0.7445528)
           (cons 40 0)
           (cons 41 0)
           (cons 42 0)
           (cons 91 0)
           (list 10 5.767336 -0.79708)
           (cons 40 0)
           (cons 41 0)
           (cons 42 0)
           (cons 91 0)
           (list 10 4.962664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.8062 -1.2474728)
           (cons 40 0)
           (cons 41 0)
           (cons 42 0)
           (cons 91 0)
           (list 10 4.8062 -1.0731272)
           (cons 40 0)
           (cons 41 0)
           (cons 42 0)
           (cons 91 0)
           (list 10 4.962664 -1.0206)
           (cons 40 0)
           (cons 41 0)
           (cons 42 0)
           (cons 91 0)
           (list 10 5.767336 -1.0206)
           (cons 40 0)
           (cons 41 0)
           (cons 42 0)
           (cons 91 0)
           (list 10 5.9238 -1.0731272)
           (cons 40 0)
           (cons 41 0)
           (cons 42 0)
           (cons 91 0)
           (list 10 5.9238 -1.2474728)
           (cons 40 0)
           (cons 41 0)
           (cons 42 0)
           (cons 91 0)
           (list 10 5.767336 -1.3)
           (cons 40 0)
           (cons 41 0)
           (cons 42 0)
           (cons 91 0)
           (list 10 4.962664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.8062 0.5702072)
           (cons 40 0)
           (cons 41 0)
           (cons 42 0)
           (cons 91 0)
           (list 10 4.8062 0.7445528)
           (cons 40 0)
           (cons 41 0)
           (cons 42 0)
           (cons 91 0)
           (list 10 4.962664 0.79708)
           (cons 40 0)
           (cons 41 0)
           (cons 42 0)
           (cons 91 0)
           (list 10 5.767336 0.79708)
           (cons 40 0)
           (cons 41 0)
           (cons 42 0)
           (cons 91 0)
           (list 10 5.9238 0.7445528)
           (cons 40 0)
           (cons 41 0)
           (cons 42 0)
           (cons 91 0)
           (list 10 5.9238 0.5702072)
           (cons 40 0)
           (cons 41 0)
           (cons 42 0)
           (cons 91 0)
           (list 10 5.767336 0.51768)
           (cons 40 0)
           (cons 41 0)
           (cons 42 0)
           (cons 91 0)
           (list 10 4.962664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.8062 1.0731272)
           (cons 40 0)
           (cons 41 0)
           (cons 42 0)
           (cons 91 0)
           (list 10 4.8062 1.2474728)
           (cons 40 0)
           (cons 41 0)
           (cons 42 0)
           (cons 91 0)
           (list 10 4.962664 1.3)
           (cons 40 0)
           (cons 41 0)
           (cons 42 0)
           (cons 91 0)
           (list 10 5.767336 1.3)
           (cons 40 0)
           (cons 41 0)
           (cons 42 0)
           (cons 91 0)
           (list 10 5.9238 1.2474728)
           (cons 40 0)
           (cons 41 0)
           (cons 42 0)
           (cons 91 0)
           (list 10 5.9238 1.0731272)
           (cons 40 0)
           (cons 41 0)
           (cons 42 0)
           (cons 91 0)
           (list 10 5.767336 1.0206)
           (cons 40 0)
           (cons 41 0)
           (cons 42 0)
           (cons 91 0)
           (list 10 4.962664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.0762 -0.7445528)
           (cons 40 0)
           (cons 41 0)
           (cons 42 0)
           (cons 91 0)
           (list 10 6.0762 -0.5702072)
           (cons 40 0)
           (cons 41 0)
           (cons 42 0)
           (cons 91 0)
           (list 10 6.232664 -0.51768)
           (cons 40 0)
           (cons 41 0)
           (cons 42 0)
           (cons 91 0)
           (list 10 7.037336 -0.51768)
           (cons 40 0)
           (cons 41 0)
           (cons 42 0)
           (cons 91 0)
           (list 10 7.1938 -0.5702072)
           (cons 40 0)
           (cons 41 0)
           (cons 42 0)
           (cons 91 0)
           (list 10 7.1938 -0.7445528)
           (cons 40 0)
           (cons 41 0)
           (cons 42 0)
           (cons 91 0)
           (list 10 7.037336 -0.79708)
           (cons 40 0)
           (cons 41 0)
           (cons 42 0)
           (cons 91 0)
           (list 10 6.232664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.0762 -1.2474728)
           (cons 40 0)
           (cons 41 0)
           (cons 42 0)
           (cons 91 0)
           (list 10 6.0762 -1.0731272)
           (cons 40 0)
           (cons 41 0)
           (cons 42 0)
           (cons 91 0)
           (list 10 6.232664 -1.0206)
           (cons 40 0)
           (cons 41 0)
           (cons 42 0)
           (cons 91 0)
           (list 10 7.037336 -1.0206)
           (cons 40 0)
           (cons 41 0)
           (cons 42 0)
           (cons 91 0)
           (list 10 7.1938 -1.0731272)
           (cons 40 0)
           (cons 41 0)
           (cons 42 0)
           (cons 91 0)
           (list 10 7.1938 -1.2474728)
           (cons 40 0)
           (cons 41 0)
           (cons 42 0)
           (cons 91 0)
           (list 10 7.037336 -1.3)
           (cons 40 0)
           (cons 41 0)
           (cons 42 0)
           (cons 91 0)
           (list 10 6.232664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.0762 0.5702072)
           (cons 40 0)
           (cons 41 0)
           (cons 42 0)
           (cons 91 0)
           (list 10 6.0762 0.7445528)
           (cons 40 0)
           (cons 41 0)
           (cons 42 0)
           (cons 91 0)
           (list 10 6.232664 0.79708)
           (cons 40 0)
           (cons 41 0)
           (cons 42 0)
           (cons 91 0)
           (list 10 7.037336 0.79708)
           (cons 40 0)
           (cons 41 0)
           (cons 42 0)
           (cons 91 0)
           (list 10 7.1938 0.7445528)
           (cons 40 0)
           (cons 41 0)
           (cons 42 0)
           (cons 91 0)
           (list 10 7.1938 0.5702072)
           (cons 40 0)
           (cons 41 0)
           (cons 42 0)
           (cons 91 0)
           (list 10 7.037336 0.51768)
           (cons 40 0)
           (cons 41 0)
           (cons 42 0)
           (cons 91 0)
           (list 10 6.232664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.0762 1.0731272)
           (cons 40 0)
           (cons 41 0)
           (cons 42 0)
           (cons 91 0)
           (list 10 6.0762 1.2474728)
           (cons 40 0)
           (cons 41 0)
           (cons 42 0)
           (cons 91 0)
           (list 10 6.232664 1.3)
           (cons 40 0)
           (cons 41 0)
           (cons 42 0)
           (cons 91 0)
           (list 10 7.037336 1.3)
           (cons 40 0)
           (cons 41 0)
           (cons 42 0)
           (cons 91 0)
           (list 10 7.1938 1.2474728)
           (cons 40 0)
           (cons 41 0)
           (cons 42 0)
           (cons 91 0)
           (list 10 7.1938 1.0731272)
           (cons 40 0)
           (cons 41 0)
           (cons 42 0)
           (cons 91 0)
           (list 10 7.037336 1.0206)
           (cons 40 0)
           (cons 41 0)
           (cons 42 0)
           (cons 91 0)
           (list 10 6.232664 1.0206)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelLeftM1")
           (list 10 0.7 -1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM1")
           (list 10 0.7 1.0206 0)
           (cons 41 1)
           (cons 42 1)
           (cons 43 1)
           (cons 50 0)
           (cons 70 0)
           (cons 71 0)
           (cons 44 0)
           (cons 45 0)
          )
         )
         (entmake
          (list
           (cons 0 "POINT")
           (cons 100 "AcDbEntity")
           (cons 67 0)
           (cons 8 "0")
           (cons 100 "AcDbPoint")
           (list 10 0.7 1.3 0)
           (cons 50 0)
          )
         )
         (entmake
          (list
           (cons 0 "POINT")
           (cons 100 "AcDbEntity")
           (cons 67 0)
           (cons 8 "0")
           (cons 100 "AcDbPoint")
           (list 10 0.7 -1.3 0)
           (cons 50 0)
          )
         )
         (entmake
          (list
           (cons 0 "POINT")
           (cons 100 "AcDbEntity")
           (cons 67 0)
           (cons 8 "0")
           (cons 100 "AcDbPoint")
           (list 10 0.7 0 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 6 0 0)
           (cons 50 0)
          )
         )
         (entmake
          (list
           (cons 0 "POINT")
           (cons 100 "AcDbEntity")
           (cons 67 0)
           (cons 8 "0")
           (cons 100 "AcDbPoint")
           (list 10 6 1.3 0)
           (cons 50 0)
          )
         )
         (entmake
          (list
           (cons 0 "POINT")
           (cons 100 "AcDbEntity")
           (cons 67 0)
           (cons 8 "0")
           (cons 100 "AcDbPoint")
           (list 10 6 -1.3 0)
           (cons 50 0)
          )
         )
         (entmake
          (list
           (cons 0 "ATTDEF")
           (cons 100 "AcDbEntity")
           (cons 67 0)
           (cons 8 "0")
           (cons 100 "AcDbText")
           (list 10 0 0.56666667 0)
           (cons 40 0.2)
           (cons 1 "0.700")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0 0.23333333 0)
           (cons 40 0.2)
           (cons 1 "0.700")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0 -0.1 0)
           (cons 40 0.2)
           (cons 1 "6.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0 -0.43333333 0)
           (cons 40 0.2)
           (cons 1 "6.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0 -0.76666667 0)
           (cons 40 0.2)
           (cons 1 "28.68")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-21-TRAILER"))
        (progn
         (entmake)
         (entmake
          (list
           (cons 0 "BLOCK")
           (cons 2 "AB_INF-WB-21-TRAILER")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 16.2 -1.3)
           (cons 40 0)
           (cons 41 0)
           (cons 42 0)
           (cons 91 0)
           (list 10 16.2 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 16.2 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 16.2 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.9412 -0.7445528)
           (cons 40 0)
           (cons 41 0)
           (cons 42 0)
           (cons 91 0)
           (list 10 11.9412 -0.5702072)
           (cons 40 0)
           (cons 41 0)
           (cons 42 0)
           (cons 91 0)
           (list 10 12.097664 -0.51768)
           (cons 40 0)
           (cons 41 0)
           (cons 42 0)
           (cons 91 0)
           (list 10 12.902336 -0.51768)
           (cons 40 0)
           (cons 41 0)
           (cons 42 0)
           (cons 91 0)
           (list 10 13.0588 -0.5702072)
           (cons 40 0)
           (cons 41 0)
           (cons 42 0)
           (cons 91 0)
           (list 10 13.0588 -0.7445528)
           (cons 40 0)
           (cons 41 0)
           (cons 42 0)
           (cons 91 0)
           (list 10 12.902336 -0.79708)
           (cons 40 0)
           (cons 41 0)
           (cons 42 0)
           (cons 91 0)
           (list 10 12.097664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.9412 -1.2474728)
           (cons 40 0)
           (cons 41 0)
           (cons 42 0)
           (cons 91 0)
           (list 10 11.9412 -1.0731272)
           (cons 40 0)
           (cons 41 0)
           (cons 42 0)
           (cons 91 0)
           (list 10 12.097664 -1.0206)
           (cons 40 0)
           (cons 41 0)
           (cons 42 0)
           (cons 91 0)
           (list 10 12.902336 -1.0206)
           (cons 40 0)
           (cons 41 0)
           (cons 42 0)
           (cons 91 0)
           (list 10 13.0588 -1.0731272)
           (cons 40 0)
           (cons 41 0)
           (cons 42 0)
           (cons 91 0)
           (list 10 13.0588 -1.2474728)
           (cons 40 0)
           (cons 41 0)
           (cons 42 0)
           (cons 91 0)
           (list 10 12.902336 -1.3)
           (cons 40 0)
           (cons 41 0)
           (cons 42 0)
           (cons 91 0)
           (list 10 12.097664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.9412 0.5702072)
           (cons 40 0)
           (cons 41 0)
           (cons 42 0)
           (cons 91 0)
           (list 10 11.9412 0.7445528)
           (cons 40 0)
           (cons 41 0)
           (cons 42 0)
           (cons 91 0)
           (list 10 12.097664 0.79708)
           (cons 40 0)
           (cons 41 0)
           (cons 42 0)
           (cons 91 0)
           (list 10 12.902336 0.79708)
           (cons 40 0)
           (cons 41 0)
           (cons 42 0)
           (cons 91 0)
           (list 10 13.0588 0.7445528)
           (cons 40 0)
           (cons 41 0)
           (cons 42 0)
           (cons 91 0)
           (list 10 13.0588 0.5702072)
           (cons 40 0)
           (cons 41 0)
           (cons 42 0)
           (cons 91 0)
           (list 10 12.902336 0.51768)
           (cons 40 0)
           (cons 41 0)
           (cons 42 0)
           (cons 91 0)
           (list 10 12.097664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.9412 1.0731272)
           (cons 40 0)
           (cons 41 0)
           (cons 42 0)
           (cons 91 0)
           (list 10 11.9412 1.2474728)
           (cons 40 0)
           (cons 41 0)
           (cons 42 0)
           (cons 91 0)
           (list 10 12.097664 1.3)
           (cons 40 0)
           (cons 41 0)
           (cons 42 0)
           (cons 91 0)
           (list 10 12.902336 1.3)
           (cons 40 0)
           (cons 41 0)
           (cons 42 0)
           (cons 91 0)
           (list 10 13.0588 1.2474728)
           (cons 40 0)
           (cons 41 0)
           (cons 42 0)
           (cons 91 0)
           (list 10 13.0588 1.0731272)
           (cons 40 0)
           (cons 41 0)
           (cons 42 0)
           (cons 91 0)
           (list 10 12.902336 1.0206)
           (cons 40 0)
           (cons 41 0)
           (cons 42 0)
           (cons 91 0)
           (list 10 12.097664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.2412 -0.7445528)
           (cons 40 0)
           (cons 41 0)
           (cons 42 0)
           (cons 91 0)
           (list 10 13.2412 -0.5702072)
           (cons 40 0)
           (cons 41 0)
           (cons 42 0)
           (cons 91 0)
           (list 10 13.397664 -0.51768)
           (cons 40 0)
           (cons 41 0)
           (cons 42 0)
           (cons 91 0)
           (list 10 14.202336 -0.51768)
           (cons 40 0)
           (cons 41 0)
           (cons 42 0)
           (cons 91 0)
           (list 10 14.3588 -0.5702072)
           (cons 40 0)
           (cons 41 0)
           (cons 42 0)
           (cons 91 0)
           (list 10 14.3588 -0.7445528)
           (cons 40 0)
           (cons 41 0)
           (cons 42 0)
           (cons 91 0)
           (list 10 14.202336 -0.79708)
           (cons 40 0)
           (cons 41 0)
           (cons 42 0)
           (cons 91 0)
           (list 10 13.397664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.2412 -1.2474728)
           (cons 40 0)
           (cons 41 0)
           (cons 42 0)
           (cons 91 0)
           (list 10 13.2412 -1.0731272)
           (cons 40 0)
           (cons 41 0)
           (cons 42 0)
           (cons 91 0)
           (list 10 13.397664 -1.0206)
           (cons 40 0)
           (cons 41 0)
           (cons 42 0)
           (cons 91 0)
           (list 10 14.202336 -1.0206)
           (cons 40 0)
           (cons 41 0)
           (cons 42 0)
           (cons 91 0)
           (list 10 14.3588 -1.0731272)
           (cons 40 0)
           (cons 41 0)
           (cons 42 0)
           (cons 91 0)
           (list 10 14.3588 -1.2474728)
           (cons 40 0)
           (cons 41 0)
           (cons 42 0)
           (cons 91 0)
           (list 10 14.202336 -1.3)
           (cons 40 0)
           (cons 41 0)
           (cons 42 0)
           (cons 91 0)
           (list 10 13.397664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.2412 0.5702072)
           (cons 40 0)
           (cons 41 0)
           (cons 42 0)
           (cons 91 0)
           (list 10 13.2412 0.7445528)
           (cons 40 0)
           (cons 41 0)
           (cons 42 0)
           (cons 91 0)
           (list 10 13.397664 0.79708)
           (cons 40 0)
           (cons 41 0)
           (cons 42 0)
           (cons 91 0)
           (list 10 14.202336 0.79708)
           (cons 40 0)
           (cons 41 0)
           (cons 42 0)
           (cons 91 0)
           (list 10 14.3588 0.7445528)
           (cons 40 0)
           (cons 41 0)
           (cons 42 0)
           (cons 91 0)
           (list 10 14.3588 0.5702072)
           (cons 40 0)
           (cons 41 0)
           (cons 42 0)
           (cons 91 0)
           (list 10 14.202336 0.51768)
           (cons 40 0)
           (cons 41 0)
           (cons 42 0)
           (cons 91 0)
           (list 10 13.397664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.2412 1.0731272)
           (cons 40 0)
           (cons 41 0)
           (cons 42 0)
           (cons 91 0)
           (list 10 13.2412 1.2474728)
           (cons 40 0)
           (cons 41 0)
           (cons 42 0)
           (cons 91 0)
           (list 10 13.397664 1.3)
           (cons 40 0)
           (cons 41 0)
           (cons 42 0)
           (cons 91 0)
           (list 10 14.202336 1.3)
           (cons 40 0)
           (cons 41 0)
           (cons 42 0)
           (cons 91 0)
           (list 10 14.3588 1.2474728)
           (cons 40 0)
           (cons 41 0)
           (cons 42 0)
           (cons 91 0)
           (list 10 14.3588 1.0731272)
           (cons 40 0)
           (cons 41 0)
           (cons 42 0)
           (cons 91 0)
           (list 10 14.202336 1.0206)
           (cons 40 0)
           (cons 41 0)
           (cons 42 0)
           (cons 91 0)
           (list 10 13.397664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.5412 -0.7445528)
           (cons 40 0)
           (cons 41 0)
           (cons 42 0)
           (cons 91 0)
           (list 10 14.5412 -0.5702072)
           (cons 40 0)
           (cons 41 0)
           (cons 42 0)
           (cons 91 0)
           (list 10 14.697664 -0.51768)
           (cons 40 0)
           (cons 41 0)
           (cons 42 0)
           (cons 91 0)
           (list 10 15.502336 -0.51768)
           (cons 40 0)
           (cons 41 0)
           (cons 42 0)
           (cons 91 0)
           (list 10 15.6588 -0.5702072)
           (cons 40 0)
           (cons 41 0)
           (cons 42 0)
           (cons 91 0)
           (list 10 15.6588 -0.7445528)
           (cons 40 0)
           (cons 41 0)
           (cons 42 0)
           (cons 91 0)
           (list 10 15.502336 -0.79708)
           (cons 40 0)
           (cons 41 0)
           (cons 42 0)
           (cons 91 0)
           (list 10 14.697664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.5412 -1.2474728)
           (cons 40 0)
           (cons 41 0)
           (cons 42 0)
           (cons 91 0)
           (list 10 14.5412 -1.0731272)
           (cons 40 0)
           (cons 41 0)
           (cons 42 0)
           (cons 91 0)
           (list 10 14.697664 -1.0206)
           (cons 40 0)
           (cons 41 0)
           (cons 42 0)
           (cons 91 0)
           (list 10 15.502336 -1.0206)
           (cons 40 0)
           (cons 41 0)
           (cons 42 0)
           (cons 91 0)
           (list 10 15.6588 -1.0731272)
           (cons 40 0)
           (cons 41 0)
           (cons 42 0)
           (cons 91 0)
           (list 10 15.6588 -1.2474728)
           (cons 40 0)
           (cons 41 0)
           (cons 42 0)
           (cons 91 0)
           (list 10 15.502336 -1.3)
           (cons 40 0)
           (cons 41 0)
           (cons 42 0)
           (cons 91 0)
           (list 10 14.697664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.5412 0.5702072)
           (cons 40 0)
           (cons 41 0)
           (cons 42 0)
           (cons 91 0)
           (list 10 14.5412 0.7445528)
           (cons 40 0)
           (cons 41 0)
           (cons 42 0)
           (cons 91 0)
           (list 10 14.697664 0.79708)
           (cons 40 0)
           (cons 41 0)
           (cons 42 0)
           (cons 91 0)
           (list 10 15.502336 0.79708)
           (cons 40 0)
           (cons 41 0)
           (cons 42 0)
           (cons 91 0)
           (list 10 15.6588 0.7445528)
           (cons 40 0)
           (cons 41 0)
           (cons 42 0)
           (cons 91 0)
           (list 10 15.6588 0.5702072)
           (cons 40 0)
           (cons 41 0)
           (cons 42 0)
           (cons 91 0)
           (list 10 15.502336 0.51768)
           (cons 40 0)
           (cons 41 0)
           (cons 42 0)
           (cons 91 0)
           (list 10 14.697664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.5412 1.0731272)
           (cons 40 0)
           (cons 41 0)
           (cons 42 0)
           (cons 91 0)
           (list 10 14.5412 1.2474728)
           (cons 40 0)
           (cons 41 0)
           (cons 42 0)
           (cons 91 0)
           (list 10 14.697664 1.3)
           (cons 40 0)
           (cons 41 0)
           (cons 42 0)
           (cons 91 0)
           (list 10 15.502336 1.3)
           (cons 40 0)
           (cons 41 0)
           (cons 42 0)
           (cons 91 0)
           (list 10 15.6588 1.2474728)
           (cons 40 0)
           (cons 41 0)
           (cons 42 0)
           (cons 91 0)
           (list 10 15.6588 1.0731272)
           (cons 40 0)
           (cons 41 0)
           (cons 42 0)
           (cons 91 0)
           (list 10 15.502336 1.0206)
           (cons 40 0)
           (cons 41 0)
           (cons 42 0)
           (cons 91 0)
           (list 10 14.697664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 13.8 1.3 0)
           (cons 50 0)
          )
         )
         (entmake
          (list
           (cons 0 "POINT")
           (cons 100 "AcDbEntity")
           (cons 67 0)
           (cons 8 "0")
           (cons 100 "AcDbPoint")
           (list 10 13.8 -1.3 0)
           (cons 50 0)
          )
         )
         (entmake
          (list
           (cons 0 "POINT")
           (cons 100 "AcDbEntity")
           (cons 67 0)
           (cons 8 "0")
           (cons 100 "AcDbPoint")
           (list 10 16.2 -1.3 0)
           (cons 50 0)
          )
         )
         (entmake
          (list
           (cons 0 "POINT")
           (cons 100 "AcDbEntity")
           (cons 67 0)
           (cons 8 "0")
           (cons 100 "AcDbPoint")
           (list 10 16.2 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 1.3 0 0)
           (cons 50 0)
          )
         )
         (entmake
          (list
           (cons 0 "ATTDEF")
           (cons 100 "AcDbEntity")
           (cons 67 0)
           (cons 8 "0")
           (cons 100 "AcDbText")
           (list 10 0.6 0.56666667 0)
           (cons 40 0.2)
           (cons 1 "1.300")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 0.23333333 0)
           (cons 40 0.2)
           (cons 1 "1.300")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.1 0)
           (cons 40 0.2)
           (cons 1 "13.800")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-17-TRAILER"))
        (progn
         (entmake)
         (entmake
          (list
           (cons 0 "BLOCK")
           (cons 2 "AB_INF-WB-17-TRAILER")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 14.3 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 14.3 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.6062 -0.7445528)
           (cons 40 0)
           (cons 41 0)
           (cons 42 0)
           (cons 91 0)
           (list 10 11.6062 -0.5702072)
           (cons 40 0)
           (cons 41 0)
           (cons 42 0)
           (cons 91 0)
           (list 10 11.762664 -0.51768)
           (cons 40 0)
           (cons 41 0)
           (cons 42 0)
           (cons 91 0)
           (list 10 12.567336 -0.51768)
           (cons 40 0)
           (cons 41 0)
           (cons 42 0)
           (cons 91 0)
           (list 10 12.7238 -0.5702072)
           (cons 40 0)
           (cons 41 0)
           (cons 42 0)
           (cons 91 0)
           (list 10 12.7238 -0.7445528)
           (cons 40 0)
           (cons 41 0)
           (cons 42 0)
           (cons 91 0)
           (list 10 12.567336 -0.79708)
           (cons 40 0)
           (cons 41 0)
           (cons 42 0)
           (cons 91 0)
           (list 10 11.762664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.6062 -1.2474728)
           (cons 40 0)
           (cons 41 0)
           (cons 42 0)
           (cons 91 0)
           (list 10 11.6062 -1.0731272)
           (cons 40 0)
           (cons 41 0)
           (cons 42 0)
           (cons 91 0)
           (list 10 11.762664 -1.0206)
           (cons 40 0)
           (cons 41 0)
           (cons 42 0)
           (cons 91 0)
           (list 10 12.567336 -1.0206)
           (cons 40 0)
           (cons 41 0)
           (cons 42 0)
           (cons 91 0)
           (list 10 12.7238 -1.0731272)
           (cons 40 0)
           (cons 41 0)
           (cons 42 0)
           (cons 91 0)
           (list 10 12.7238 -1.2474728)
           (cons 40 0)
           (cons 41 0)
           (cons 42 0)
           (cons 91 0)
           (list 10 12.567336 -1.3)
           (cons 40 0)
           (cons 41 0)
           (cons 42 0)
           (cons 91 0)
           (list 10 11.762664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.6062 0.5702072)
           (cons 40 0)
           (cons 41 0)
           (cons 42 0)
           (cons 91 0)
           (list 10 11.6062 0.7445528)
           (cons 40 0)
           (cons 41 0)
           (cons 42 0)
           (cons 91 0)
           (list 10 11.762664 0.79708)
           (cons 40 0)
           (cons 41 0)
           (cons 42 0)
           (cons 91 0)
           (list 10 12.567336 0.79708)
           (cons 40 0)
           (cons 41 0)
           (cons 42 0)
           (cons 91 0)
           (list 10 12.7238 0.7445528)
           (cons 40 0)
           (cons 41 0)
           (cons 42 0)
           (cons 91 0)
           (list 10 12.7238 0.5702072)
           (cons 40 0)
           (cons 41 0)
           (cons 42 0)
           (cons 91 0)
           (list 10 12.567336 0.51768)
           (cons 40 0)
           (cons 41 0)
           (cons 42 0)
           (cons 91 0)
           (list 10 11.762664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.6062 1.0731272)
           (cons 40 0)
           (cons 41 0)
           (cons 42 0)
           (cons 91 0)
           (list 10 11.6062 1.2474728)
           (cons 40 0)
           (cons 41 0)
           (cons 42 0)
           (cons 91 0)
           (list 10 11.762664 1.3)
           (cons 40 0)
           (cons 41 0)
           (cons 42 0)
           (cons 91 0)
           (list 10 12.567336 1.3)
           (cons 40 0)
           (cons 41 0)
           (cons 42 0)
           (cons 91 0)
           (list 10 12.7238 1.2474728)
           (cons 40 0)
           (cons 41 0)
           (cons 42 0)
           (cons 91 0)
           (list 10 12.7238 1.0731272)
           (cons 40 0)
           (cons 41 0)
           (cons 42 0)
           (cons 91 0)
           (list 10 12.567336 1.0206)
           (cons 40 0)
           (cons 41 0)
           (cons 42 0)
           (cons 91 0)
           (list 10 11.762664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.8762 -0.7445528)
           (cons 40 0)
           (cons 41 0)
           (cons 42 0)
           (cons 91 0)
           (list 10 12.8762 -0.5702072)
           (cons 40 0)
           (cons 41 0)
           (cons 42 0)
           (cons 91 0)
           (list 10 13.032664 -0.51768)
           (cons 40 0)
           (cons 41 0)
           (cons 42 0)
           (cons 91 0)
           (list 10 13.837336 -0.51768)
           (cons 40 0)
           (cons 41 0)
           (cons 42 0)
           (cons 91 0)
           (list 10 13.9938 -0.5702072)
           (cons 40 0)
           (cons 41 0)
           (cons 42 0)
           (cons 91 0)
           (list 10 13.9938 -0.7445528)
           (cons 40 0)
           (cons 41 0)
           (cons 42 0)
           (cons 91 0)
           (list 10 13.837336 -0.79708)
           (cons 40 0)
           (cons 41 0)
           (cons 42 0)
           (cons 91 0)
           (list 10 13.032664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.8762 -1.2474728)
           (cons 40 0)
           (cons 41 0)
           (cons 42 0)
           (cons 91 0)
           (list 10 12.8762 -1.0731272)
           (cons 40 0)
           (cons 41 0)
           (cons 42 0)
           (cons 91 0)
           (list 10 13.032664 -1.0206)
           (cons 40 0)
           (cons 41 0)
           (cons 42 0)
           (cons 91 0)
           (list 10 13.837336 -1.0206)
           (cons 40 0)
           (cons 41 0)
           (cons 42 0)
           (cons 91 0)
           (list 10 13.9938 -1.0731272)
           (cons 40 0)
           (cons 41 0)
           (cons 42 0)
           (cons 91 0)
           (list 10 13.9938 -1.2474728)
           (cons 40 0)
           (cons 41 0)
           (cons 42 0)
           (cons 91 0)
           (list 10 13.837336 -1.3)
           (cons 40 0)
           (cons 41 0)
           (cons 42 0)
           (cons 91 0)
           (list 10 13.032664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.8762 0.5702072)
           (cons 40 0)
           (cons 41 0)
           (cons 42 0)
           (cons 91 0)
           (list 10 12.8762 0.7445528)
           (cons 40 0)
           (cons 41 0)
           (cons 42 0)
           (cons 91 0)
           (list 10 13.032664 0.79708)
           (cons 40 0)
           (cons 41 0)
           (cons 42 0)
           (cons 91 0)
           (list 10 13.837336 0.79708)
           (cons 40 0)
           (cons 41 0)
           (cons 42 0)
           (cons 91 0)
           (list 10 13.9938 0.7445528)
           (cons 40 0)
           (cons 41 0)
           (cons 42 0)
           (cons 91 0)
           (list 10 13.9938 0.5702072)
           (cons 40 0)
           (cons 41 0)
           (cons 42 0)
           (cons 91 0)
           (list 10 13.837336 0.51768)
           (cons 40 0)
           (cons 41 0)
           (cons 42 0)
           (cons 91 0)
           (list 10 13.032664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.8762 1.0731272)
           (cons 40 0)
           (cons 41 0)
           (cons 42 0)
           (cons 91 0)
           (list 10 12.8762 1.2474728)
           (cons 40 0)
           (cons 41 0)
           (cons 42 0)
           (cons 91 0)
           (list 10 13.032664 1.3)
           (cons 40 0)
           (cons 41 0)
           (cons 42 0)
           (cons 91 0)
           (list 10 13.837336 1.3)
           (cons 40 0)
           (cons 41 0)
           (cons 42 0)
           (cons 91 0)
           (list 10 13.9938 1.2474728)
           (cons 40 0)
           (cons 41 0)
           (cons 42 0)
           (cons 91 0)
           (list 10 13.9938 1.0731272)
           (cons 40 0)
           (cons 41 0)
           (cons 42 0)
           (cons 91 0)
           (list 10 13.837336 1.0206)
           (cons 40 0)
           (cons 41 0)
           (cons 42 0)
           (cons 91 0)
           (list 10 13.032664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 1.3 0 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 14.3 -1.3 0)
           (cons 50 0)
          )
         )
         (entmake
          (list
           (cons 0 "POINT")
           (cons 100 "AcDbEntity")
           (cons 67 0)
           (cons 8 "0")
           (cons 100 "AcDbPoint")
           (list 10 14.3 1.3 0)
           (cons 50 0)
          )
         )
         (entmake
          (list
           (cons 0 "POINT")
           (cons 100 "AcDbEntity")
           (cons 67 0)
           (cons 8 "0")
           (cons 100 "AcDbPoint")
           (list 10 12.8 1.3 0)
           (cons 50 0)
          )
         )
         (entmake
          (list
           (cons 0 "POINT")
           (cons 100 "AcDbEntity")
           (cons 67 0)
           (cons 8 "0")
           (cons 100 "AcDbPoint")
           (list 10 12.8 -1.3 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 14.3 -1.3)
           (cons 40 0)
           (cons 41 0)
           (cons 42 0)
           (cons 91 0)
           (list 10 14.3 1.3)
           (cons 40 0)
           (cons 41 0)
           (cons 42 0)
           (cons 91 0)
           (list 10 0 1.3)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.6 0.56666667 0)
           (cons 40 0.2)
           (cons 1 "1.300")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 0.23333333 0)
           (cons 40 0.2)
           (cons 1 "1.300")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.1 0)
           (cons 40 0.2)
           (cons 1 "12.800")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-17-TRUCK"))
        (progn
         (entmake)
         (entmake
          (list
           (cons 0 "BLOCK")
           (cons 2 "AB_INF-WB-17-TRUCK")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.2 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.2 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.135 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.135 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.2 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.2 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 6.5 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 6.76263966 -0.26263966 0)
           (list 11 6.76263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.3062 -0.7445528)
           (cons 40 0)
           (cons 41 0)
           (cons 42 0)
           (cons 91 0)
           (list 10 5.3062 -0.5702072)
           (cons 40 0)
           (cons 41 0)
           (cons 42 0)
           (cons 91 0)
           (list 10 5.462664 -0.51768)
           (cons 40 0)
           (cons 41 0)
           (cons 42 0)
           (cons 91 0)
           (list 10 6.267336 -0.51768)
           (cons 40 0)
           (cons 41 0)
           (cons 42 0)
           (cons 91 0)
           (list 10 6.4238 -0.5702072)
           (cons 40 0)
           (cons 41 0)
           (cons 42 0)
           (cons 91 0)
           (list 10 6.4238 -0.7445528)
           (cons 40 0)
           (cons 41 0)
           (cons 42 0)
           (cons 91 0)
           (list 10 6.267336 -0.79708)
           (cons 40 0)
           (cons 41 0)
           (cons 42 0)
           (cons 91 0)
           (list 10 5.462664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.3062 -1.2474728)
           (cons 40 0)
           (cons 41 0)
           (cons 42 0)
           (cons 91 0)
           (list 10 5.3062 -1.0731272)
           (cons 40 0)
           (cons 41 0)
           (cons 42 0)
           (cons 91 0)
           (list 10 5.462664 -1.0206)
           (cons 40 0)
           (cons 41 0)
           (cons 42 0)
           (cons 91 0)
           (list 10 6.267336 -1.0206)
           (cons 40 0)
           (cons 41 0)
           (cons 42 0)
           (cons 91 0)
           (list 10 6.4238 -1.0731272)
           (cons 40 0)
           (cons 41 0)
           (cons 42 0)
           (cons 91 0)
           (list 10 6.4238 -1.2474728)
           (cons 40 0)
           (cons 41 0)
           (cons 42 0)
           (cons 91 0)
           (list 10 6.267336 -1.3)
           (cons 40 0)
           (cons 41 0)
           (cons 42 0)
           (cons 91 0)
           (list 10 5.462664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.3062 0.5702072)
           (cons 40 0)
           (cons 41 0)
           (cons 42 0)
           (cons 91 0)
           (list 10 5.3062 0.7445528)
           (cons 40 0)
           (cons 41 0)
           (cons 42 0)
           (cons 91 0)
           (list 10 5.462664 0.79708)
           (cons 40 0)
           (cons 41 0)
           (cons 42 0)
           (cons 91 0)
           (list 10 6.267336 0.79708)
           (cons 40 0)
           (cons 41 0)
           (cons 42 0)
           (cons 91 0)
           (list 10 6.4238 0.7445528)
           (cons 40 0)
           (cons 41 0)
           (cons 42 0)
           (cons 91 0)
           (list 10 6.4238 0.5702072)
           (cons 40 0)
           (cons 41 0)
           (cons 42 0)
           (cons 91 0)
           (list 10 6.267336 0.51768)
           (cons 40 0)
           (cons 41 0)
           (cons 42 0)
           (cons 91 0)
           (list 10 5.462664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.3062 1.0731272)
           (cons 40 0)
           (cons 41 0)
           (cons 42 0)
           (cons 91 0)
           (list 10 5.3062 1.2474728)
           (cons 40 0)
           (cons 41 0)
           (cons 42 0)
           (cons 91 0)
           (list 10 5.462664 1.3)
           (cons 40 0)
           (cons 41 0)
           (cons 42 0)
           (cons 91 0)
           (list 10 6.267336 1.3)
           (cons 40 0)
           (cons 41 0)
           (cons 42 0)
           (cons 91 0)
           (list 10 6.4238 1.2474728)
           (cons 40 0)
           (cons 41 0)
           (cons 42 0)
           (cons 91 0)
           (list 10 6.4238 1.0731272)
           (cons 40 0)
           (cons 41 0)
           (cons 42 0)
           (cons 91 0)
           (list 10 6.267336 1.0206)
           (cons 40 0)
           (cons 41 0)
           (cons 42 0)
           (cons 91 0)
           (list 10 5.462664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.5762 -0.7445528)
           (cons 40 0)
           (cons 41 0)
           (cons 42 0)
           (cons 91 0)
           (list 10 6.5762 -0.5702072)
           (cons 40 0)
           (cons 41 0)
           (cons 42 0)
           (cons 91 0)
           (list 10 6.732664 -0.51768)
           (cons 40 0)
           (cons 41 0)
           (cons 42 0)
           (cons 91 0)
           (list 10 7.537336 -0.51768)
           (cons 40 0)
           (cons 41 0)
           (cons 42 0)
           (cons 91 0)
           (list 10 7.6938 -0.5702072)
           (cons 40 0)
           (cons 41 0)
           (cons 42 0)
           (cons 91 0)
           (list 10 7.6938 -0.7445528)
           (cons 40 0)
           (cons 41 0)
           (cons 42 0)
           (cons 91 0)
           (list 10 7.537336 -0.79708)
           (cons 40 0)
           (cons 41 0)
           (cons 42 0)
           (cons 91 0)
           (list 10 6.732664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.5762 -1.2474728)
           (cons 40 0)
           (cons 41 0)
           (cons 42 0)
           (cons 91 0)
           (list 10 6.5762 -1.0731272)
           (cons 40 0)
           (cons 41 0)
           (cons 42 0)
           (cons 91 0)
           (list 10 6.732664 -1.0206)
           (cons 40 0)
           (cons 41 0)
           (cons 42 0)
           (cons 91 0)
           (list 10 7.537336 -1.0206)
           (cons 40 0)
           (cons 41 0)
           (cons 42 0)
           (cons 91 0)
           (list 10 7.6938 -1.0731272)
           (cons 40 0)
           (cons 41 0)
           (cons 42 0)
           (cons 91 0)
           (list 10 7.6938 -1.2474728)
           (cons 40 0)
           (cons 41 0)
           (cons 42 0)
           (cons 91 0)
           (list 10 7.537336 -1.3)
           (cons 40 0)
           (cons 41 0)
           (cons 42 0)
           (cons 91 0)
           (list 10 6.732664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.5762 0.5702072)
           (cons 40 0)
           (cons 41 0)
           (cons 42 0)
           (cons 91 0)
           (list 10 6.5762 0.7445528)
           (cons 40 0)
           (cons 41 0)
           (cons 42 0)
           (cons 91 0)
           (list 10 6.732664 0.79708)
           (cons 40 0)
           (cons 41 0)
           (cons 42 0)
           (cons 91 0)
           (list 10 7.537336 0.79708)
           (cons 40 0)
           (cons 41 0)
           (cons 42 0)
           (cons 91 0)
           (list 10 7.6938 0.7445528)
           (cons 40 0)
           (cons 41 0)
           (cons 42 0)
           (cons 91 0)
           (list 10 7.6938 0.5702072)
           (cons 40 0)
           (cons 41 0)
           (cons 42 0)
           (cons 91 0)
           (list 10 7.537336 0.51768)
           (cons 40 0)
           (cons 41 0)
           (cons 42 0)
           (cons 91 0)
           (list 10 6.732664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.5762 1.0731272)
           (cons 40 0)
           (cons 41 0)
           (cons 42 0)
           (cons 91 0)
           (list 10 6.5762 1.2474728)
           (cons 40 0)
           (cons 41 0)
           (cons 42 0)
           (cons 91 0)
           (list 10 6.732664 1.3)
           (cons 40 0)
           (cons 41 0)
           (cons 42 0)
           (cons 91 0)
           (list 10 7.537336 1.3)
           (cons 40 0)
           (cons 41 0)
           (cons 42 0)
           (cons 91 0)
           (list 10 7.6938 1.2474728)
           (cons 40 0)
           (cons 41 0)
           (cons 42 0)
           (cons 91 0)
           (list 10 7.6938 1.0731272)
           (cons 40 0)
           (cons 41 0)
           (cons 42 0)
           (cons 91 0)
           (list 10 7.537336 1.0206)
           (cons 40 0)
           (cons 41 0)
           (cons 42 0)
           (cons 91 0)
           (list 10 6.732664 1.0206)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelLeftM1")
           (list 10 1 -1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM1")
           (list 10 1 1.0206 0)
           (cons 41 1)
           (cons 42 1)
           (cons 43 1)
           (cons 50 0)
           (cons 70 0)
           (cons 71 0)
           (cons 44 0)
           (cons 45 0)
          )
         )
         (entmake
          (list
           (cons 0 "POINT")
           (cons 100 "AcDbEntity")
           (cons 67 0)
           (cons 8 "0")
           (cons 100 "AcDbPoint")
           (list 10 1 0 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 6.5 0 0)
           (cons 50 0)
          )
         )
         (entmake
          (list
           (cons 0 "POINT")
           (cons 100 "AcDbEntity")
           (cons 67 0)
           (cons 8 "0")
           (cons 100 "AcDbPoint")
           (list 10 6.5 1.3 0)
           (cons 50 0)
          )
         )
         (entmake
          (list
           (cons 0 "POINT")
           (cons 100 "AcDbEntity")
           (cons 67 0)
           (cons 8 "0")
           (cons 100 "AcDbPoint")
           (list 10 6.5 -1.3 0)
           (cons 50 0)
          )
         )
         (entmake
          (list
           (cons 0 "POINT")
           (cons 100 "AcDbEntity")
           (cons 67 0)
           (cons 8 "0")
           (cons 100 "AcDbPoint")
           (list 10 1 1.3 0)
           (cons 50 0)
          )
         )
         (entmake
          (list
           (cons 0 "POINT")
           (cons 100 "AcDbEntity")
           (cons 67 0)
           (cons 8 "0")
           (cons 100 "AcDbPoint")
           (list 10 1 -1.3 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 7.135 -1.3)
           (cons 40 0)
           (cons 41 0)
           (cons 42 0)
           (cons 91 0)
           (list 10 7.135 1.3)
           (cons 40 0)
           (cons 41 0)
           (cons 42 0)
           (cons 91 0)
           (list 10 0 1.3)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.3 0.56666667 0)
           (cons 40 0.2)
           (cons 1 "1.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 0.23333333 0)
           (cons 40 0.2)
           (cons 1 "1.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.1 0)
           (cons 40 0.2)
           (cons 1 "6.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.43333333 0)
           (cons 40 0.2)
           (cons 1 "6.500")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.76666667 0)
           (cons 40 0.2)
           (cons 1 "24.22")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-15-TRAILER"))
        (progn
         (entmake)
         (entmake
          (list
           (cons 0 "BLOCK")
           (cons 2 "AB_INF-WB-15-TRAILER")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 11.6 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 11.6 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.2062 -0.7445528)
           (cons 40 0)
           (cons 41 0)
           (cons 42 0)
           (cons 91 0)
           (list 10 9.2062 -0.5702072)
           (cons 40 0)
           (cons 41 0)
           (cons 42 0)
           (cons 91 0)
           (list 10 9.362664 -0.51768)
           (cons 40 0)
           (cons 41 0)
           (cons 42 0)
           (cons 91 0)
           (list 10 10.167336 -0.51768)
           (cons 40 0)
           (cons 41 0)
           (cons 42 0)
           (cons 91 0)
           (list 10 10.3238 -0.5702072)
           (cons 40 0)
           (cons 41 0)
           (cons 42 0)
           (cons 91 0)
           (list 10 10.3238 -0.7445528)
           (cons 40 0)
           (cons 41 0)
           (cons 42 0)
           (cons 91 0)
           (list 10 10.167336 -0.79708)
           (cons 40 0)
           (cons 41 0)
           (cons 42 0)
           (cons 91 0)
           (list 10 9.362664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.2062 -1.2474728)
           (cons 40 0)
           (cons 41 0)
           (cons 42 0)
           (cons 91 0)
           (list 10 9.2062 -1.0731272)
           (cons 40 0)
           (cons 41 0)
           (cons 42 0)
           (cons 91 0)
           (list 10 9.362664 -1.0206)
           (cons 40 0)
           (cons 41 0)
           (cons 42 0)
           (cons 91 0)
           (list 10 10.167336 -1.0206)
           (cons 40 0)
           (cons 41 0)
           (cons 42 0)
           (cons 91 0)
           (list 10 10.3238 -1.0731272)
           (cons 40 0)
           (cons 41 0)
           (cons 42 0)
           (cons 91 0)
           (list 10 10.3238 -1.2474728)
           (cons 40 0)
           (cons 41 0)
           (cons 42 0)
           (cons 91 0)
           (list 10 10.167336 -1.3)
           (cons 40 0)
           (cons 41 0)
           (cons 42 0)
           (cons 91 0)
           (list 10 9.362664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.2062 0.5702072)
           (cons 40 0)
           (cons 41 0)
           (cons 42 0)
           (cons 91 0)
           (list 10 9.2062 0.7445528)
           (cons 40 0)
           (cons 41 0)
           (cons 42 0)
           (cons 91 0)
           (list 10 9.362664 0.79708)
           (cons 40 0)
           (cons 41 0)
           (cons 42 0)
           (cons 91 0)
           (list 10 10.167336 0.79708)
           (cons 40 0)
           (cons 41 0)
           (cons 42 0)
           (cons 91 0)
           (list 10 10.3238 0.7445528)
           (cons 40 0)
           (cons 41 0)
           (cons 42 0)
           (cons 91 0)
           (list 10 10.3238 0.5702072)
           (cons 40 0)
           (cons 41 0)
           (cons 42 0)
           (cons 91 0)
           (list 10 10.167336 0.51768)
           (cons 40 0)
           (cons 41 0)
           (cons 42 0)
           (cons 91 0)
           (list 10 9.362664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.2062 1.0731272)
           (cons 40 0)
           (cons 41 0)
           (cons 42 0)
           (cons 91 0)
           (list 10 9.2062 1.2474728)
           (cons 40 0)
           (cons 41 0)
           (cons 42 0)
           (cons 91 0)
           (list 10 9.362664 1.3)
           (cons 40 0)
           (cons 41 0)
           (cons 42 0)
           (cons 91 0)
           (list 10 10.167336 1.3)
           (cons 40 0)
           (cons 41 0)
           (cons 42 0)
           (cons 91 0)
           (list 10 10.3238 1.2474728)
           (cons 40 0)
           (cons 41 0)
           (cons 42 0)
           (cons 91 0)
           (list 10 10.3238 1.0731272)
           (cons 40 0)
           (cons 41 0)
           (cons 42 0)
           (cons 91 0)
           (list 10 10.167336 1.0206)
           (cons 40 0)
           (cons 41 0)
           (cons 42 0)
           (cons 91 0)
           (list 10 9.362664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.4762 -0.7445528)
           (cons 40 0)
           (cons 41 0)
           (cons 42 0)
           (cons 91 0)
           (list 10 10.4762 -0.5702072)
           (cons 40 0)
           (cons 41 0)
           (cons 42 0)
           (cons 91 0)
           (list 10 10.632664 -0.51768)
           (cons 40 0)
           (cons 41 0)
           (cons 42 0)
           (cons 91 0)
           (list 10 11.437336 -0.51768)
           (cons 40 0)
           (cons 41 0)
           (cons 42 0)
           (cons 91 0)
           (list 10 11.5938 -0.5702072)
           (cons 40 0)
           (cons 41 0)
           (cons 42 0)
           (cons 91 0)
           (list 10 11.5938 -0.7445528)
           (cons 40 0)
           (cons 41 0)
           (cons 42 0)
           (cons 91 0)
           (list 10 11.437336 -0.79708)
           (cons 40 0)
           (cons 41 0)
           (cons 42 0)
           (cons 91 0)
           (list 10 10.632664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.4762 -1.2474728)
           (cons 40 0)
           (cons 41 0)
           (cons 42 0)
           (cons 91 0)
           (list 10 10.4762 -1.0731272)
           (cons 40 0)
           (cons 41 0)
           (cons 42 0)
           (cons 91 0)
           (list 10 10.632664 -1.0206)
           (cons 40 0)
           (cons 41 0)
           (cons 42 0)
           (cons 91 0)
           (list 10 11.437336 -1.0206)
           (cons 40 0)
           (cons 41 0)
           (cons 42 0)
           (cons 91 0)
           (list 10 11.5938 -1.0731272)
           (cons 40 0)
           (cons 41 0)
           (cons 42 0)
           (cons 91 0)
           (list 10 11.5938 -1.2474728)
           (cons 40 0)
           (cons 41 0)
           (cons 42 0)
           (cons 91 0)
           (list 10 11.437336 -1.3)
           (cons 40 0)
           (cons 41 0)
           (cons 42 0)
           (cons 91 0)
           (list 10 10.632664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.4762 0.5702072)
           (cons 40 0)
           (cons 41 0)
           (cons 42 0)
           (cons 91 0)
           (list 10 10.4762 0.7445528)
           (cons 40 0)
           (cons 41 0)
           (cons 42 0)
           (cons 91 0)
           (list 10 10.632664 0.79708)
           (cons 40 0)
           (cons 41 0)
           (cons 42 0)
           (cons 91 0)
           (list 10 11.437336 0.79708)
           (cons 40 0)
           (cons 41 0)
           (cons 42 0)
           (cons 91 0)
           (list 10 11.5938 0.7445528)
           (cons 40 0)
           (cons 41 0)
           (cons 42 0)
           (cons 91 0)
           (list 10 11.5938 0.5702072)
           (cons 40 0)
           (cons 41 0)
           (cons 42 0)
           (cons 91 0)
           (list 10 11.437336 0.51768)
           (cons 40 0)
           (cons 41 0)
           (cons 42 0)
           (cons 91 0)
           (list 10 10.632664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.4762 1.0731272)
           (cons 40 0)
           (cons 41 0)
           (cons 42 0)
           (cons 91 0)
           (list 10 10.4762 1.2474728)
           (cons 40 0)
           (cons 41 0)
           (cons 42 0)
           (cons 91 0)
           (list 10 10.632664 1.3)
           (cons 40 0)
           (cons 41 0)
           (cons 42 0)
           (cons 91 0)
           (list 10 11.437336 1.3)
           (cons 40 0)
           (cons 41 0)
           (cons 42 0)
           (cons 91 0)
           (list 10 11.5938 1.2474728)
           (cons 40 0)
           (cons 41 0)
           (cons 42 0)
           (cons 91 0)
           (list 10 11.5938 1.0731272)
           (cons 40 0)
           (cons 41 0)
           (cons 42 0)
           (cons 91 0)
           (list 10 11.437336 1.0206)
           (cons 40 0)
           (cons 41 0)
           (cons 42 0)
           (cons 91 0)
           (list 10 10.632664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 1.3 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 11.6 -1.3)
           (cons 40 0)
           (cons 41 0)
           (cons 42 0)
           (cons 91 0)
           (list 10 11.6 1.3)
           (cons 40 0)
           (cons 41 0)
           (cons 42 0)
           (cons 91 0)
           (list 10 0 1.3)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 11.6 -1.3 0)
           (cons 50 0)
          )
         )
         (entmake
          (list
           (cons 0 "POINT")
           (cons 100 "AcDbEntity")
           (cons 67 0)
           (cons 8 "0")
           (cons 100 "AcDbPoint")
           (list 10 11.6 1.3 0)
           (cons 50 0)
          )
         )
         (entmake
          (list
           (cons 0 "POINT")
           (cons 100 "AcDbEntity")
           (cons 67 0)
           (cons 8 "0")
           (cons 100 "AcDbPoint")
           (list 10 10.4 1.3 0)
           (cons 50 0)
          )
         )
         (entmake
          (list
           (cons 0 "POINT")
           (cons 100 "AcDbEntity")
           (cons 67 0)
           (cons 8 "0")
           (cons 100 "AcDbPoint")
           (list 10 10.4 -1.3 0)
           (cons 50 0)
          )
         )
         (entmake
          (list
           (cons 0 "ATTDEF")
           (cons 100 "AcDbEntity")
           (cons 67 0)
           (cons 8 "0")
           (cons 100 "AcDbText")
           (list 10 0.6 0.56666667 0)
           (cons 40 0.2)
           (cons 1 "1.300")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 0.23333333 0)
           (cons 40 0.2)
           (cons 1 "1.300")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.1 0)
           (cons 40 0.2)
           (cons 1 "10.400")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-15-TRUCK"))
        (progn
         (entmake)
         (entmake
          (list
           (cons 0 "BLOCK")
           (cons 2 "AB_INF-WB-15-TRUCK")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.035 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.035 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 6.4 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 6.66263966 -0.26263966 0)
           (list 11 6.66263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.2062 -0.7445528)
           (cons 40 0)
           (cons 41 0)
           (cons 42 0)
           (cons 91 0)
           (list 10 5.2062 -0.5702072)
           (cons 40 0)
           (cons 41 0)
           (cons 42 0)
           (cons 91 0)
           (list 10 5.362664 -0.51768)
           (cons 40 0)
           (cons 41 0)
           (cons 42 0)
           (cons 91 0)
           (list 10 6.167336 -0.51768)
           (cons 40 0)
           (cons 41 0)
           (cons 42 0)
           (cons 91 0)
           (list 10 6.3238 -0.5702072)
           (cons 40 0)
           (cons 41 0)
           (cons 42 0)
           (cons 91 0)
           (list 10 6.3238 -0.7445528)
           (cons 40 0)
           (cons 41 0)
           (cons 42 0)
           (cons 91 0)
           (list 10 6.167336 -0.79708)
           (cons 40 0)
           (cons 41 0)
           (cons 42 0)
           (cons 91 0)
           (list 10 5.362664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.2062 -1.2474728)
           (cons 40 0)
           (cons 41 0)
           (cons 42 0)
           (cons 91 0)
           (list 10 5.2062 -1.0731272)
           (cons 40 0)
           (cons 41 0)
           (cons 42 0)
           (cons 91 0)
           (list 10 5.362664 -1.0206)
           (cons 40 0)
           (cons 41 0)
           (cons 42 0)
           (cons 91 0)
           (list 10 6.167336 -1.0206)
           (cons 40 0)
           (cons 41 0)
           (cons 42 0)
           (cons 91 0)
           (list 10 6.3238 -1.0731272)
           (cons 40 0)
           (cons 41 0)
           (cons 42 0)
           (cons 91 0)
           (list 10 6.3238 -1.2474728)
           (cons 40 0)
           (cons 41 0)
           (cons 42 0)
           (cons 91 0)
           (list 10 6.167336 -1.3)
           (cons 40 0)
           (cons 41 0)
           (cons 42 0)
           (cons 91 0)
           (list 10 5.362664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.2062 0.5702072)
           (cons 40 0)
           (cons 41 0)
           (cons 42 0)
           (cons 91 0)
           (list 10 5.2062 0.7445528)
           (cons 40 0)
           (cons 41 0)
           (cons 42 0)
           (cons 91 0)
           (list 10 5.362664 0.79708)
           (cons 40 0)
           (cons 41 0)
           (cons 42 0)
           (cons 91 0)
           (list 10 6.167336 0.79708)
           (cons 40 0)
           (cons 41 0)
           (cons 42 0)
           (cons 91 0)
           (list 10 6.3238 0.7445528)
           (cons 40 0)
           (cons 41 0)
           (cons 42 0)
           (cons 91 0)
           (list 10 6.3238 0.5702072)
           (cons 40 0)
           (cons 41 0)
           (cons 42 0)
           (cons 91 0)
           (list 10 6.167336 0.51768)
           (cons 40 0)
           (cons 41 0)
           (cons 42 0)
           (cons 91 0)
           (list 10 5.362664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.2062 1.0731272)
           (cons 40 0)
           (cons 41 0)
           (cons 42 0)
           (cons 91 0)
           (list 10 5.2062 1.2474728)
           (cons 40 0)
           (cons 41 0)
           (cons 42 0)
           (cons 91 0)
           (list 10 5.362664 1.3)
           (cons 40 0)
           (cons 41 0)
           (cons 42 0)
           (cons 91 0)
           (list 10 6.167336 1.3)
           (cons 40 0)
           (cons 41 0)
           (cons 42 0)
           (cons 91 0)
           (list 10 6.3238 1.2474728)
           (cons 40 0)
           (cons 41 0)
           (cons 42 0)
           (cons 91 0)
           (list 10 6.3238 1.0731272)
           (cons 40 0)
           (cons 41 0)
           (cons 42 0)
           (cons 91 0)
           (list 10 6.167336 1.0206)
           (cons 40 0)
           (cons 41 0)
           (cons 42 0)
           (cons 91 0)
           (list 10 5.362664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.4762 -0.7445528)
           (cons 40 0)
           (cons 41 0)
           (cons 42 0)
           (cons 91 0)
           (list 10 6.4762 -0.5702072)
           (cons 40 0)
           (cons 41 0)
           (cons 42 0)
           (cons 91 0)
           (list 10 6.632664 -0.51768)
           (cons 40 0)
           (cons 41 0)
           (cons 42 0)
           (cons 91 0)
           (list 10 7.437336 -0.51768)
           (cons 40 0)
           (cons 41 0)
           (cons 42 0)
           (cons 91 0)
           (list 10 7.5938 -0.5702072)
           (cons 40 0)
           (cons 41 0)
           (cons 42 0)
           (cons 91 0)
           (list 10 7.5938 -0.7445528)
           (cons 40 0)
           (cons 41 0)
           (cons 42 0)
           (cons 91 0)
           (list 10 7.437336 -0.79708)
           (cons 40 0)
           (cons 41 0)
           (cons 42 0)
           (cons 91 0)
           (list 10 6.632664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.4762 -1.2474728)
           (cons 40 0)
           (cons 41 0)
           (cons 42 0)
           (cons 91 0)
           (list 10 6.4762 -1.0731272)
           (cons 40 0)
           (cons 41 0)
           (cons 42 0)
           (cons 91 0)
           (list 10 6.632664 -1.0206)
           (cons 40 0)
           (cons 41 0)
           (cons 42 0)
           (cons 91 0)
           (list 10 7.437336 -1.0206)
           (cons 40 0)
           (cons 41 0)
           (cons 42 0)
           (cons 91 0)
           (list 10 7.5938 -1.0731272)
           (cons 40 0)
           (cons 41 0)
           (cons 42 0)
           (cons 91 0)
           (list 10 7.5938 -1.2474728)
           (cons 40 0)
           (cons 41 0)
           (cons 42 0)
           (cons 91 0)
           (list 10 7.437336 -1.3)
           (cons 40 0)
           (cons 41 0)
           (cons 42 0)
           (cons 91 0)
           (list 10 6.632664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.4762 0.5702072)
           (cons 40 0)
           (cons 41 0)
           (cons 42 0)
           (cons 91 0)
           (list 10 6.4762 0.7445528)
           (cons 40 0)
           (cons 41 0)
           (cons 42 0)
           (cons 91 0)
           (list 10 6.632664 0.79708)
           (cons 40 0)
           (cons 41 0)
           (cons 42 0)
           (cons 91 0)
           (list 10 7.437336 0.79708)
           (cons 40 0)
           (cons 41 0)
           (cons 42 0)
           (cons 91 0)
           (list 10 7.5938 0.7445528)
           (cons 40 0)
           (cons 41 0)
           (cons 42 0)
           (cons 91 0)
           (list 10 7.5938 0.5702072)
           (cons 40 0)
           (cons 41 0)
           (cons 42 0)
           (cons 91 0)
           (list 10 7.437336 0.51768)
           (cons 40 0)
           (cons 41 0)
           (cons 42 0)
           (cons 91 0)
           (list 10 6.632664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.4762 1.0731272)
           (cons 40 0)
           (cons 41 0)
           (cons 42 0)
           (cons 91 0)
           (list 10 6.4762 1.2474728)
           (cons 40 0)
           (cons 41 0)
           (cons 42 0)
           (cons 91 0)
           (list 10 6.632664 1.3)
           (cons 40 0)
           (cons 41 0)
           (cons 42 0)
           (cons 91 0)
           (list 10 7.437336 1.3)
           (cons 40 0)
           (cons 41 0)
           (cons 42 0)
           (cons 91 0)
           (list 10 7.5938 1.2474728)
           (cons 40 0)
           (cons 41 0)
           (cons 42 0)
           (cons 91 0)
           (list 10 7.5938 1.0731272)
           (cons 40 0)
           (cons 41 0)
           (cons 42 0)
           (cons 91 0)
           (list 10 7.437336 1.0206)
           (cons 40 0)
           (cons 41 0)
           (cons 42 0)
           (cons 91 0)
           (list 10 6.632664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0.9 0 0)
           (cons 50 0)
          )
         )
         (entmake
          (list
           (cons 0 "INSERT")
           (cons 100 "AcDbEntity")
           (cons 67 0)
           (cons 8 "0")
           (cons 100 "AcDbBlockReference")
           (cons 2 "WheelRightM1")
           (list 10 0.9 -1.3 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM1")
           (list 10 0.9 1.3 0)
           (cons 41 1)
           (cons 42 1)
           (cons 43 1)
           (cons 50 0)
           (cons 70 0)
           (cons 71 0)
           (cons 44 0)
           (cons 45 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 7.035 -1.3)
           (cons 40 0)
           (cons 41 0)
           (cons 42 0)
           (cons 91 0)
           (list 10 7.035 1.3)
           (cons 40 0)
           (cons 41 0)
           (cons 42 0)
           (cons 91 0)
           (list 10 0 1.3)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0.9 1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 6.4 1.3 0)
           (cons 50 0)
          )
         )
         (entmake
          (list
           (cons 0 "POINT")
           (cons 100 "AcDbEntity")
           (cons 67 0)
           (cons 8 "0")
           (cons 100 "AcDbPoint")
           (list 10 0.9 -1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 6.4 -1.3 0)
           (cons 50 0)
          )
         )
         (entmake
          (list
           (cons 0 "POINT")
           (cons 100 "AcDbEntity")
           (cons 67 0)
           (cons 8 "0")
           (cons 100 "AcDbPoint")
           (list 10 6.4 0 0)
           (cons 50 0)
          )
         )
         (entmake
          (list
           (cons 0 "ATTDEF")
           (cons 100 "AcDbEntity")
           (cons 67 0)
           (cons 8 "0")
           (cons 100 "AcDbText")
           (list 10 0.2 0.56666667 0)
           (cons 40 0.2)
           (cons 1 "0.900")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.2 0.23333333 0)
           (cons 40 0.2)
           (cons 1 "0.900")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.2 -0.1 0)
           (cons 40 0.2)
           (cons 1 "6.400")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.2 -0.43333333 0)
           (cons 40 0.2)
           (cons 1 "6.400")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.2 -0.76666667 0)
           (cons 40 0.2)
           (cons 1 "26.06")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-12-TRAILER"))
        (progn
         (entmake)
         (entmake
          (list
           (cons 0 "BLOCK")
           (cons 2 "AB_INF-WB-12-TRAILER")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 10.6 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 10.6 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.0412 -0.7445528)
           (cons 40 0)
           (cons 41 0)
           (cons 42 0)
           (cons 91 0)
           (list 10 7.0412 -0.5702072)
           (cons 40 0)
           (cons 41 0)
           (cons 42 0)
           (cons 91 0)
           (list 10 7.197664 -0.51768)
           (cons 40 0)
           (cons 41 0)
           (cons 42 0)
           (cons 91 0)
           (list 10 8.002336 -0.51768)
           (cons 40 0)
           (cons 41 0)
           (cons 42 0)
           (cons 91 0)
           (list 10 8.1588 -0.5702072)
           (cons 40 0)
           (cons 41 0)
           (cons 42 0)
           (cons 91 0)
           (list 10 8.1588 -0.7445528)
           (cons 40 0)
           (cons 41 0)
           (cons 42 0)
           (cons 91 0)
           (list 10 8.002336 -0.79708)
           (cons 40 0)
           (cons 41 0)
           (cons 42 0)
           (cons 91 0)
           (list 10 7.197664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.0412 -1.2474728)
           (cons 40 0)
           (cons 41 0)
           (cons 42 0)
           (cons 91 0)
           (list 10 7.0412 -1.0731272)
           (cons 40 0)
           (cons 41 0)
           (cons 42 0)
           (cons 91 0)
           (list 10 7.197664 -1.0206)
           (cons 40 0)
           (cons 41 0)
           (cons 42 0)
           (cons 91 0)
           (list 10 8.002336 -1.0206)
           (cons 40 0)
           (cons 41 0)
           (cons 42 0)
           (cons 91 0)
           (list 10 8.1588 -1.0731272)
           (cons 40 0)
           (cons 41 0)
           (cons 42 0)
           (cons 91 0)
           (list 10 8.1588 -1.2474728)
           (cons 40 0)
           (cons 41 0)
           (cons 42 0)
           (cons 91 0)
           (list 10 8.002336 -1.3)
           (cons 40 0)
           (cons 41 0)
           (cons 42 0)
           (cons 91 0)
           (list 10 7.197664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.0412 0.5702072)
           (cons 40 0)
           (cons 41 0)
           (cons 42 0)
           (cons 91 0)
           (list 10 7.0412 0.7445528)
           (cons 40 0)
           (cons 41 0)
           (cons 42 0)
           (cons 91 0)
           (list 10 7.197664 0.79708)
           (cons 40 0)
           (cons 41 0)
           (cons 42 0)
           (cons 91 0)
           (list 10 8.002336 0.79708)
           (cons 40 0)
           (cons 41 0)
           (cons 42 0)
           (cons 91 0)
           (list 10 8.1588 0.7445528)
           (cons 40 0)
           (cons 41 0)
           (cons 42 0)
           (cons 91 0)
           (list 10 8.1588 0.5702072)
           (cons 40 0)
           (cons 41 0)
           (cons 42 0)
           (cons 91 0)
           (list 10 8.002336 0.51768)
           (cons 40 0)
           (cons 41 0)
           (cons 42 0)
           (cons 91 0)
           (list 10 7.197664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.0412 1.0731272)
           (cons 40 0)
           (cons 41 0)
           (cons 42 0)
           (cons 91 0)
           (list 10 7.0412 1.2474728)
           (cons 40 0)
           (cons 41 0)
           (cons 42 0)
           (cons 91 0)
           (list 10 7.197664 1.3)
           (cons 40 0)
           (cons 41 0)
           (cons 42 0)
           (cons 91 0)
           (list 10 8.002336 1.3)
           (cons 40 0)
           (cons 41 0)
           (cons 42 0)
           (cons 91 0)
           (list 10 8.1588 1.2474728)
           (cons 40 0)
           (cons 41 0)
           (cons 42 0)
           (cons 91 0)
           (list 10 8.1588 1.0731272)
           (cons 40 0)
           (cons 41 0)
           (cons 42 0)
           (cons 91 0)
           (list 10 8.002336 1.0206)
           (cons 40 0)
           (cons 41 0)
           (cons 42 0)
           (cons 91 0)
           (list 10 7.197664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.2412 -0.7445528)
           (cons 40 0)
           (cons 41 0)
           (cons 42 0)
           (cons 91 0)
           (list 10 8.2412 -0.5702072)
           (cons 40 0)
           (cons 41 0)
           (cons 42 0)
           (cons 91 0)
           (list 10 8.397664 -0.51768)
           (cons 40 0)
           (cons 41 0)
           (cons 42 0)
           (cons 91 0)
           (list 10 9.202336 -0.51768)
           (cons 40 0)
           (cons 41 0)
           (cons 42 0)
           (cons 91 0)
           (list 10 9.3588 -0.5702072)
           (cons 40 0)
           (cons 41 0)
           (cons 42 0)
           (cons 91 0)
           (list 10 9.3588 -0.7445528)
           (cons 40 0)
           (cons 41 0)
           (cons 42 0)
           (cons 91 0)
           (list 10 9.202336 -0.79708)
           (cons 40 0)
           (cons 41 0)
           (cons 42 0)
           (cons 91 0)
           (list 10 8.397664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.2412 -1.2474728)
           (cons 40 0)
           (cons 41 0)
           (cons 42 0)
           (cons 91 0)
           (list 10 8.2412 -1.0731272)
           (cons 40 0)
           (cons 41 0)
           (cons 42 0)
           (cons 91 0)
           (list 10 8.397664 -1.0206)
           (cons 40 0)
           (cons 41 0)
           (cons 42 0)
           (cons 91 0)
           (list 10 9.202336 -1.0206)
           (cons 40 0)
           (cons 41 0)
           (cons 42 0)
           (cons 91 0)
           (list 10 9.3588 -1.0731272)
           (cons 40 0)
           (cons 41 0)
           (cons 42 0)
           (cons 91 0)
           (list 10 9.3588 -1.2474728)
           (cons 40 0)
           (cons 41 0)
           (cons 42 0)
           (cons 91 0)
           (list 10 9.202336 -1.3)
           (cons 40 0)
           (cons 41 0)
           (cons 42 0)
           (cons 91 0)
           (list 10 8.397664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.2412 0.5702072)
           (cons 40 0)
           (cons 41 0)
           (cons 42 0)
           (cons 91 0)
           (list 10 8.2412 0.7445528)
           (cons 40 0)
           (cons 41 0)
           (cons 42 0)
           (cons 91 0)
           (list 10 8.397664 0.79708)
           (cons 40 0)
           (cons 41 0)
           (cons 42 0)
           (cons 91 0)
           (list 10 9.202336 0.79708)
           (cons 40 0)
           (cons 41 0)
           (cons 42 0)
           (cons 91 0)
           (list 10 9.3588 0.7445528)
           (cons 40 0)
           (cons 41 0)
           (cons 42 0)
           (cons 91 0)
           (list 10 9.3588 0.5702072)
           (cons 40 0)
           (cons 41 0)
           (cons 42 0)
           (cons 91 0)
           (list 10 9.202336 0.51768)
           (cons 40 0)
           (cons 41 0)
           (cons 42 0)
           (cons 91 0)
           (list 10 8.397664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.2412 1.0731272)
           (cons 40 0)
           (cons 41 0)
           (cons 42 0)
           (cons 91 0)
           (list 10 8.2412 1.2474728)
           (cons 40 0)
           (cons 41 0)
           (cons 42 0)
           (cons 91 0)
           (list 10 8.397664 1.3)
           (cons 40 0)
           (cons 41 0)
           (cons 42 0)
           (cons 91 0)
           (list 10 9.202336 1.3)
           (cons 40 0)
           (cons 41 0)
           (cons 42 0)
           (cons 91 0)
           (list 10 9.3588 1.2474728)
           (cons 40 0)
           (cons 41 0)
           (cons 42 0)
           (cons 91 0)
           (list 10 9.3588 1.0731272)
           (cons 40 0)
           (cons 41 0)
           (cons 42 0)
           (cons 91 0)
           (list 10 9.202336 1.0206)
           (cons 40 0)
           (cons 41 0)
           (cons 42 0)
           (cons 91 0)
           (list 10 8.397664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0.6 0 0)
           (cons 50 0)
          )
         )
         (entmake
          (list
           (cons 0 "POINT")
           (cons 100 "AcDbEntity")
           (cons 67 0)
           (cons 8 "0")
           (cons 100 "AcDbPoint")
           (list 10 8.2 1.3 0)
           (cons 50 0)
          )
         )
         (entmake
          (list
           (cons 0 "POINT")
           (cons 100 "AcDbEntity")
           (cons 67 0)
           (cons 8 "0")
           (cons 100 "AcDbPoint")
           (list 10 8.2 -1.3 0)
           (cons 50 0)
          )
         )
         (entmake
          (list
           (cons 0 "POINT")
           (cons 100 "AcDbEntity")
           (cons 67 0)
           (cons 8 "0")
           (cons 100 "AcDbPoint")
           (list 10 10.6 -1.3 0)
           (cons 50 0)
          )
         )
         (entmake
          (list
           (cons 0 "POINT")
           (cons 100 "AcDbEntity")
           (cons 67 0)
           (cons 8 "0")
           (cons 100 "AcDbPoint")
           (list 10 10.6 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 10.6 -1.3)
           (cons 40 0)
           (cons 41 0)
           (cons 42 0)
           (cons 91 0)
           (list 10 10.6 1.3)
           (cons 40 0)
           (cons 41 0)
           (cons 42 0)
           (cons 91 0)
           (list 10 0 1.3)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 -0.1 0.56666667 0)
           (cons 40 0.2)
           (cons 1 "0.600")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 0.23333333 0)
           (cons 40 0.2)
           (cons 1 "0.600")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 -0.1 0)
           (cons 40 0.2)
           (cons 1 "8.200")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-12-TRUCK"))
        (progn
         (entmake)
         (entmake
          (list
           (cons 0 "BLOCK")
           (cons 2 "AB_INF-WB-12-TRUCK")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.2 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.2 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 5.2 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 5.46263966 -0.26263966 0)
           (list 11 5.46263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.6412 -0.7445528)
           (cons 40 0)
           (cons 41 0)
           (cons 42 0)
           (cons 91 0)
           (list 10 4.6412 -0.5702072)
           (cons 40 0)
           (cons 41 0)
           (cons 42 0)
           (cons 91 0)
           (list 10 4.797664 -0.51768)
           (cons 40 0)
           (cons 41 0)
           (cons 42 0)
           (cons 91 0)
           (list 10 5.602336 -0.51768)
           (cons 40 0)
           (cons 41 0)
           (cons 42 0)
           (cons 91 0)
           (list 10 5.7588 -0.5702072)
           (cons 40 0)
           (cons 41 0)
           (cons 42 0)
           (cons 91 0)
           (list 10 5.7588 -0.7445528)
           (cons 40 0)
           (cons 41 0)
           (cons 42 0)
           (cons 91 0)
           (list 10 5.602336 -0.79708)
           (cons 40 0)
           (cons 41 0)
           (cons 42 0)
           (cons 91 0)
           (list 10 4.797664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.6412 -1.2474728)
           (cons 40 0)
           (cons 41 0)
           (cons 42 0)
           (cons 91 0)
           (list 10 4.6412 -1.0731272)
           (cons 40 0)
           (cons 41 0)
           (cons 42 0)
           (cons 91 0)
           (list 10 4.797664 -1.0206)
           (cons 40 0)
           (cons 41 0)
           (cons 42 0)
           (cons 91 0)
           (list 10 5.602336 -1.0206)
           (cons 40 0)
           (cons 41 0)
           (cons 42 0)
           (cons 91 0)
           (list 10 5.7588 -1.0731272)
           (cons 40 0)
           (cons 41 0)
           (cons 42 0)
           (cons 91 0)
           (list 10 5.7588 -1.2474728)
           (cons 40 0)
           (cons 41 0)
           (cons 42 0)
           (cons 91 0)
           (list 10 5.602336 -1.3)
           (cons 40 0)
           (cons 41 0)
           (cons 42 0)
           (cons 91 0)
           (list 10 4.797664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.6412 0.5702072)
           (cons 40 0)
           (cons 41 0)
           (cons 42 0)
           (cons 91 0)
           (list 10 4.6412 0.7445528)
           (cons 40 0)
           (cons 41 0)
           (cons 42 0)
           (cons 91 0)
           (list 10 4.797664 0.79708)
           (cons 40 0)
           (cons 41 0)
           (cons 42 0)
           (cons 91 0)
           (list 10 5.602336 0.79708)
           (cons 40 0)
           (cons 41 0)
           (cons 42 0)
           (cons 91 0)
           (list 10 5.7588 0.7445528)
           (cons 40 0)
           (cons 41 0)
           (cons 42 0)
           (cons 91 0)
           (list 10 5.7588 0.5702072)
           (cons 40 0)
           (cons 41 0)
           (cons 42 0)
           (cons 91 0)
           (list 10 5.602336 0.51768)
           (cons 40 0)
           (cons 41 0)
           (cons 42 0)
           (cons 91 0)
           (list 10 4.797664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.6412 1.0731272)
           (cons 40 0)
           (cons 41 0)
           (cons 42 0)
           (cons 91 0)
           (list 10 4.6412 1.2474728)
           (cons 40 0)
           (cons 41 0)
           (cons 42 0)
           (cons 91 0)
           (list 10 4.797664 1.3)
           (cons 40 0)
           (cons 41 0)
           (cons 42 0)
           (cons 91 0)
           (list 10 5.602336 1.3)
           (cons 40 0)
           (cons 41 0)
           (cons 42 0)
           (cons 91 0)
           (list 10 5.7588 1.2474728)
           (cons 40 0)
           (cons 41 0)
           (cons 42 0)
           (cons 91 0)
           (list 10 5.7588 1.0731272)
           (cons 40 0)
           (cons 41 0)
           (cons 42 0)
           (cons 91 0)
           (list 10 5.602336 1.0206)
           (cons 40 0)
           (cons 41 0)
           (cons 42 0)
           (cons 91 0)
           (list 10 4.797664 1.0206)
           (cons 40 0)
           (cons 41 0)
           (cons 42 0)
           (cons 91 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 5.2 -1.3)
           (cons 40 0)
           (cons 41 0)
           (cons 42 0)
           (cons 91 0)
           (list 10 5.2 1.3)
           (cons 40 0)
           (cons 41 0)
           (cons 42 0)
           (cons 91 0)
           (list 10 0 1.3)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 5.2 0 0)
           (cons 50 0)
          )
         )
         (entmake
          (list
           (cons 0 "POINT")
           (cons 100 "AcDbEntity")
           (cons 67 0)
           (cons 8 "0")
           (cons 100 "AcDbPoint")
           (list 10 5.2 1.3 0)
           (cons 50 0)
          )
         )
         (entmake
          (list
           (cons 0 "POINT")
           (cons 100 "AcDbEntity")
           (cons 67 0)
           (cons 8 "0")
           (cons 100 "AcDbPoint")
           (list 10 5.2 -1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 1.2 0 0)
           (cons 50 0)
          )
         )
         (entmake
          (list
           (cons 0 "INSERT")
           (cons 100 "AcDbEntity")
           (cons 67 0)
           (cons 8 "0")
           (cons 100 "AcDbBlockReference")
           (cons 2 "WheelRightM1")
           (list 10 1.2 1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM1")
           (list 10 1.2 -1.0206 0)
           (cons 41 1)
           (cons 42 1)
           (cons 43 1)
           (cons 50 0)
           (cons 70 0)
           (cons 71 0)
           (cons 44 0)
           (cons 45 0)
          )
         )
         (entmake
          (list
           (cons 0 "POINT")
           (cons 100 "AcDbEntity")
           (cons 67 0)
           (cons 8 "0")
           (cons 100 "AcDbPoint")
           (list 10 1.2 1.3 0)
           (cons 50 0)
          )
         )
         (entmake
          (list
           (cons 0 "POINT")
           (cons 100 "AcDbEntity")
           (cons 67 0)
           (cons 8 "0")
           (cons 100 "AcDbPoint")
           (list 10 1.2 -1.3 0)
           (cons 50 0)
          )
         )
         (entmake
          (list
           (cons 0 "ATTDEF")
           (cons 100 "AcDbEntity")
           (cons 67 0)
           (cons 8 "0")
           (cons 100 "AcDbText")
           (list 10 0.5 0.56666667 0)
           (cons 40 0.2)
           (cons 1 "1.200")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.5 0.23333333 0)
           (cons 40 0.2)
           (cons 1 "1.200")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.5 -0.1 0)
           (cons 40 0.2)
           (cons 1 "5.200")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.5 -0.43333333 0)
           (cons 40 0.2)
           (cons 1 "5.200")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.5 -0.76666667 0)
           (cons 40 0.2)
           (cons 1 "21.36")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-SU9"))
        (progn
         (entmake)
         (entmake
          (list
           (cons 0 "BLOCK")
           (cons 2 "AB_INF-SU9")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 9.1 -1.3)
           (cons 40 0)
           (cons 41 0)
           (cons 42 0)
           (cons 91 0)
           (list 10 9.1 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.1 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.1 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.792 -0.795048)
           (cons 40 0)
           (cons 41 0)
           (cons 42 0)
           (cons 91 0)
           (list 10 6.792 -0.636552)
           (cons 40 0)
           (cons 41 0)
           (cons 42 0)
           (cons 91 0)
           (list 10 6.93424 -0.5888)
           (cons 40 0)
           (cons 41 0)
           (cons 42 0)
           (cons 91 0)
           (list 10 7.66576 -0.5888)
           (cons 40 0)
           (cons 41 0)
           (cons 42 0)
           (cons 91 0)
           (list 10 7.808 -0.636552)
           (cons 40 0)
           (cons 41 0)
           (cons 42 0)
           (cons 91 0)
           (list 10 7.808 -0.795048)
           (cons 40 0)
           (cons 41 0)
           (cons 42 0)
           (cons 91 0)
           (list 10 7.66576 -0.8428)
           (cons 40 0)
           (cons 41 0)
           (cons 42 0)
           (cons 91 0)
           (list 10 6.93424 -0.8428)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.792 -1.252248)
           (cons 40 0)
           (cons 41 0)
           (cons 42 0)
           (cons 91 0)
           (list 10 6.792 -1.093752)
           (cons 40 0)
           (cons 41 0)
           (cons 42 0)
           (cons 91 0)
           (list 10 6.93424 -1.046)
           (cons 40 0)
           (cons 41 0)
           (cons 42 0)
           (cons 91 0)
           (list 10 7.66576 -1.046)
           (cons 40 0)
           (cons 41 0)
           (cons 42 0)
           (cons 91 0)
           (list 10 7.808 -1.093752)
           (cons 40 0)
           (cons 41 0)
           (cons 42 0)
           (cons 91 0)
           (list 10 7.808 -1.252248)
           (cons 40 0)
           (cons 41 0)
           (cons 42 0)
           (cons 91 0)
           (list 10 7.66576 -1.3)
           (cons 40 0)
           (cons 41 0)
           (cons 42 0)
           (cons 91 0)
           (list 10 6.93424 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.792 0.636552)
           (cons 40 0)
           (cons 41 0)
           (cons 42 0)
           (cons 91 0)
           (list 10 6.792 0.795048)
           (cons 40 0)
           (cons 41 0)
           (cons 42 0)
           (cons 91 0)
           (list 10 6.93424 0.8428)
           (cons 40 0)
           (cons 41 0)
           (cons 42 0)
           (cons 91 0)
           (list 10 7.66576 0.8428)
           (cons 40 0)
           (cons 41 0)
           (cons 42 0)
           (cons 91 0)
           (list 10 7.808 0.795048)
           (cons 40 0)
           (cons 41 0)
           (cons 42 0)
           (cons 91 0)
           (list 10 7.808 0.636552)
           (cons 40 0)
           (cons 41 0)
           (cons 42 0)
           (cons 91 0)
           (list 10 7.66576 0.5888)
           (cons 40 0)
           (cons 41 0)
           (cons 42 0)
           (cons 91 0)
           (list 10 6.93424 0.5888)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.792 1.093752)
           (cons 40 0)
           (cons 41 0)
           (cons 42 0)
           (cons 91 0)
           (list 10 6.792 1.252248)
           (cons 40 0)
           (cons 41 0)
           (cons 42 0)
           (cons 91 0)
           (list 10 6.93424 1.3)
           (cons 40 0)
           (cons 41 0)
           (cons 42 0)
           (cons 91 0)
           (list 10 7.66576 1.3)
           (cons 40 0)
           (cons 41 0)
           (cons 42 0)
           (cons 91 0)
           (list 10 7.808 1.252248)
           (cons 40 0)
           (cons 41 0)
           (cons 42 0)
           (cons 91 0)
           (list 10 7.808 1.093752)
           (cons 40 0)
           (cons 41 0)
           (cons 42 0)
           (cons 91 0)
           (list 10 7.66576 1.046)
           (cons 40 0)
           (cons 41 0)
           (cons 42 0)
           (cons 91 0)
           (list 10 6.93424 1.046)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelRightM2")
           (list 10 1.2 1.046 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM2")
           (list 10 1.2 -1.046 0)
           (cons 41 1)
           (cons 42 1)
           (cons 43 1)
           (cons 50 0)
           (cons 70 0)
           (cons 71 0)
           (cons 44 0)
           (cons 45 0)
          )
         )
         (entmake
          (list
           (cons 0 "POINT")
           (cons 100 "AcDbEntity")
           (cons 67 0)
           (cons 8 "0")
           (cons 100 "AcDbPoint")
           (list 10 1.2 0 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 9.1 1.3 0)
           (cons 50 0)
          )
         )
         (entmake
          (list
           (cons 0 "POINT")
           (cons 100 "AcDbEntity")
           (cons 67 0)
           (cons 8 "0")
           (cons 100 "AcDbPoint")
           (list 10 9.1 -1.3 0)
           (cons 50 0)
          )
         )
         (entmake
          (list
           (cons 0 "POINT")
           (cons 100 "AcDbEntity")
           (cons 67 0)
           (cons 8 "0")
           (cons 100 "AcDbPoint")
           (list 10 1.2 -1.3 0)
           (cons 50 0)
          )
         )
         (entmake
          (list
           (cons 0 "POINT")
           (cons 100 "AcDbEntity")
           (cons 67 0)
           (cons 8 "0")
           (cons 100 "AcDbPoint")
           (list 10 1.2 1.3 0)
           (cons 50 0)
          )
         )
         (entmake
          (list
           (cons 0 "POINT")
           (cons 100 "AcDbEntity")
           (cons 67 0)
           (cons 8 "0")
           (cons 100 "AcDbPoint")
           (list 10 7.3 1.3 0)
           (cons 50 0)
          )
         )
         (entmake
          (list
           (cons 0 "POINT")
           (cons 100 "AcDbEntity")
           (cons 67 0)
           (cons 8 "0")
           (cons 100 "AcDbPoint")
           (list 10 7.3 -1.3 0)
           (cons 50 0)
          )
         )
         (entmake
          (list
           (cons 0 "ATTDEF")
           (cons 100 "AcDbEntity")
           (cons 67 0)
           (cons 8 "0")
           (cons 100 "AcDbText")
           (list 10 0.5 0.56666667 0)
           (cons 40 0.2)
           (cons 1 "1.200")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.5 0.23333333 0)
           (cons 40 0.2)
           (cons 1 "1.200")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.5 -0.1 0)
           (cons 40 0.2)
           (cons 1 "7.300")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.5 -0.43333333 0)
           (cons 40 0.2)
           (cons 1 "5.800")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.5 -0.76666667 0)
           (cons 40 0.2)
           (cons 1 "31.50")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-CAMPER"))
        (progn
         (entmake)
         (entmake
          (list
           (cons 0 "BLOCK")
           (cons 2 "AB_INF-CAMPER")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 5)
           (cons 70 129)
           (cons 43 0)
           (cons 38 0)
           (cons 39 0)
           (list 10 0 0)
           (cons 40 0)
           (cons 41 0)
           (cons 42 0)
           (cons 91 0)
           (list 10 0.9 -1.2)
           (cons 40 0)
           (cons 41 0)
           (cons 42 0)
           (cons 91 0)
           (list 10 9.1 -1.2)
           (cons 40 0)
           (cons 41 0)
           (cons 42 0)
           (cons 91 0)
           (list 10 9.1 1.2)
           (cons 40 0)
           (cons 41 0)
           (cons 42 0)
           (cons 91 0)
           (list 10 0.9 1.2)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0.9 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.1 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.1 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0.9 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0.9 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0.9 -1.2 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 0.9 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.16)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.63 -1.170155)
           (cons 40 0)
           (cons 41 0)
           (cons 42 0)
           (cons 91 0)
           (list 10 4.63 -1.071095)
           (cons 40 0)
           (cons 41 0)
           (cons 42 0)
           (cons 91 0)
           (list 10 4.7189 -1.04125)
           (cons 40 0)
           (cons 41 0)
           (cons 42 0)
           (cons 91 0)
           (list 10 5.1761 -1.04125)
           (cons 40 0)
           (cons 41 0)
           (cons 42 0)
           (cons 91 0)
           (list 10 5.265 -1.071095)
           (cons 40 0)
           (cons 41 0)
           (cons 42 0)
           (cons 91 0)
           (list 10 5.265 -1.170155)
           (cons 40 0)
           (cons 41 0)
           (cons 42 0)
           (cons 91 0)
           (list 10 5.1761 -1.2)
           (cons 40 0)
           (cons 41 0)
           (cons 42 0)
           (cons 91 0)
           (list 10 4.7189 -1.2)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.63 1.071095)
           (cons 40 0)
           (cons 41 0)
           (cons 42 0)
           (cons 91 0)
           (list 10 4.63 1.170155)
           (cons 40 0)
           (cons 41 0)
           (cons 42 0)
           (cons 91 0)
           (list 10 4.7189 1.2)
           (cons 40 0)
           (cons 41 0)
           (cons 42 0)
           (cons 91 0)
           (list 10 5.1761 1.2)
           (cons 40 0)
           (cons 41 0)
           (cons 42 0)
           (cons 91 0)
           (list 10 5.265 1.170155)
           (cons 40 0)
           (cons 41 0)
           (cons 42 0)
           (cons 91 0)
           (list 10 5.265 1.071095)
           (cons 40 0)
           (cons 41 0)
           (cons 42 0)
           (cons 91 0)
           (list 10 5.1761 1.04125)
           (cons 40 0)
           (cons 41 0)
           (cons 42 0)
           (cons 91 0)
           (list 10 4.7189 1.04125)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9 -1.170155)
           (cons 40 0)
           (cons 41 0)
           (cons 42 0)
           (cons 91 0)
           (list 10 5.9 -1.071095)
           (cons 40 0)
           (cons 41 0)
           (cons 42 0)
           (cons 91 0)
           (list 10 5.9889 -1.04125)
           (cons 40 0)
           (cons 41 0)
           (cons 42 0)
           (cons 91 0)
           (list 10 6.4461 -1.04125)
           (cons 40 0)
           (cons 41 0)
           (cons 42 0)
           (cons 91 0)
           (list 10 6.535 -1.071095)
           (cons 40 0)
           (cons 41 0)
           (cons 42 0)
           (cons 91 0)
           (list 10 6.535 -1.170155)
           (cons 40 0)
           (cons 41 0)
           (cons 42 0)
           (cons 91 0)
           (list 10 6.4461 -1.2)
           (cons 40 0)
           (cons 41 0)
           (cons 42 0)
           (cons 91 0)
           (list 10 5.9889 -1.2)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9 1.071095)
           (cons 40 0)
           (cons 41 0)
           (cons 42 0)
           (cons 91 0)
           (list 10 5.9 1.170155)
           (cons 40 0)
           (cons 41 0)
           (cons 42 0)
           (cons 91 0)
           (list 10 5.9889 1.2)
           (cons 40 0)
           (cons 41 0)
           (cons 42 0)
           (cons 91 0)
           (list 10 6.4461 1.2)
           (cons 40 0)
           (cons 41 0)
           (cons 42 0)
           (cons 91 0)
           (list 10 6.535 1.170155)
           (cons 40 0)
           (cons 41 0)
           (cons 42 0)
           (cons 91 0)
           (list 10 6.535 1.071095)
           (cons 40 0)
           (cons 41 0)
           (cons 42 0)
           (cons 91 0)
           (list 10 6.4461 1.04125)
           (cons 40 0)
           (cons 41 0)
           (cons 42 0)
           (cons 91 0)
           (list 10 5.9889 1.04125)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 0.9 1.2 0)
           (cons 50 0)
          )
         )
         (entmake
          (list
           (cons 0 "POINT")
           (cons 100 "AcDbEntity")
           (cons 67 0)
           (cons 8 "0")
           (cons 100 "AcDbPoint")
           (list 10 0.9 -1.2 0)
           (cons 50 0)
          )
         )
         (entmake
          (list
           (cons 0 "POINT")
           (cons 100 "AcDbEntity")
           (cons 67 0)
           (cons 8 "0")
           (cons 100 "AcDbPoint")
           (list 10 9.1 -1.2 0)
           (cons 50 0)
          )
         )
         (entmake
          (list
           (cons 0 "POINT")
           (cons 100 "AcDbEntity")
           (cons 67 0)
           (cons 8 "0")
           (cons 100 "AcDbPoint")
           (list 10 9.1 1.2 0)
           (cons 50 0)
          )
         )
         (entmake
          (list
           (cons 0 "POINT")
           (cons 100 "AcDbEntity")
           (cons 67 0)
           (cons 8 "0")
           (cons 100 "AcDbPoint")
           (list 10 5.6 1.2 0)
           (cons 50 0)
          )
         )
         (entmake
          (list
           (cons 0 "POINT")
           (cons 100 "AcDbEntity")
           (cons 67 0)
           (cons 8 "0")
           (cons 100 "AcDbPoint")
           (list 10 5.6 -1.2 0)
           (cons 50 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "5.600")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-P"))
        (progn
         (entmake)
         (entmake
          (list
           (cons 0 "BLOCK")
           (cons 2 "AB_INF-P")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.05)
           (cons 40 0)
           (cons 41 0)
           (cons 42 0)
           (cons 91 0)
           (list 10 5.8 -1.05)
           (cons 40 0)
           (cons 41 0)
           (cons 42 0)
           (cons 91 0)
           (list 10 5.8 1.05)
           (cons 40 0)
           (cons 41 0)
           (cons 42 0)
           (cons 91 0)
           (list 10 0 1.05)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.05 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.8 -1.05 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.8 1.05 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.05 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.05 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.05 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.9571 -1.0177674)
           (cons 40 0)
           (cons 41 0)
           (cons 42 0)
           (cons 91 0)
           (list 10 3.9571 -0.9107826)
           (cons 40 0)
           (cons 41 0)
           (cons 42 0)
           (cons 91 0)
           (list 10 4.053112 -0.87855)
           (cons 40 0)
           (cons 41 0)
           (cons 42 0)
           (cons 91 0)
           (list 10 4.546888 -0.87855)
           (cons 40 0)
           (cons 41 0)
           (cons 42 0)
           (cons 91 0)
           (list 10 4.6429 -0.9107826)
           (cons 40 0)
           (cons 41 0)
           (cons 42 0)
           (cons 91 0)
           (list 10 4.6429 -1.0177674)
           (cons 40 0)
           (cons 41 0)
           (cons 42 0)
           (cons 91 0)
           (list 10 4.546888 -1.05)
           (cons 40 0)
           (cons 41 0)
           (cons 42 0)
           (cons 91 0)
           (list 10 4.053112 -1.05)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.9571 0.9107826)
           (cons 40 0)
           (cons 41 0)
           (cons 42 0)
           (cons 91 0)
           (list 10 3.9571 1.0177674)
           (cons 40 0)
           (cons 41 0)
           (cons 42 0)
           (cons 91 0)
           (list 10 4.053112 1.05)
           (cons 40 0)
           (cons 41 0)
           (cons 42 0)
           (cons 91 0)
           (list 10 4.546888 1.05)
           (cons 40 0)
           (cons 41 0)
           (cons 42 0)
           (cons 91 0)
           (list 10 4.6429 1.0177674)
           (cons 40 0)
           (cons 41 0)
           (cons 42 0)
           (cons 91 0)
           (list 10 4.6429 0.9107826)
           (cons 40 0)
           (cons 41 0)
           (cons 42 0)
           (cons 91 0)
           (list 10 4.546888 0.87855)
           (cons 40 0)
           (cons 41 0)
           (cons 42 0)
           (cons 91 0)
           (list 10 4.053112 0.87855)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelRightM3")
           (list 10 0.9 0.87855 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM3")
           (list 10 0.9 -0.87855 0)
           (cons 41 1)
           (cons 42 1)
           (cons 43 1)
           (cons 50 0)
           (cons 70 0)
           (cons 71 0)
           (cons 44 0)
           (cons 45 0)
          )
         )
         (entmake
          (list
           (cons 0 "POINT")
           (cons 100 "AcDbEntity")
           (cons 67 0)
           (cons 8 "0")
           (cons 100 "AcDbPoint")
           (list 10 0 -1.05 0)
           (cons 50 0)
          )
         )
         (entmake
          (list
           (cons 0 "POINT")
           (cons 100 "AcDbEntity")
           (cons 67 0)
           (cons 8 "0")
           (cons 100 "AcDbPoint")
           (list 10 5.8 -1.05 0)
           (cons 50 0)
          )
         )
         (entmake
          (list
           (cons 0 "POINT")
           (cons 100 "AcDbEntity")
           (cons 67 0)
           (cons 8 "0")
           (cons 100 "AcDbPoint")
           (list 10 5.8 1.05 0)
           (cons 50 0)
          )
         )
         (entmake
          (list
           (cons 0 "POINT")
           (cons 100 "AcDbEntity")
           (cons 67 0)
           (cons 8 "0")
           (cons 100 "AcDbPoint")
           (list 10 0 1.05 0)
           (cons 50 0)
          )
         )
         (entmake
          (list
           (cons 0 "POINT")
           (cons 100 "AcDbEntity")
           (cons 67 0)
           (cons 8 "0")
           (cons 100 "AcDbPoint")
           (list 10 0.9 1.05 0)
           (cons 50 0)
          )
         )
         (entmake
          (list
           (cons 0 "POINT")
           (cons 100 "AcDbEntity")
           (cons 67 0)
           (cons 8 "0")
           (cons 100 "AcDbPoint")
           (list 10 4.3 1.05 0)
           (cons 50 0)
          )
         )
         (entmake
          (list
           (cons 0 "POINT")
           (cons 100 "AcDbEntity")
           (cons 67 0)
           (cons 8 "0")
           (cons 100 "AcDbPoint")
           (list 10 0.9 -1.05 0)
           (cons 50 0)
          )
         )
         (entmake
          (list
           (cons 0 "POINT")
           (cons 100 "AcDbEntity")
           (cons 67 0)
           (cons 8 "0")
           (cons 100 "AcDbPoint")
           (list 10 4.3 -1.05 0)
           (cons 50 0)
          )
         )
         (entmake
          (list
           (cons 0 "POINT")
           (cons 100 "AcDbEntity")
           (cons 67 0)
           (cons 8 "0")
           (cons 100 "AcDbPoint")
           (list 10 0.9 0 0)
           (cons 50 0)
          )
         )
         (entmake
          (list
           (cons 0 "ATTDEF")
           (cons 100 "AcDbEntity")
           (cons 67 0)
           (cons 8 "0")
           (cons 100 "AcDbText")
           (list 10 0.2 0.56666667 0)
           (cons 40 0.2)
           (cons 1 "0.900")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.2 0.23333333 0)
           (cons 40 0.2)
           (cons 1 "0.900")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.2 -0.1 0)
           (cons 40 0.2)
           (cons 1 "4.300")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.2 -0.43333333 0)
           (cons 40 0.2)
           (cons 1 "5.800")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.2 -0.76666667 0)
           (cons 40 0.2)
           (cons 1 "32.1")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "POINT")
           (cons 100 "AcDbEntity")
           (cons 67 0)
           (cons 8 "0")
           (cons 100 "AcDbPoint")
           (list 10 5.8 0 0)
           (cons 50 0)
          )
         )
         (entmake (list (cons 0 "ENDBLK")))
        )
       )
       ((= (strcase BLKNAME) (strcase "AB_INF-P"))
        (progn
         (entmake)
         (entmake
          (list
           (cons 0 "BLOCK")
           (cons 2 "AB_INF-P")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.05)
           (cons 40 0)
           (cons 41 0)
           (cons 42 0)
           (cons 91 0)
           (list 10 5.8 -1.05)
           (cons 40 0)
           (cons 41 0)
           (cons 42 0)
           (cons 91 0)
           (list 10 5.8 1.05)
           (cons 40 0)
           (cons 41 0)
           (cons 42 0)
           (cons 91 0)
           (list 10 0 1.05)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.05 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.8 -1.05 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.8 1.05 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.05 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.05 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.05 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.9571 -1.0177674)
           (cons 40 0)
           (cons 41 0)
           (cons 42 0)
           (cons 91 0)
           (list 10 3.9571 -0.9107826)
           (cons 40 0)
           (cons 41 0)
           (cons 42 0)
           (cons 91 0)
           (list 10 4.053112 -0.87855)
           (cons 40 0)
           (cons 41 0)
           (cons 42 0)
           (cons 91 0)
           (list 10 4.546888 -0.87855)
           (cons 40 0)
           (cons 41 0)
           (cons 42 0)
           (cons 91 0)
           (list 10 4.6429 -0.9107826)
           (cons 40 0)
           (cons 41 0)
           (cons 42 0)
           (cons 91 0)
           (list 10 4.6429 -1.0177674)
           (cons 40 0)
           (cons 41 0)
           (cons 42 0)
           (cons 91 0)
           (list 10 4.546888 -1.05)
           (cons 40 0)
           (cons 41 0)
           (cons 42 0)
           (cons 91 0)
           (list 10 4.053112 -1.05)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.9571 0.9107826)
           (cons 40 0)
           (cons 41 0)
           (cons 42 0)
           (cons 91 0)
           (list 10 3.9571 1.0177674)
           (cons 40 0)
           (cons 41 0)
           (cons 42 0)
           (cons 91 0)
           (list 10 4.053112 1.05)
           (cons 40 0)
           (cons 41 0)
           (cons 42 0)
           (cons 91 0)
           (list 10 4.546888 1.05)
           (cons 40 0)
           (cons 41 0)
           (cons 42 0)
           (cons 91 0)
           (list 10 4.6429 1.0177674)
           (cons 40 0)
           (cons 41 0)
           (cons 42 0)
           (cons 91 0)
           (list 10 4.6429 0.9107826)
           (cons 40 0)
           (cons 41 0)
           (cons 42 0)
           (cons 91 0)
           (list 10 4.546888 0.87855)
           (cons 40 0)
           (cons 41 0)
           (cons 42 0)
           (cons 91 0)
           (list 10 4.053112 0.87855)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelRightM3")
           (list 10 0.9 0.87855 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM3")
           (list 10 0.9 -0.87855 0)
           (cons 41 1)
           (cons 42 1)
           (cons 43 1)
           (cons 50 0)
           (cons 70 0)
           (cons 71 0)
           (cons 44 0)
           (cons 45 0)
          )
         )
         (entmake
          (list
           (cons 0 "POINT")
           (cons 100 "AcDbEntity")
           (cons 67 0)
           (cons 8 "0")
           (cons 100 "AcDbPoint")
           (list 10 0 -1.05 0)
           (cons 50 0)
          )
         )
         (entmake
          (list
           (cons 0 "POINT")
           (cons 100 "AcDbEntity")
           (cons 67 0)
           (cons 8 "0")
           (cons 100 "AcDbPoint")
           (list 10 5.8 -1.05 0)
           (cons 50 0)
          )
         )
         (entmake
          (list
           (cons 0 "POINT")
           (cons 100 "AcDbEntity")
           (cons 67 0)
           (cons 8 "0")
           (cons 100 "AcDbPoint")
           (list 10 5.8 1.05 0)
           (cons 50 0)
          )
         )
         (entmake
          (list
           (cons 0 "POINT")
           (cons 100 "AcDbEntity")
           (cons 67 0)
           (cons 8 "0")
           (cons 100 "AcDbPoint")
           (list 10 0 1.05 0)
           (cons 50 0)
          )
         )
         (entmake
          (list
           (cons 0 "POINT")
           (cons 100 "AcDbEntity")
           (cons 67 0)
           (cons 8 "0")
           (cons 100 "AcDbPoint")
           (list 10 0.9 1.05 0)
           (cons 50 0)
          )
         )
         (entmake
          (list
           (cons 0 "POINT")
           (cons 100 "AcDbEntity")
           (cons 67 0)
           (cons 8 "0")
           (cons 100 "AcDbPoint")
           (list 10 4.3 1.05 0)
           (cons 50 0)
          )
         )
         (entmake
          (list
           (cons 0 "POINT")
           (cons 100 "AcDbEntity")
           (cons 67 0)
           (cons 8 "0")
           (cons 100 "AcDbPoint")
           (list 10 0.9 -1.05 0)
           (cons 50 0)
          )
         )
         (entmake
          (list
           (cons 0 "POINT")
           (cons 100 "AcDbEntity")
           (cons 67 0)
           (cons 8 "0")
           (cons 100 "AcDbPoint")
           (list 10 4.3 -1.05 0)
           (cons 50 0)
          )
         )
         (entmake
          (list
           (cons 0 "POINT")
           (cons 100 "AcDbEntity")
           (cons 67 0)
           (cons 8 "0")
           (cons 100 "AcDbPoint")
           (list 10 0.9 0 0)
           (cons 50 0)
          )
         )
         (entmake
          (list
           (cons 0 "ATTDEF")
           (cons 100 "AcDbEntity")
           (cons 67 0)
           (cons 8 "0")
           (cons 100 "AcDbText")
           (list 10 0.2 0.56666667 0)
           (cons 40 0.2)
           (cons 1 "0.900")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.2 0.23333333 0)
           (cons 40 0.2)
           (cons 1 "0.900")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.2 -0.1 0)
           (cons 40 0.2)
           (cons 1 "4.300")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.2 -0.43333333 0)
           (cons 40 0.2)
           (cons 1 "5.800")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.2 -0.76666667 0)
           (cons 40 0.2)
           (cons 1 "32.1")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "POINT")
           (cons 100 "AcDbEntity")
           (cons 67 0)
           (cons 8 "0")
           (cons 100 "AcDbPoint")
           (list 10 5.8 0 0)
           (cons 50 0)
          )
         )
         (entmake (list (cons 0 "ENDBLK")))
        )
       )
       ((= (strcase BLKNAME) (strcase "AB_INF-LogHaul-Load"))
        (progn
         (entmake)
         (entmake
          (list
           (cons 0 "BLOCK")
           (cons 2 "AB_INF-LogHaul-Load")
           (cons 70 2)
           (cons 4 "")
           (list 10 0 0 0)
          )
         )
         (entmake
          (list
           (cons 0 "ATTDEF")
           (cons 100 "AcDbEntity")
           (cons 67 0)
           (cons 8 "0")
           (cons 100 "AcDbText")
           (list 10 2.4 -0.1 0)
           (cons 40 0.2)
           (cons 1 "13.650")
           (cons 50 0)
           (cons 41 1)
           (cons 51 0)
           (cons 7 "Standard")
           (cons 71 0)
           (cons 72 0)
           (list 11 0 0 0)
           (cons 100 "AcDbAttributeDefinition")
           (cons 3 "Load Base Point (LB)")
           (cons 2 "LB")
           (cons 70 9)
           (cons 73 0)
           (cons 74 0)
          )
         )
         (entmake
          (list
           (cons 0 "ATTDEF")
           (cons 100 "AcDbEntity")
           (cons 67 0)
           (cons 8 "0")
           (cons 100 "AcDbText")
           (list 10 2.4 -0.43333333 0)
           (cons 40 0.2)
           (cons 1 "3.100")
           (cons 50 0)
           (cons 41 1)
           (cons 51 0)
           (cons 7 "Standard")
           (cons 71 0)
           (cons 72 0)
           (list 11 0 0 0)
           (cons 100 "AcDbAttributeDefinition")
           (cons 3 "Load Angle Point (LA)")
           (cons 2 "LA")
           (cons 70 9)
           (cons 73 0)
           (cons 74 0)
          )
         )
         (entmake
          (list
           (cons 0 "POINT")
           (cons 100 "AcDbEntity")
           (cons 67 0)
           (cons 8 "0")
           (cons 100 "AcDbPoint")
           (list 10 23.35 1.6 0)
           (cons 50 0)
          )
         )
         (entmake
          (list
           (cons 0 "POINT")
           (cons 100 "AcDbEntity")
           (cons 67 0)
           (cons 8 "0")
           (cons 100 "AcDbPoint")
           (list 10 23.35 -1.6 0)
           (cons 50 0)
          )
         )
         (entmake
          (list
           (cons 0 "POINT")
           (cons 100 "AcDbEntity")
           (cons 67 0)
           (cons 8 "0")
           (cons 100 "AcDbPoint")
           (list 10 0 -1.6 0)
           (cons 50 0)
          )
         )
         (entmake
          (list
           (cons 0 "POINT")
           (cons 100 "AcDbEntity")
           (cons 67 0)
           (cons 8 "0")
           (cons 100 "AcDbPoint")
           (list 10 0 1.6 0)
           (cons 50 0)
          )
         )
         (entmake
          (list
           (cons 0 "POINT")
           (cons 100 "AcDbEntity")
           (cons 67 0)
           (cons 8 "0")
           (cons 62 3)
           (cons 100 "AcDbPoint")
           (list 10 13.65 0 0)
           (cons 50 0)
          )
         )
         (entmake
          (list
           (cons 0 "POINT")
           (cons 100 "AcDbEntity")
           (cons 67 0)
           (cons 8 "0")
           (cons 62 3)
           (cons 100 "AcDbPoint")
           (list 10 3.1 0 0)
           (cons 50 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 3.1 0 0)
           (cons 40 0.1524)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.6 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 23.35 -1.6 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 23.35 1.6 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.6 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.6 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 13.65 0 0)
           (cons 40 0.1524)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.6)
           (cons 40 0)
           (cons 41 0)
           (cons 42 0)
           (cons 91 0)
           (list 10 23.35 -1.6)
           (cons 40 0)
           (cons 41 0)
           (cons 42 0)
           (cons 91 0)
           (list 10 23.35 1.6)
           (cons 40 0)
           (cons 41 0)
           (cons 42 0)
           (cons 91 0)
           (list 10 0 1.6)
           (cons 40 0)
           (cons 41 0)
           (cons 42 0)
           (cons 91 0)
          )
         )
         (entmake
          (list
           (cons 0 "TEXT")
           (cons 100 "AcDbEntity")
           (cons 67 0)
           (cons 8 "0")
           (cons 100 "AcDbText")
           (list 10 3.92142857 -0.25 0)
           (cons 40 0.5)
           (cons 1 "4")
           (cons 50 0)
           (cons 41 1)
           (cons 51 0)
           (cons 7 "Standard")
           (cons 71 0)
           (cons 72 4)
           (list 11 4.1 0 0)
           (cons 100 "AcDbText")
           (cons 73 0)
          )
         )
         (entmake (list (cons 0 "ENDBLK")))
        )
       )
       ((= (strcase BLKNAME) (strcase "AB_INF-LogHaul-Trailer2"))
        (progn
         (entmake)
         (entmake
          (list
           (cons 0 "BLOCK")
           (cons 2 "AB_INF-LogHaul-Trailer2")
           (cons 70 2)
           (cons 4 "")
           (list 10 0 0 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "4.850")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -1.1 0)
           (cons 40 0.2)
           (cons 1 "4.850")
           (cons 50 0)
           (cons 41 1)
           (cons 51 0)
           (cons 7 "Standard")
           (cons 71 0)
           (cons 72 0)
           (list 11 0 0 0)
           (cons 100 "AcDbAttributeDefinition")
           (cons 3 "Load Base Point (LB)")
           (cons 2 "LB")
           (cons 70 9)
           (cons 73 0)
           (cons 74 0)
          )
         )
         (entmake
          (list
           (cons 0 "POINT")
           (cons 100 "AcDbEntity")
           (cons 67 0)
           (cons 8 "0")
           (cons 100 "AcDbPoint")
           (list 10 4.85 -1.3 0)
           (cons 50 0)
          )
         )
         (entmake
          (list
           (cons 0 "POINT")
           (cons 100 "AcDbEntity")
           (cons 67 0)
           (cons 8 "0")
           (cons 100 "AcDbPoint")
           (list 10 4.85 1.3 0)
           (cons 50 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 4.85 0 0)
           (cons 40 0.1524)
          )
         )
         (entmake
          (list
           (cons 0 "POINT")
           (cons 100 "AcDbEntity")
           (cons 67 0)
           (cons 8 "0")
           (cons 62 1)
           (cons 6 "Continuous")
           (cons 48 1.524)
           (cons 100 "AcDbPoint")
           (list 10 4.85 0 0)
           (cons 50 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.991 0.570452)
           (cons 40 0)
           (cons 41 0)
           (cons 42 0)
           (cons 91 0)
           (list 10 4.991 0.744548)
           (cons 40 0)
           (cons 41 0)
           (cons 42 0)
           (cons 91 0)
           (list 10 5.14752 0.797)
           (cons 40 0)
           (cons 41 0)
           (cons 42 0)
           (cons 91 0)
           (list 10 5.95248 0.797)
           (cons 40 0)
           (cons 41 0)
           (cons 42 0)
           (cons 91 0)
           (list 10 6.109 0.744548)
           (cons 40 0)
           (cons 41 0)
           (cons 42 0)
           (cons 91 0)
           (list 10 6.109 0.570452)
           (cons 40 0)
           (cons 41 0)
           (cons 42 0)
           (cons 91 0)
           (list 10 5.95248 0.518)
           (cons 40 0)
           (cons 41 0)
           (cons 42 0)
           (cons 91 0)
           (list 10 5.14752 0.518)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.591 -0.744548)
           (cons 40 0)
           (cons 41 0)
           (cons 42 0)
           (cons 91 0)
           (list 10 3.591 -0.570452)
           (cons 40 0)
           (cons 41 0)
           (cons 42 0)
           (cons 91 0)
           (list 10 3.74752 -0.518)
           (cons 40 0)
           (cons 41 0)
           (cons 42 0)
           (cons 91 0)
           (list 10 4.55248 -0.518)
           (cons 40 0)
           (cons 41 0)
           (cons 42 0)
           (cons 91 0)
           (list 10 4.709 -0.570452)
           (cons 40 0)
           (cons 41 0)
           (cons 42 0)
           (cons 91 0)
           (list 10 4.709 -0.744548)
           (cons 40 0)
           (cons 41 0)
           (cons 42 0)
           (cons 91 0)
           (list 10 4.55248 -0.797)
           (cons 40 0)
           (cons 41 0)
           (cons 42 0)
           (cons 91 0)
           (list 10 3.74752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.591 -1.247548)
           (cons 40 0)
           (cons 41 0)
           (cons 42 0)
           (cons 91 0)
           (list 10 3.591 -1.073452)
           (cons 40 0)
           (cons 41 0)
           (cons 42 0)
           (cons 91 0)
           (list 10 3.74752 -1.021)
           (cons 40 0)
           (cons 41 0)
           (cons 42 0)
           (cons 91 0)
           (list 10 4.55248 -1.021)
           (cons 40 0)
           (cons 41 0)
           (cons 42 0)
           (cons 91 0)
           (list 10 4.709 -1.073452)
           (cons 40 0)
           (cons 41 0)
           (cons 42 0)
           (cons 91 0)
           (list 10 4.709 -1.247548)
           (cons 40 0)
           (cons 41 0)
           (cons 42 0)
           (cons 91 0)
           (list 10 4.55248 -1.3)
           (cons 40 0)
           (cons 41 0)
           (cons 42 0)
           (cons 91 0)
           (list 10 3.74752 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.991 -0.744548)
           (cons 40 0)
           (cons 41 0)
           (cons 42 0)
           (cons 91 0)
           (list 10 4.991 -0.570452)
           (cons 40 0)
           (cons 41 0)
           (cons 42 0)
           (cons 91 0)
           (list 10 5.14752 -0.518)
           (cons 40 0)
           (cons 41 0)
           (cons 42 0)
           (cons 91 0)
           (list 10 5.95248 -0.518)
           (cons 40 0)
           (cons 41 0)
           (cons 42 0)
           (cons 91 0)
           (list 10 6.109 -0.570452)
           (cons 40 0)
           (cons 41 0)
           (cons 42 0)
           (cons 91 0)
           (list 10 6.109 -0.744548)
           (cons 40 0)
           (cons 41 0)
           (cons 42 0)
           (cons 91 0)
           (list 10 5.95248 -0.797)
           (cons 40 0)
           (cons 41 0)
           (cons 42 0)
           (cons 91 0)
           (list 10 5.14752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.991 -1.247548)
           (cons 40 0)
           (cons 41 0)
           (cons 42 0)
           (cons 91 0)
           (list 10 4.991 -1.073452)
           (cons 40 0)
           (cons 41 0)
           (cons 42 0)
           (cons 91 0)
           (list 10 5.14752 -1.021)
           (cons 40 0)
           (cons 41 0)
           (cons 42 0)
           (cons 91 0)
           (list 10 5.95248 -1.021)
           (cons 40 0)
           (cons 41 0)
           (cons 42 0)
           (cons 91 0)
           (list 10 6.109 -1.073452)
           (cons 40 0)
           (cons 41 0)
           (cons 42 0)
           (cons 91 0)
           (list 10 6.109 -1.247548)
           (cons 40 0)
           (cons 41 0)
           (cons 42 0)
           (cons 91 0)
           (list 10 5.95248 -1.3)
           (cons 40 0)
           (cons 41 0)
           (cons 42 0)
           (cons 91 0)
           (list 10 5.14752 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.991 1.073452)
           (cons 40 0)
           (cons 41 0)
           (cons 42 0)
           (cons 91 0)
           (list 10 4.991 1.247548)
           (cons 40 0)
           (cons 41 0)
           (cons 42 0)
           (cons 91 0)
           (list 10 5.14752 1.3)
           (cons 40 0)
           (cons 41 0)
           (cons 42 0)
           (cons 91 0)
           (list 10 5.95248 1.3)
           (cons 40 0)
           (cons 41 0)
           (cons 42 0)
           (cons 91 0)
           (list 10 6.109 1.247548)
           (cons 40 0)
           (cons 41 0)
           (cons 42 0)
           (cons 91 0)
           (list 10 6.109 1.073452)
           (cons 40 0)
           (cons 41 0)
           (cons 42 0)
           (cons 91 0)
           (list 10 5.95248 1.021)
           (cons 40 0)
           (cons 41 0)
           (cons 42 0)
           (cons 91 0)
           (list 10 5.14752 1.021)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.591 1.073452)
           (cons 40 0)
           (cons 41 0)
           (cons 42 0)
           (cons 91 0)
           (list 10 3.591 1.247548)
           (cons 40 0)
           (cons 41 0)
           (cons 42 0)
           (cons 91 0)
           (list 10 3.74752 1.3)
           (cons 40 0)
           (cons 41 0)
           (cons 42 0)
           (cons 91 0)
           (list 10 4.55248 1.3)
           (cons 40 0)
           (cons 41 0)
           (cons 42 0)
           (cons 91 0)
           (list 10 4.709 1.247548)
           (cons 40 0)
           (cons 41 0)
           (cons 42 0)
           (cons 91 0)
           (list 10 4.709 1.073452)
           (cons 40 0)
           (cons 41 0)
           (cons 42 0)
           (cons 91 0)
           (list 10 4.55248 1.021)
           (cons 40 0)
           (cons 41 0)
           (cons 42 0)
           (cons 91 0)
           (list 10 3.74752 1.021)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.591 0.570452)
           (cons 40 0)
           (cons 41 0)
           (cons 42 0)
           (cons 91 0)
           (list 10 3.591 0.744548)
           (cons 40 0)
           (cons 41 0)
           (cons 42 0)
           (cons 91 0)
           (list 10 3.74752 0.797)
           (cons 40 0)
           (cons 41 0)
           (cons 42 0)
           (cons 91 0)
           (list 10 4.55248 0.797)
           (cons 40 0)
           (cons 41 0)
           (cons 42 0)
           (cons 91 0)
           (list 10 4.709 0.744548)
           (cons 40 0)
           (cons 41 0)
           (cons 42 0)
           (cons 91 0)
           (list 10 4.709 0.570452)
           (cons 40 0)
           (cons 41 0)
           (cons 42 0)
           (cons 91 0)
           (list 10 4.55248 0.518)
           (cons 40 0)
           (cons 41 0)
           (cons 42 0)
           (cons 91 0)
           (list 10 3.74752 0.518)
           (cons 40 0)
           (cons 41 0)
           (cons 42 0)
           (cons 91 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.1016)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.55 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.55 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "POLYLINE")
           (cons 100 "AcDbEntity")
           (cons 67 0)
           (cons 8 "Defpoints")
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "Defpoints")
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 3.591 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 3.591 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.109 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.109 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.55 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.55 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.109 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.109 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 3.591 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 3.591 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 0 0.5 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "Defpoints")
          )
         )
         (entmake
          (list
           (cons 0 "TEXT")
           (cons 100 "AcDbEntity")
           (cons 67 0)
           (cons 8 "0")
           (cons 100 "AcDbText")
           (list 10 0.83333333 -0.25 0)
           (cons 40 0.5)
           (cons 1 "3")
           (cons 50 0)
           (cons 41 1)
           (cons 51 0)
           (cons 7 "Standard")
           (cons 71 0)
           (cons 72 4)
           (list 11 1 0 0)
           (cons 100 "AcDbText")
           (cons 73 0)
          )
         )
         (entmake (list (cons 0 "ENDBLK")))
        )
       )
       ((= (strcase BLKNAME) (strcase "AB_INF-LogHaul-Trailer1"))
        (progn
         (entmake)
         (entmake
          (list
           (cons 0 "BLOCK")
           (cons 2 "AB_INF-LogHaul-Trailer1")
           (cons 70 2)
           (cons 4 "")
           (list 10 0 0 0)
          )
         )
         (entmake
          (list
           (cons 0 "ATTDEF")
           (cons 100 "AcDbEntity")
           (cons 67 0)
           (cons 8 "0")
           (cons 100 "AcDbText")
           (list 10 -0.3 0.56666667 0)
           (cons 40 0.2)
           (cons 1 "0.400")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 0.23333333 0)
           (cons 40 0.2)
           (cons 1 "0.400")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.1 0)
           (cons 40 0.2)
           (cons 1 "7.300")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.43333333 0)
           (cons 40 0.2)
           (cons 1 "9.200")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -1.1 0)
           (cons 40 0.2)
           (cons 1 "3.500")
           (cons 50 0)
           (cons 41 1)
           (cons 51 0)
           (cons 7 "Standard")
           (cons 71 0)
           (cons 72 0)
           (list 11 0 0 0)
           (cons 100 "AcDbAttributeDefinition")
           (cons 3 "Load Angle Point (LA)")
           (cons 2 "LA")
           (cons 70 9)
           (cons 73 0)
           (cons 74 0)
          )
         )
         (entmake
          (list
           (cons 0 "POINT")
           (cons 100 "AcDbEntity")
           (cons 67 0)
           (cons 8 "0")
           (cons 62 1)
           (cons 100 "AcDbPoint")
           (list 10 3.5 0 0)
           (cons 50 0)
          )
         )
         (entmake
          (list
           (cons 0 "POINT")
           (cons 100 "AcDbEntity")
           (cons 67 0)
           (cons 8 "0")
           (cons 100 "AcDbPoint")
           (list 10 7.3 -1.3 0)
           (cons 50 0)
          )
         )
         (entmake
          (list
           (cons 0 "POINT")
           (cons 100 "AcDbEntity")
           (cons 67 0)
           (cons 8 "0")
           (cons 100 "AcDbPoint")
           (list 10 7.3 1.3 0)
           (cons 50 0)
          )
         )
         (entmake
          (list
           (cons 0 "POINT")
           (cons 100 "AcDbEntity")
           (cons 67 0)
           (cons 8 "0")
           (cons 100 "AcDbPoint")
           (list 10 0.4 0 0)
           (cons 50 0)
          )
         )
         (entmake
          (list
           (cons 0 "POINT")
           (cons 100 "AcDbEntity")
           (cons 67 0)
           (cons 8 "0")
           (cons 100 "AcDbPoint")
           (list 10 9.2 0 0)
           (cons 50 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 3.5 0 0)
           (cons 40 0.1524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 9.2 0 0)
           (cons 40 0.17333333)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.441 1.073452)
           (cons 40 0)
           (cons 41 0)
           (cons 42 0)
           (cons 91 0)
           (list 10 7.441 1.247548)
           (cons 40 0)
           (cons 41 0)
           (cons 42 0)
           (cons 91 0)
           (list 10 7.59752 1.3)
           (cons 40 0)
           (cons 41 0)
           (cons 42 0)
           (cons 91 0)
           (list 10 8.40248 1.3)
           (cons 40 0)
           (cons 41 0)
           (cons 42 0)
           (cons 91 0)
           (list 10 8.559 1.247548)
           (cons 40 0)
           (cons 41 0)
           (cons 42 0)
           (cons 91 0)
           (list 10 8.559 1.073452)
           (cons 40 0)
           (cons 41 0)
           (cons 42 0)
           (cons 91 0)
           (list 10 8.40248 1.021)
           (cons 40 0)
           (cons 41 0)
           (cons 42 0)
           (cons 91 0)
           (list 10 7.59752 1.021)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.441 0.570452)
           (cons 40 0)
           (cons 41 0)
           (cons 42 0)
           (cons 91 0)
           (list 10 7.441 0.744548)
           (cons 40 0)
           (cons 41 0)
           (cons 42 0)
           (cons 91 0)
           (list 10 7.59752 0.797)
           (cons 40 0)
           (cons 41 0)
           (cons 42 0)
           (cons 91 0)
           (list 10 8.40248 0.797)
           (cons 40 0)
           (cons 41 0)
           (cons 42 0)
           (cons 91 0)
           (list 10 8.559 0.744548)
           (cons 40 0)
           (cons 41 0)
           (cons 42 0)
           (cons 91 0)
           (list 10 8.559 0.570452)
           (cons 40 0)
           (cons 41 0)
           (cons 42 0)
           (cons 91 0)
           (list 10 8.40248 0.518)
           (cons 40 0)
           (cons 41 0)
           (cons 42 0)
           (cons 91 0)
           (list 10 7.59752 0.518)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.441 -0.744548)
           (cons 40 0)
           (cons 41 0)
           (cons 42 0)
           (cons 91 0)
           (list 10 7.441 -0.570452)
           (cons 40 0)
           (cons 41 0)
           (cons 42 0)
           (cons 91 0)
           (list 10 7.59752 -0.518)
           (cons 40 0)
           (cons 41 0)
           (cons 42 0)
           (cons 91 0)
           (list 10 8.40248 -0.518)
           (cons 40 0)
           (cons 41 0)
           (cons 42 0)
           (cons 91 0)
           (list 10 8.559 -0.570452)
           (cons 40 0)
           (cons 41 0)
           (cons 42 0)
           (cons 91 0)
           (list 10 8.559 -0.744548)
           (cons 40 0)
           (cons 41 0)
           (cons 42 0)
           (cons 91 0)
           (list 10 8.40248 -0.797)
           (cons 40 0)
           (cons 41 0)
           (cons 42 0)
           (cons 91 0)
           (list 10 7.59752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.441 -1.247548)
           (cons 40 0)
           (cons 41 0)
           (cons 42 0)
           (cons 91 0)
           (list 10 7.441 -1.073452)
           (cons 40 0)
           (cons 41 0)
           (cons 42 0)
           (cons 91 0)
           (list 10 7.59752 -1.021)
           (cons 40 0)
           (cons 41 0)
           (cons 42 0)
           (cons 91 0)
           (list 10 8.40248 -1.021)
           (cons 40 0)
           (cons 41 0)
           (cons 42 0)
           (cons 91 0)
           (list 10 8.559 -1.073452)
           (cons 40 0)
           (cons 41 0)
           (cons 42 0)
           (cons 91 0)
           (list 10 8.559 -1.247548)
           (cons 40 0)
           (cons 41 0)
           (cons 42 0)
           (cons 91 0)
           (list 10 8.40248 -1.3)
           (cons 40 0)
           (cons 41 0)
           (cons 42 0)
           (cons 91 0)
           (list 10 7.59752 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.041 -1.247548)
           (cons 40 0)
           (cons 41 0)
           (cons 42 0)
           (cons 91 0)
           (list 10 6.041 -1.073452)
           (cons 40 0)
           (cons 41 0)
           (cons 42 0)
           (cons 91 0)
           (list 10 6.19752 -1.021)
           (cons 40 0)
           (cons 41 0)
           (cons 42 0)
           (cons 91 0)
           (list 10 7.00248 -1.021)
           (cons 40 0)
           (cons 41 0)
           (cons 42 0)
           (cons 91 0)
           (list 10 7.159 -1.073452)
           (cons 40 0)
           (cons 41 0)
           (cons 42 0)
           (cons 91 0)
           (list 10 7.159 -1.247548)
           (cons 40 0)
           (cons 41 0)
           (cons 42 0)
           (cons 91 0)
           (list 10 7.00248 -1.3)
           (cons 40 0)
           (cons 41 0)
           (cons 42 0)
           (cons 91 0)
           (list 10 6.19752 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.041 -0.744548)
           (cons 40 0)
           (cons 41 0)
           (cons 42 0)
           (cons 91 0)
           (list 10 6.041 -0.570452)
           (cons 40 0)
           (cons 41 0)
           (cons 42 0)
           (cons 91 0)
           (list 10 6.19752 -0.518)
           (cons 40 0)
           (cons 41 0)
           (cons 42 0)
           (cons 91 0)
           (list 10 7.00248 -0.518)
           (cons 40 0)
           (cons 41 0)
           (cons 42 0)
           (cons 91 0)
           (list 10 7.159 -0.570452)
           (cons 40 0)
           (cons 41 0)
           (cons 42 0)
           (cons 91 0)
           (list 10 7.159 -0.744548)
           (cons 40 0)
           (cons 41 0)
           (cons 42 0)
           (cons 91 0)
           (list 10 7.00248 -0.797)
           (cons 40 0)
           (cons 41 0)
           (cons 42 0)
           (cons 91 0)
           (list 10 6.19752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.041 1.073452)
           (cons 40 0)
           (cons 41 0)
           (cons 42 0)
           (cons 91 0)
           (list 10 6.041 1.247548)
           (cons 40 0)
           (cons 41 0)
           (cons 42 0)
           (cons 91 0)
           (list 10 6.19752 1.3)
           (cons 40 0)
           (cons 41 0)
           (cons 42 0)
           (cons 91 0)
           (list 10 7.00248 1.3)
           (cons 40 0)
           (cons 41 0)
           (cons 42 0)
           (cons 91 0)
           (list 10 7.159 1.247548)
           (cons 40 0)
           (cons 41 0)
           (cons 42 0)
           (cons 91 0)
           (list 10 7.159 1.073452)
           (cons 40 0)
           (cons 41 0)
           (cons 42 0)
           (cons 91 0)
           (list 10 7.00248 1.021)
           (cons 40 0)
           (cons 41 0)
           (cons 42 0)
           (cons 91 0)
           (list 10 6.19752 1.021)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.041 0.570452)
           (cons 40 0)
           (cons 41 0)
           (cons 42 0)
           (cons 91 0)
           (list 10 6.041 0.744548)
           (cons 40 0)
           (cons 41 0)
           (cons 42 0)
           (cons 91 0)
           (list 10 6.19752 0.797)
           (cons 40 0)
           (cons 41 0)
           (cons 42 0)
           (cons 91 0)
           (list 10 7.00248 0.797)
           (cons 40 0)
           (cons 41 0)
           (cons 42 0)
           (cons 91 0)
           (list 10 7.159 0.744548)
           (cons 40 0)
           (cons 41 0)
           (cons 42 0)
           (cons 91 0)
           (list 10 7.159 0.570452)
           (cons 40 0)
           (cons 41 0)
           (cons 42 0)
           (cons 91 0)
           (list 10 7.00248 0.518)
           (cons 40 0)
           (cons 41 0)
           (cons 42 0)
           (cons 91 0)
           (list 10 6.19752 0.518)
           (cons 40 0)
           (cons 41 0)
           (cons 42 0)
           (cons 91 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0.4 0 0)
           (cons 40 0.104)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.2 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.2 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "POLYLINE")
           (cons 100 "AcDbEntity")
           (cons 67 0)
           (cons 8 "Defpoints")
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "Defpoints")
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.041 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.041 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 8.559 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 8.559 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 9.2 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 9.2 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 8.559 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 8.559 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.041 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.041 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 0 0.5 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "Defpoints")
          )
         )
         (entmake
          (list
           (cons 0 "TEXT")
           (cons 100 "AcDbEntity")
           (cons 67 0)
           (cons 8 "0")
           (cons 100 "AcDbText")
           (list 10 1.23333333 -0.25 0)
           (cons 40 0.5)
           (cons 1 "2")
           (cons 50 0)
           (cons 41 1)
           (cons 51 0)
           (cons 7 "Standard")
           (cons 71 0)
           (cons 72 4)
           (list 11 1.4 0 0)
           (cons 100 "AcDbText")
           (cons 73 0)
          )
         )
         (entmake (list (cons 0 "ENDBLK")))
        )
       )
       ((= (strcase BLKNAME) (strcase "AB_INF-LogHaul-Truck"))
        (progn
         (entmake)
         (entmake
          (list
           (cons 0 "BLOCK")
           (cons 2 "AB_INF-LogHaul-Truck")
           (cons 70 2)
           (cons 4 "")
           (list 10 0 0 0)
          )
         )
         (entmake
          (list
           (cons 0 "ATTDEF")
           (cons 100 "AcDbEntity")
           (cons 67 0)
           (cons 8 "0")
           (cons 100 "AcDbText")
           (list 10 0.3 0.56666667 0)
           (cons 40 0.2)
           (cons 1 "1.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 0.23333333 0)
           (cons 40 0.2)
           (cons 1 "1.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.1 0)
           (cons 40 0.2)
           (cons 1 "7.150")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.43333333 0)
           (cons 40 0.2)
           (cons 1 "7.150")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.76666667 0)
           (cons 40 0.2)
           (cons 1 "26.4")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 7.15 -1.3 0)
           (cons 50 0)
          )
         )
         (entmake
          (list
           (cons 0 "POINT")
           (cons 100 "AcDbEntity")
           (cons 67 0)
           (cons 8 "0")
           (cons 100 "AcDbPoint")
           (list 10 7.15 1.3 0)
           (cons 50 0)
          )
         )
         (entmake
          (list
           (cons 0 "POINT")
           (cons 100 "AcDbEntity")
           (cons 67 0)
           (cons 8 "0")
           (cons 100 "AcDbPoint")
           (list 10 1 -1.3 0)
           (cons 50 0)
          )
         )
         (entmake
          (list
           (cons 0 "POINT")
           (cons 100 "AcDbEntity")
           (cons 67 0)
           (cons 8 "0")
           (cons 100 "AcDbPoint")
           (list 10 1 1.3 0)
           (cons 50 0)
          )
         )
         (entmake
          (list
           (cons 0 "POINT")
           (cons 100 "AcDbEntity")
           (cons 67 0)
           (cons 8 "0")
           (cons 100 "AcDbPoint")
           (list 10 1 0 0)
           (cons 50 0)
          )
         )
         (entmake
          (list
           (cons 0 "INSERT")
           (cons 100 "AcDbEntity")
           (cons 67 0)
           (cons 8 "0")
           (cons 100 "AcDbBlockReference")
           (cons 2 "WheelLeftM1")
           (list 10 1 -1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM1")
           (list 10 1 1.0206 0)
           (cons 41 1)
           (cons 42 1)
           (cons 43 1)
           (cons 50 0)
           (cons 70 0)
           (cons 71 0)
           (cons 44 0)
           (cons 45 0)
          )
         )
         (entmake
          (list
           (cons 0 "POINT")
           (cons 100 "AcDbEntity")
           (cons 67 0)
           (cons 8 "0")
           (cons 100 "AcDbPoint")
           (list 10 7.15 0 0)
           (cons 50 0)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 7.41263966 -0.26263966 0)
           (list 11 7.41263966 0.26263966 0)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 7.15 0 0)
           (cons 40 0.37142857)
           (cons 100 "AcDbArc")
           (cons 50 0.78539816)
           (cons 51 5.49778714)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.291 1.073452)
           (cons 40 0)
           (cons 41 0)
           (cons 42 0)
           (cons 91 0)
           (list 10 7.291 1.247548)
           (cons 40 0)
           (cons 41 0)
           (cons 42 0)
           (cons 91 0)
           (list 10 7.44752 1.3)
           (cons 40 0)
           (cons 41 0)
           (cons 42 0)
           (cons 91 0)
           (list 10 8.25248 1.3)
           (cons 40 0)
           (cons 41 0)
           (cons 42 0)
           (cons 91 0)
           (list 10 8.409 1.247548)
           (cons 40 0)
           (cons 41 0)
           (cons 42 0)
           (cons 91 0)
           (list 10 8.409 1.073452)
           (cons 40 0)
           (cons 41 0)
           (cons 42 0)
           (cons 91 0)
           (list 10 8.25248 1.021)
           (cons 40 0)
           (cons 41 0)
           (cons 42 0)
           (cons 91 0)
           (list 10 7.44752 1.021)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.291 0.570452)
           (cons 40 0)
           (cons 41 0)
           (cons 42 0)
           (cons 91 0)
           (list 10 7.291 0.744548)
           (cons 40 0)
           (cons 41 0)
           (cons 42 0)
           (cons 91 0)
           (list 10 7.44752 0.797)
           (cons 40 0)
           (cons 41 0)
           (cons 42 0)
           (cons 91 0)
           (list 10 8.25248 0.797)
           (cons 40 0)
           (cons 41 0)
           (cons 42 0)
           (cons 91 0)
           (list 10 8.409 0.744548)
           (cons 40 0)
           (cons 41 0)
           (cons 42 0)
           (cons 91 0)
           (list 10 8.409 0.570452)
           (cons 40 0)
           (cons 41 0)
           (cons 42 0)
           (cons 91 0)
           (list 10 8.25248 0.518)
           (cons 40 0)
           (cons 41 0)
           (cons 42 0)
           (cons 91 0)
           (list 10 7.44752 0.518)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.891 1.073452)
           (cons 40 0)
           (cons 41 0)
           (cons 42 0)
           (cons 91 0)
           (list 10 5.891 1.247548)
           (cons 40 0)
           (cons 41 0)
           (cons 42 0)
           (cons 91 0)
           (list 10 6.04752 1.3)
           (cons 40 0)
           (cons 41 0)
           (cons 42 0)
           (cons 91 0)
           (list 10 6.85248 1.3)
           (cons 40 0)
           (cons 41 0)
           (cons 42 0)
           (cons 91 0)
           (list 10 7.009 1.247548)
           (cons 40 0)
           (cons 41 0)
           (cons 42 0)
           (cons 91 0)
           (list 10 7.009 1.073452)
           (cons 40 0)
           (cons 41 0)
           (cons 42 0)
           (cons 91 0)
           (list 10 6.85248 1.021)
           (cons 40 0)
           (cons 41 0)
           (cons 42 0)
           (cons 91 0)
           (list 10 6.04752 1.021)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.891 0.570452)
           (cons 40 0)
           (cons 41 0)
           (cons 42 0)
           (cons 91 0)
           (list 10 5.891 0.744548)
           (cons 40 0)
           (cons 41 0)
           (cons 42 0)
           (cons 91 0)
           (list 10 6.04752 0.797)
           (cons 40 0)
           (cons 41 0)
           (cons 42 0)
           (cons 91 0)
           (list 10 6.85248 0.797)
           (cons 40 0)
           (cons 41 0)
           (cons 42 0)
           (cons 91 0)
           (list 10 7.009 0.744548)
           (cons 40 0)
           (cons 41 0)
           (cons 42 0)
           (cons 91 0)
           (list 10 7.009 0.570452)
           (cons 40 0)
           (cons 41 0)
           (cons 42 0)
           (cons 91 0)
           (list 10 6.85248 0.518)
           (cons 40 0)
           (cons 41 0)
           (cons 42 0)
           (cons 91 0)
           (list 10 6.04752 0.518)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.291 -0.744548)
           (cons 40 0)
           (cons 41 0)
           (cons 42 0)
           (cons 91 0)
           (list 10 7.291 -0.570452)
           (cons 40 0)
           (cons 41 0)
           (cons 42 0)
           (cons 91 0)
           (list 10 7.44752 -0.518)
           (cons 40 0)
           (cons 41 0)
           (cons 42 0)
           (cons 91 0)
           (list 10 8.25248 -0.518)
           (cons 40 0)
           (cons 41 0)
           (cons 42 0)
           (cons 91 0)
           (list 10 8.409 -0.570452)
           (cons 40 0)
           (cons 41 0)
           (cons 42 0)
           (cons 91 0)
           (list 10 8.409 -0.744548)
           (cons 40 0)
           (cons 41 0)
           (cons 42 0)
           (cons 91 0)
           (list 10 8.25248 -0.797)
           (cons 40 0)
           (cons 41 0)
           (cons 42 0)
           (cons 91 0)
           (list 10 7.44752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.291 -1.247548)
           (cons 40 0)
           (cons 41 0)
           (cons 42 0)
           (cons 91 0)
           (list 10 7.291 -1.073452)
           (cons 40 0)
           (cons 41 0)
           (cons 42 0)
           (cons 91 0)
           (list 10 7.44752 -1.021)
           (cons 40 0)
           (cons 41 0)
           (cons 42 0)
           (cons 91 0)
           (list 10 8.25248 -1.021)
           (cons 40 0)
           (cons 41 0)
           (cons 42 0)
           (cons 91 0)
           (list 10 8.409 -1.073452)
           (cons 40 0)
           (cons 41 0)
           (cons 42 0)
           (cons 91 0)
           (list 10 8.409 -1.247548)
           (cons 40 0)
           (cons 41 0)
           (cons 42 0)
           (cons 91 0)
           (list 10 8.25248 -1.3)
           (cons 40 0)
           (cons 41 0)
           (cons 42 0)
           (cons 91 0)
           (list 10 7.44752 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.891 -0.744548)
           (cons 40 0)
           (cons 41 0)
           (cons 42 0)
           (cons 91 0)
           (list 10 5.891 -0.570452)
           (cons 40 0)
           (cons 41 0)
           (cons 42 0)
           (cons 91 0)
           (list 10 6.04752 -0.518)
           (cons 40 0)
           (cons 41 0)
           (cons 42 0)
           (cons 91 0)
           (list 10 6.85248 -0.518)
           (cons 40 0)
           (cons 41 0)
           (cons 42 0)
           (cons 91 0)
           (list 10 7.009 -0.570452)
           (cons 40 0)
           (cons 41 0)
           (cons 42 0)
           (cons 91 0)
           (list 10 7.009 -0.744548)
           (cons 40 0)
           (cons 41 0)
           (cons 42 0)
           (cons 91 0)
           (list 10 6.85248 -0.797)
           (cons 40 0)
           (cons 41 0)
           (cons 42 0)
           (cons 91 0)
           (list 10 6.04752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.891 -1.247548)
           (cons 40 0)
           (cons 41 0)
           (cons 42 0)
           (cons 91 0)
           (list 10 5.891 -1.073452)
           (cons 40 0)
           (cons 41 0)
           (cons 42 0)
           (cons 91 0)
           (list 10 6.04752 -1.021)
           (cons 40 0)
           (cons 41 0)
           (cons 42 0)
           (cons 91 0)
           (list 10 6.85248 -1.021)
           (cons 40 0)
           (cons 41 0)
           (cons 42 0)
           (cons 91 0)
           (list 10 7.009 -1.073452)
           (cons 40 0)
           (cons 41 0)
           (cons 42 0)
           (cons 91 0)
           (list 10 7.009 -1.247548)
           (cons 40 0)
           (cons 41 0)
           (cons 42 0)
           (cons 91 0)
           (list 10 6.85248 -1.3)
           (cons 40 0)
           (cons 41 0)
           (cons 42 0)
           (cons 91 0)
           (list 10 6.04752 -1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.2 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.2 -0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.85 -0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.85 0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.2 0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.2 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 7.85 -1.3)
           (cons 40 0)
           (cons 41 0)
           (cons 42 0)
           (cons 91 0)
           (list 10 7.85 1.3)
           (cons 40 0)
           (cons 41 0)
           (cons 42 0)
           (cons 91 0)
           (list 10 0 1.3)
           (cons 40 0)
           (cons 41 0)
           (cons 42 0)
           (cons 91 0)
          )
         )
         (entmake
          (list
           (cons 0 "TEXT")
           (cons 100 "AcDbEntity")
           (cons 67 0)
           (cons 8 "0")
           (cons 100 "AcDbText")
           (list 10 1.94047619 -0.25 0)
           (cons 40 0.5)
           (cons 1 "1")
           (cons 50 0)
           (cons 41 1)
           (cons 51 0)
           (cons 7 "Standard")
           (cons 71 0)
           (cons 72 4)
           (list 11 2 0 0)
           (cons 100 "AcDbText")
           (cons 73 0)
          )
         )
         (entmake (list (cons 0 "ENDBLK")))
        )
       )
       ((= (strcase BLKNAME) (strcase "AB_INF-I-BUS"))
        (progn
         (entmake)
         (entmake
          (list
           (cons 0 "BLOCK")
           (cons 2 "AB_INF-I-BUS")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 12.2 -1.3)
           (cons 40 0)
           (cons 41 0)
           (cons 42 0)
           (cons 91 0)
           (list 10 12.2 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 12.2 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 12.2 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.942 -0.795048)
           (cons 40 0)
           (cons 41 0)
           (cons 42 0)
           (cons 91 0)
           (list 10 7.942 -0.636552)
           (cons 40 0)
           (cons 41 0)
           (cons 42 0)
           (cons 91 0)
           (list 10 8.08424 -0.5888)
           (cons 40 0)
           (cons 41 0)
           (cons 42 0)
           (cons 91 0)
           (list 10 8.81576 -0.5888)
           (cons 40 0)
           (cons 41 0)
           (cons 42 0)
           (cons 91 0)
           (list 10 8.958 -0.636552)
           (cons 40 0)
           (cons 41 0)
           (cons 42 0)
           (cons 91 0)
           (list 10 8.958 -0.795048)
           (cons 40 0)
           (cons 41 0)
           (cons 42 0)
           (cons 91 0)
           (list 10 8.81576 -0.8428)
           (cons 40 0)
           (cons 41 0)
           (cons 42 0)
           (cons 91 0)
           (list 10 8.08424 -0.8428)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.942 -1.252248)
           (cons 40 0)
           (cons 41 0)
           (cons 42 0)
           (cons 91 0)
           (list 10 7.942 -1.093752)
           (cons 40 0)
           (cons 41 0)
           (cons 42 0)
           (cons 91 0)
           (list 10 8.08424 -1.046)
           (cons 40 0)
           (cons 41 0)
           (cons 42 0)
           (cons 91 0)
           (list 10 8.81576 -1.046)
           (cons 40 0)
           (cons 41 0)
           (cons 42 0)
           (cons 91 0)
           (list 10 8.958 -1.093752)
           (cons 40 0)
           (cons 41 0)
           (cons 42 0)
           (cons 91 0)
           (list 10 8.958 -1.252248)
           (cons 40 0)
           (cons 41 0)
           (cons 42 0)
           (cons 91 0)
           (list 10 8.81576 -1.3)
           (cons 40 0)
           (cons 41 0)
           (cons 42 0)
           (cons 91 0)
           (list 10 8.08424 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.942 0.636552)
           (cons 40 0)
           (cons 41 0)
           (cons 42 0)
           (cons 91 0)
           (list 10 7.942 0.795048)
           (cons 40 0)
           (cons 41 0)
           (cons 42 0)
           (cons 91 0)
           (list 10 8.08424 0.8428)
           (cons 40 0)
           (cons 41 0)
           (cons 42 0)
           (cons 91 0)
           (list 10 8.81576 0.8428)
           (cons 40 0)
           (cons 41 0)
           (cons 42 0)
           (cons 91 0)
           (list 10 8.958 0.795048)
           (cons 40 0)
           (cons 41 0)
           (cons 42 0)
           (cons 91 0)
           (list 10 8.958 0.636552)
           (cons 40 0)
           (cons 41 0)
           (cons 42 0)
           (cons 91 0)
           (list 10 8.81576 0.5888)
           (cons 40 0)
           (cons 41 0)
           (cons 42 0)
           (cons 91 0)
           (list 10 8.08424 0.5888)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.942 1.093752)
           (cons 40 0)
           (cons 41 0)
           (cons 42 0)
           (cons 91 0)
           (list 10 7.942 1.252248)
           (cons 40 0)
           (cons 41 0)
           (cons 42 0)
           (cons 91 0)
           (list 10 8.08424 1.3)
           (cons 40 0)
           (cons 41 0)
           (cons 42 0)
           (cons 91 0)
           (list 10 8.81576 1.3)
           (cons 40 0)
           (cons 41 0)
           (cons 42 0)
           (cons 91 0)
           (list 10 8.958 1.252248)
           (cons 40 0)
           (cons 41 0)
           (cons 42 0)
           (cons 91 0)
           (list 10 8.958 1.093752)
           (cons 40 0)
           (cons 41 0)
           (cons 42 0)
           (cons 91 0)
           (list 10 8.81576 1.046)
           (cons 40 0)
           (cons 41 0)
           (cons 42 0)
           (cons 91 0)
           (list 10 8.08424 1.046)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.242 -0.795048)
           (cons 40 0)
           (cons 41 0)
           (cons 42 0)
           (cons 91 0)
           (list 10 9.242 -0.636552)
           (cons 40 0)
           (cons 41 0)
           (cons 42 0)
           (cons 91 0)
           (list 10 9.38424 -0.5888)
           (cons 40 0)
           (cons 41 0)
           (cons 42 0)
           (cons 91 0)
           (list 10 10.11576 -0.5888)
           (cons 40 0)
           (cons 41 0)
           (cons 42 0)
           (cons 91 0)
           (list 10 10.258 -0.636552)
           (cons 40 0)
           (cons 41 0)
           (cons 42 0)
           (cons 91 0)
           (list 10 10.258 -0.795048)
           (cons 40 0)
           (cons 41 0)
           (cons 42 0)
           (cons 91 0)
           (list 10 10.11576 -0.8428)
           (cons 40 0)
           (cons 41 0)
           (cons 42 0)
           (cons 91 0)
           (list 10 9.38424 -0.8428)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.242 -1.252248)
           (cons 40 0)
           (cons 41 0)
           (cons 42 0)
           (cons 91 0)
           (list 10 9.242 -1.093752)
           (cons 40 0)
           (cons 41 0)
           (cons 42 0)
           (cons 91 0)
           (list 10 9.38424 -1.046)
           (cons 40 0)
           (cons 41 0)
           (cons 42 0)
           (cons 91 0)
           (list 10 10.11576 -1.046)
           (cons 40 0)
           (cons 41 0)
           (cons 42 0)
           (cons 91 0)
           (list 10 10.258 -1.093752)
           (cons 40 0)
           (cons 41 0)
           (cons 42 0)
           (cons 91 0)
           (list 10 10.258 -1.252248)
           (cons 40 0)
           (cons 41 0)
           (cons 42 0)
           (cons 91 0)
           (list 10 10.11576 -1.3)
           (cons 40 0)
           (cons 41 0)
           (cons 42 0)
           (cons 91 0)
           (list 10 9.38424 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.242 0.636552)
           (cons 40 0)
           (cons 41 0)
           (cons 42 0)
           (cons 91 0)
           (list 10 9.242 0.795048)
           (cons 40 0)
           (cons 41 0)
           (cons 42 0)
           (cons 91 0)
           (list 10 9.38424 0.8428)
           (cons 40 0)
           (cons 41 0)
           (cons 42 0)
           (cons 91 0)
           (list 10 10.11576 0.8428)
           (cons 40 0)
           (cons 41 0)
           (cons 42 0)
           (cons 91 0)
           (list 10 10.258 0.795048)
           (cons 40 0)
           (cons 41 0)
           (cons 42 0)
           (cons 91 0)
           (list 10 10.258 0.636552)
           (cons 40 0)
           (cons 41 0)
           (cons 42 0)
           (cons 91 0)
           (list 10 10.11576 0.5888)
           (cons 40 0)
           (cons 41 0)
           (cons 42 0)
           (cons 91 0)
           (list 10 9.38424 0.5888)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.242 1.093752)
           (cons 40 0)
           (cons 41 0)
           (cons 42 0)
           (cons 91 0)
           (list 10 9.242 1.252248)
           (cons 40 0)
           (cons 41 0)
           (cons 42 0)
           (cons 91 0)
           (list 10 9.38424 1.3)
           (cons 40 0)
           (cons 41 0)
           (cons 42 0)
           (cons 91 0)
           (list 10 10.11576 1.3)
           (cons 40 0)
           (cons 41 0)
           (cons 42 0)
           (cons 91 0)
           (list 10 10.258 1.252248)
           (cons 40 0)
           (cons 41 0)
           (cons 42 0)
           (cons 91 0)
           (list 10 10.258 1.093752)
           (cons 40 0)
           (cons 41 0)
           (cons 42 0)
           (cons 91 0)
           (list 10 10.11576 1.046)
           (cons 40 0)
           (cons 41 0)
           (cons 42 0)
           (cons 91 0)
           (list 10 9.38424 1.046)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelRightM2")
           (list 10 1.8 1.046 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM2")
           (list 10 1.8 -1.046 0)
           (cons 41 1)
           (cons 42 1)
           (cons 43 1)
           (cons 50 0)
           (cons 70 0)
           (cons 71 0)
           (cons 44 0)
           (cons 45 0)
          )
         )
         (entmake
          (list
           (cons 0 "POINT")
           (cons 100 "AcDbEntity")
           (cons 67 0)
           (cons 8 "0")
           (cons 100 "AcDbPoint")
           (list 10 1.8 0 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 12.2 -1.3 0)
           (cons 50 0)
          )
         )
         (entmake
          (list
           (cons 0 "POINT")
           (cons 100 "AcDbEntity")
           (cons 67 0)
           (cons 8 "0")
           (cons 100 "AcDbPoint")
           (list 10 12.2 1.3 0)
           (cons 50 0)
          )
         )
         (entmake
          (list
           (cons 0 "POINT")
           (cons 100 "AcDbEntity")
           (cons 67 0)
           (cons 8 "0")
           (cons 100 "AcDbPoint")
           (list 10 1.8 -1.3 0)
           (cons 50 0)
          )
         )
         (entmake
          (list
           (cons 0 "POINT")
           (cons 100 "AcDbEntity")
           (cons 67 0)
           (cons 8 "0")
           (cons 100 "AcDbPoint")
           (list 10 1.8 1.3 0)
           (cons 50 0)
          )
         )
         (entmake
          (list
           (cons 0 "POINT")
           (cons 100 "AcDbEntity")
           (cons 67 0)
           (cons 8 "0")
           (cons 100 "AcDbPoint")
           (list 10 9.1 1.3 0)
           (cons 50 0)
          )
         )
         (entmake
          (list
           (cons 0 "POINT")
           (cons 100 "AcDbEntity")
           (cons 67 0)
           (cons 8 "0")
           (cons 100 "AcDbPoint")
           (list 10 9.1 -1.3 0)
           (cons 50 0)
          )
         )
         (entmake
          (list
           (cons 0 "ATTDEF")
           (cons 100 "AcDbEntity")
           (cons 67 0)
           (cons 8 "0")
           (cons 100 "AcDbText")
           (list 10 1.1 0.56666667 0)
           (cons 40 0.2)
           (cons 1 "1.800")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.1 0.23333333 0)
           (cons 40 0.2)
           (cons 1 "1.800")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.1 -0.1 0)
           (cons 40 0.2)
           (cons 1 "9.100")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.1 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.1 -0.76666667 0)
           (cons 40 0.2)
           (cons 1 "31.2")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-HeavyHaul-Pup3"))
        (progn
         (entmake)
         (entmake
          (list
           (cons 0 "BLOCK")
           (cons 2 "AB_INF-HeavyHaul-Pup3")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.762 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.059936 -0.762 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.059936 -0.32766 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.6388 -0.32766 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.6388 0.32766 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.059936 0.32766 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.059936 0.762 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 0.762 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.762 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.762 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 2.4384 0 0)
           (cons 40 0.3452368)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.6576 -0.55256176)
           (cons 40 0)
           (cons 41 0)
           (cons 42 0)
           (cons 91 0)
           (list 10 3.6576 -0.21655024)
           (cons 40 0)
           (cons 41 0)
           (cons 42 0)
           (cons 91 0)
           (list 10 3.785616 -0.115316)
           (cons 40 0)
           (cons 41 0)
           (cons 42 0)
           (cons 91 0)
           (list 10 4.443984 -0.115316)
           (cons 40 0)
           (cons 41 0)
           (cons 42 0)
           (cons 91 0)
           (list 10 4.572 -0.21655024)
           (cons 40 0)
           (cons 41 0)
           (cons 42 0)
           (cons 91 0)
           (list 10 4.572 -0.55256176)
           (cons 40 0)
           (cons 41 0)
           (cons 42 0)
           (cons 91 0)
           (list 10 4.443984 -0.653796)
           (cons 40 0)
           (cons 41 0)
           (cons 42 0)
           (cons 91 0)
           (list 10 3.785616 -0.653796)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.6576 -1.52030176)
           (cons 40 0)
           (cons 41 0)
           (cons 42 0)
           (cons 91 0)
           (list 10 3.6576 -1.18429024)
           (cons 40 0)
           (cons 41 0)
           (cons 42 0)
           (cons 91 0)
           (list 10 3.785616 -1.083056)
           (cons 40 0)
           (cons 41 0)
           (cons 42 0)
           (cons 91 0)
           (list 10 4.443984 -1.083056)
           (cons 40 0)
           (cons 41 0)
           (cons 42 0)
           (cons 91 0)
           (list 10 4.572 -1.18429024)
           (cons 40 0)
           (cons 41 0)
           (cons 42 0)
           (cons 91 0)
           (list 10 4.572 -1.52030176)
           (cons 40 0)
           (cons 41 0)
           (cons 42 0)
           (cons 91 0)
           (list 10 4.443984 -1.621536)
           (cons 40 0)
           (cons 41 0)
           (cons 42 0)
           (cons 91 0)
           (list 10 3.785616 -1.621536)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.6576 -2.48804176)
           (cons 40 0)
           (cons 41 0)
           (cons 42 0)
           (cons 91 0)
           (list 10 3.6576 -2.15203024)
           (cons 40 0)
           (cons 41 0)
           (cons 42 0)
           (cons 91 0)
           (list 10 3.785616 -2.050796)
           (cons 40 0)
           (cons 41 0)
           (cons 42 0)
           (cons 91 0)
           (list 10 4.443984 -2.050796)
           (cons 40 0)
           (cons 41 0)
           (cons 42 0)
           (cons 91 0)
           (list 10 4.572 -2.15203024)
           (cons 40 0)
           (cons 41 0)
           (cons 42 0)
           (cons 91 0)
           (list 10 4.572 -2.48804176)
           (cons 40 0)
           (cons 41 0)
           (cons 42 0)
           (cons 91 0)
           (list 10 4.443984 -2.589276)
           (cons 40 0)
           (cons 41 0)
           (cons 42 0)
           (cons 91 0)
           (list 10 3.785616 -2.589276)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.6576 0.21655024)
           (cons 40 0)
           (cons 41 0)
           (cons 42 0)
           (cons 91 0)
           (list 10 3.6576 0.55256176)
           (cons 40 0)
           (cons 41 0)
           (cons 42 0)
           (cons 91 0)
           (list 10 3.785616 0.653796)
           (cons 40 0)
           (cons 41 0)
           (cons 42 0)
           (cons 91 0)
           (list 10 4.443984 0.653796)
           (cons 40 0)
           (cons 41 0)
           (cons 42 0)
           (cons 91 0)
           (list 10 4.572 0.55256176)
           (cons 40 0)
           (cons 41 0)
           (cons 42 0)
           (cons 91 0)
           (list 10 4.572 0.21655024)
           (cons 40 0)
           (cons 41 0)
           (cons 42 0)
           (cons 91 0)
           (list 10 4.443984 0.115316)
           (cons 40 0)
           (cons 41 0)
           (cons 42 0)
           (cons 91 0)
           (list 10 3.785616 0.115316)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.6576 1.18429024)
           (cons 40 0)
           (cons 41 0)
           (cons 42 0)
           (cons 91 0)
           (list 10 3.6576 1.52030176)
           (cons 40 0)
           (cons 41 0)
           (cons 42 0)
           (cons 91 0)
           (list 10 3.785616 1.621536)
           (cons 40 0)
           (cons 41 0)
           (cons 42 0)
           (cons 91 0)
           (list 10 4.443984 1.621536)
           (cons 40 0)
           (cons 41 0)
           (cons 42 0)
           (cons 91 0)
           (list 10 4.572 1.52030176)
           (cons 40 0)
           (cons 41 0)
           (cons 42 0)
           (cons 91 0)
           (list 10 4.572 1.18429024)
           (cons 40 0)
           (cons 41 0)
           (cons 42 0)
           (cons 91 0)
           (list 10 4.443984 1.083056)
           (cons 40 0)
           (cons 41 0)
           (cons 42 0)
           (cons 91 0)
           (list 10 3.785616 1.083056)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.6576 2.15203024)
           (cons 40 0)
           (cons 41 0)
           (cons 42 0)
           (cons 91 0)
           (list 10 3.6576 2.48804176)
           (cons 40 0)
           (cons 41 0)
           (cons 42 0)
           (cons 91 0)
           (list 10 3.785616 2.589276)
           (cons 40 0)
           (cons 41 0)
           (cons 42 0)
           (cons 91 0)
           (list 10 4.443984 2.589276)
           (cons 40 0)
           (cons 41 0)
           (cons 42 0)
           (cons 91 0)
           (list 10 4.572 2.48804176)
           (cons 40 0)
           (cons 41 0)
           (cons 42 0)
           (cons 91 0)
           (list 10 4.572 2.15203024)
           (cons 40 0)
           (cons 41 0)
           (cons 42 0)
           (cons 91 0)
           (list 10 4.443984 2.050796)
           (cons 40 0)
           (cons 41 0)
           (cons 42 0)
           (cons 91 0)
           (list 10 3.785616 2.050796)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.1816 -0.55256176)
           (cons 40 0)
           (cons 41 0)
           (cons 42 0)
           (cons 91 0)
           (list 10 5.1816 -0.21655024)
           (cons 40 0)
           (cons 41 0)
           (cons 42 0)
           (cons 91 0)
           (list 10 5.309616 -0.115316)
           (cons 40 0)
           (cons 41 0)
           (cons 42 0)
           (cons 91 0)
           (list 10 5.967984 -0.115316)
           (cons 40 0)
           (cons 41 0)
           (cons 42 0)
           (cons 91 0)
           (list 10 6.096 -0.21655024)
           (cons 40 0)
           (cons 41 0)
           (cons 42 0)
           (cons 91 0)
           (list 10 6.096 -0.55256176)
           (cons 40 0)
           (cons 41 0)
           (cons 42 0)
           (cons 91 0)
           (list 10 5.967984 -0.653796)
           (cons 40 0)
           (cons 41 0)
           (cons 42 0)
           (cons 91 0)
           (list 10 5.309616 -0.653796)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.1816 -1.52030176)
           (cons 40 0)
           (cons 41 0)
           (cons 42 0)
           (cons 91 0)
           (list 10 5.1816 -1.18429024)
           (cons 40 0)
           (cons 41 0)
           (cons 42 0)
           (cons 91 0)
           (list 10 5.309616 -1.083056)
           (cons 40 0)
           (cons 41 0)
           (cons 42 0)
           (cons 91 0)
           (list 10 5.967984 -1.083056)
           (cons 40 0)
           (cons 41 0)
           (cons 42 0)
           (cons 91 0)
           (list 10 6.096 -1.18429024)
           (cons 40 0)
           (cons 41 0)
           (cons 42 0)
           (cons 91 0)
           (list 10 6.096 -1.52030176)
           (cons 40 0)
           (cons 41 0)
           (cons 42 0)
           (cons 91 0)
           (list 10 5.967984 -1.621536)
           (cons 40 0)
           (cons 41 0)
           (cons 42 0)
           (cons 91 0)
           (list 10 5.309616 -1.621536)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.1816 -2.48804176)
           (cons 40 0)
           (cons 41 0)
           (cons 42 0)
           (cons 91 0)
           (list 10 5.1816 -2.15203024)
           (cons 40 0)
           (cons 41 0)
           (cons 42 0)
           (cons 91 0)
           (list 10 5.309616 -2.050796)
           (cons 40 0)
           (cons 41 0)
           (cons 42 0)
           (cons 91 0)
           (list 10 5.967984 -2.050796)
           (cons 40 0)
           (cons 41 0)
           (cons 42 0)
           (cons 91 0)
           (list 10 6.096 -2.15203024)
           (cons 40 0)
           (cons 41 0)
           (cons 42 0)
           (cons 91 0)
           (list 10 6.096 -2.48804176)
           (cons 40 0)
           (cons 41 0)
           (cons 42 0)
           (cons 91 0)
           (list 10 5.967984 -2.589276)
           (cons 40 0)
           (cons 41 0)
           (cons 42 0)
           (cons 91 0)
           (list 10 5.309616 -2.589276)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.1816 0.21655024)
           (cons 40 0)
           (cons 41 0)
           (cons 42 0)
           (cons 91 0)
           (list 10 5.1816 0.55256176)
           (cons 40 0)
           (cons 41 0)
           (cons 42 0)
           (cons 91 0)
           (list 10 5.309616 0.653796)
           (cons 40 0)
           (cons 41 0)
           (cons 42 0)
           (cons 91 0)
           (list 10 5.967984 0.653796)
           (cons 40 0)
           (cons 41 0)
           (cons 42 0)
           (cons 91 0)
           (list 10 6.096 0.55256176)
           (cons 40 0)
           (cons 41 0)
           (cons 42 0)
           (cons 91 0)
           (list 10 6.096 0.21655024)
           (cons 40 0)
           (cons 41 0)
           (cons 42 0)
           (cons 91 0)
           (list 10 5.967984 0.115316)
           (cons 40 0)
           (cons 41 0)
           (cons 42 0)
           (cons 91 0)
           (list 10 5.309616 0.115316)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.1816 1.18429024)
           (cons 40 0)
           (cons 41 0)
           (cons 42 0)
           (cons 91 0)
           (list 10 5.1816 1.52030176)
           (cons 40 0)
           (cons 41 0)
           (cons 42 0)
           (cons 91 0)
           (list 10 5.309616 1.621536)
           (cons 40 0)
           (cons 41 0)
           (cons 42 0)
           (cons 91 0)
           (list 10 5.967984 1.621536)
           (cons 40 0)
           (cons 41 0)
           (cons 42 0)
           (cons 91 0)
           (list 10 6.096 1.52030176)
           (cons 40 0)
           (cons 41 0)
           (cons 42 0)
           (cons 91 0)
           (list 10 6.096 1.18429024)
           (cons 40 0)
           (cons 41 0)
           (cons 42 0)
           (cons 91 0)
           (list 10 5.967984 1.083056)
           (cons 40 0)
           (cons 41 0)
           (cons 42 0)
           (cons 91 0)
           (list 10 5.309616 1.083056)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.1816 2.15203024)
           (cons 40 0)
           (cons 41 0)
           (cons 42 0)
           (cons 91 0)
           (list 10 5.1816 2.48804176)
           (cons 40 0)
           (cons 41 0)
           (cons 42 0)
           (cons 91 0)
           (list 10 5.309616 2.589276)
           (cons 40 0)
           (cons 41 0)
           (cons 42 0)
           (cons 91 0)
           (list 10 5.967984 2.589276)
           (cons 40 0)
           (cons 41 0)
           (cons 42 0)
           (cons 91 0)
           (list 10 6.096 2.48804176)
           (cons 40 0)
           (cons 41 0)
           (cons 42 0)
           (cons 91 0)
           (list 10 6.096 2.15203024)
           (cons 40 0)
           (cons 41 0)
           (cons 42 0)
           (cons 91 0)
           (list 10 5.967984 2.050796)
           (cons 40 0)
           (cons 41 0)
           (cons 42 0)
           (cons 91 0)
           (list 10 5.309616 2.050796)
           (cons 40 0)
           (cons 41 0)
           (cons 42 0)
           (cons 91 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 -1.2192 2.589276)
           (cons 40 0)
           (cons 41 0)
           (cons 42 0)
           (cons 91 0)
           (list 10 6.096 2.589276)
           (cons 40 0)
           (cons 41 0)
           (cons 42 0)
           (cons 91 0)
           (list 10 6.096 -2.589276)
           (cons 40 0)
           (cons 41 0)
           (cons 42 0)
           (cons 91 0)
           (list 10 -1.2192 -2.589276)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 4.8768 2.589276 0)
           (cons 50 0)
          )
         )
         (entmake
          (list
           (cons 0 "POINT")
           (cons 100 "AcDbEntity")
           (cons 67 0)
           (cons 8 "0")
           (cons 100 "AcDbPoint")
           (list 10 0 2.589276 0)
           (cons 50 0)
          )
         )
         (entmake
          (list
           (cons 0 "POINT")
           (cons 100 "AcDbEntity")
           (cons 67 0)
           (cons 8 "0")
           (cons 100 "AcDbPoint")
           (list 10 4.8768 -2.589276 0)
           (cons 50 0)
          )
         )
         (entmake
          (list
           (cons 0 "POINT")
           (cons 100 "AcDbEntity")
           (cons 67 0)
           (cons 8 "0")
           (cons 100 "AcDbPoint")
           (list 10 0 -2.589276 0)
           (cons 50 0)
          )
         )
         (entmake
          (list
           (cons 0 "ATTDEF")
           (cons 100 "AcDbEntity")
           (cons 67 0)
           (cons 8 "0")
           (cons 100 "AcDbText")
           (list 10 -0.3 0.56666667 0)
           (cons 40 0.2)
           (cons 1 "2.44")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 0.23333333 0)
           (cons 40 0.2)
           (cons 1 "0.00")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.1 0)
           (cons 40 0.2)
           (cons 1 "4.88")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.43333333 0)
           (cons 40 0.2)
           (cons 1 "0.0")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "POINT")
           (cons 100 "AcDbEntity")
           (cons 67 0)
           (cons 8 "0")
           (cons 100 "AcDbPoint")
           (list 10 2.4384 0 0)
           (cons 50 0)
          )
         )
         (entmake
          (list
           (cons 0 "ATTDEF")
           (cons 100 "AcDbEntity")
           (cons 67 0)
           (cons 8 "0")
           (cons 100 "AcDbText")
           (list 10 -0.3 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "Wheel5")
           (list 10 -0.762 0 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "Wheel5")
           (list 10 0.762 0 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "AB_INF-HeavyHaul-Trailer"))
        (progn
         (entmake)
         (entmake
          (list
           (cons 0 "BLOCK")
           (cons 2 "AB_INF-HeavyHaul-Trailer")
           (cons 70 2)
           (cons 4 "")
           (list 10 0 0 0)
          )
         )
         (entmake
          (list
           (cons 0 "POLYLINE")
           (cons 100 "AcDbEntity")
           (cons 67 0)
           (cons 8 "0")
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 100 "AcDbVertex")
           (cons 100 "AcDb2dVertex")
           (list 10 0 -1.830324 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 100 "AcDbVertex")
           (cons 100 "AcDb2dVertex")
           (list 10 28.6512 -1.830324 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 100 "AcDbVertex")
           (cons 100 "AcDb2dVertex")
           (list 10 28.6512 1.830324 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 100 "AcDbVertex")
           (cons 100 "AcDb2dVertex")
           (list 10 0 1.830324 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 100 "AcDbVertex")
           (cons 100 "AcDb2dVertex")
           (list 10 0 -1.830324 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 100 "AcDbVertex")
           (cons 100 "AcDb2dVertex")
           (list 10 0 -1.830324 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 0 1.830324 0)
           (cons 50 0)
          )
         )
         (entmake
          (list
           (cons 0 "POINT")
           (cons 100 "AcDbEntity")
           (cons 67 0)
           (cons 8 "0")
           (cons 100 "AcDbPoint")
           (list 10 0 -1.830324 0)
           (cons 50 0)
          )
         )
         (entmake
          (list
           (cons 0 "POINT")
           (cons 100 "AcDbEntity")
           (cons 67 0)
           (cons 8 "0")
           (cons 100 "AcDbPoint")
           (list 10 27.1272 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 1.830324)
           (cons 40 0)
           (cons 41 0)
           (cons 42 0)
           (cons 91 0)
           (list 10 28.6512 1.830324)
           (cons 40 0)
           (cons 41 0)
           (cons 42 0)
           (cons 91 0)
           (list 10 28.6512 -1.830324)
           (cons 40 0)
           (cons 41 0)
           (cons 42 0)
           (cons 91 0)
           (list 10 0 -1.830324)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 28.6512 -1.830324 0)
           (cons 50 0)
          )
         )
         (entmake
          (list
           (cons 0 "POINT")
           (cons 100 "AcDbEntity")
           (cons 67 0)
           (cons 8 "0")
           (cons 100 "AcDbPoint")
           (list 10 28.6512 1.830324 0)
           (cons 50 0)
          )
         )
         (entmake
          (list
           (cons 0 "POINT")
           (cons 100 "AcDbEntity")
           (cons 67 0)
           (cons 8 "0")
           (cons 100 "AcDbPoint")
           (list 10 14.33 0 0)
           (cons 50 0)
          )
         )
         (entmake
          (list
           (cons 0 "ATTDEF")
           (cons 100 "AcDbEntity")
           (cons 67 0)
           (cons 8 "0")
           (cons 100 "AcDbText")
           (list 10 -0.3 0.56666667 0)
           (cons 40 0.2)
           (cons 1 "0.0")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 0.23333333 0)
           (cons 40 0.2)
           (cons 1 "0.0")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.1 0)
           (cons 40 0.2)
           (cons 1 "14.33")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.43333333 0)
           (cons 40 0.2)
           (cons 1 "27.13")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-HeavyHaul-Pup2"))
        (progn
         (entmake)
         (entmake
          (list
           (cons 0 "BLOCK")
           (cons 2 "AB_INF-HeavyHaul-Pup2")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.762 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.059936 -0.762 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.059936 -0.338328 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.6388 -0.338328 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.6388 0.338328 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.059936 0.338328 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.059936 0.762 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 0.762 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.762 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.762 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.20714208)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 2.4384 0 0)
           (cons 40 0.73979314)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 2.96151275 -0.52311275 0)
           (list 11 2.96151275 0.52311275 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.6576 -0.55811928)
           (cons 40 0)
           (cons 41 0)
           (cons 42 0)
           (cons 91 0)
           (list 10 3.6576 -0.22369272)
           (cons 40 0)
           (cons 41 0)
           (cons 42 0)
           (cons 91 0)
           (list 10 3.785616 -0.122936)
           (cons 40 0)
           (cons 41 0)
           (cons 42 0)
           (cons 91 0)
           (list 10 4.443984 -0.122936)
           (cons 40 0)
           (cons 41 0)
           (cons 42 0)
           (cons 91 0)
           (list 10 4.572 -0.22369272)
           (cons 40 0)
           (cons 41 0)
           (cons 42 0)
           (cons 91 0)
           (list 10 4.572 -0.55811928)
           (cons 40 0)
           (cons 41 0)
           (cons 42 0)
           (cons 91 0)
           (list 10 4.443984 -0.658876)
           (cons 40 0)
           (cons 41 0)
           (cons 42 0)
           (cons 91 0)
           (list 10 3.785616 -0.658876)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.6576 -1.52331928)
           (cons 40 0)
           (cons 41 0)
           (cons 42 0)
           (cons 91 0)
           (list 10 3.6576 -1.18889272)
           (cons 40 0)
           (cons 41 0)
           (cons 42 0)
           (cons 91 0)
           (list 10 3.785616 -1.088136)
           (cons 40 0)
           (cons 41 0)
           (cons 42 0)
           (cons 91 0)
           (list 10 4.443984 -1.088136)
           (cons 40 0)
           (cons 41 0)
           (cons 42 0)
           (cons 91 0)
           (list 10 4.572 -1.18889272)
           (cons 40 0)
           (cons 41 0)
           (cons 42 0)
           (cons 91 0)
           (list 10 4.572 -1.52331928)
           (cons 40 0)
           (cons 41 0)
           (cons 42 0)
           (cons 91 0)
           (list 10 4.443984 -1.624076)
           (cons 40 0)
           (cons 41 0)
           (cons 42 0)
           (cons 91 0)
           (list 10 3.785616 -1.624076)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.6576 -2.48851928)
           (cons 40 0)
           (cons 41 0)
           (cons 42 0)
           (cons 91 0)
           (list 10 3.6576 -2.15409272)
           (cons 40 0)
           (cons 41 0)
           (cons 42 0)
           (cons 91 0)
           (list 10 3.785616 -2.053336)
           (cons 40 0)
           (cons 41 0)
           (cons 42 0)
           (cons 91 0)
           (list 10 4.443984 -2.053336)
           (cons 40 0)
           (cons 41 0)
           (cons 42 0)
           (cons 91 0)
           (list 10 4.572 -2.15409272)
           (cons 40 0)
           (cons 41 0)
           (cons 42 0)
           (cons 91 0)
           (list 10 4.572 -2.48851928)
           (cons 40 0)
           (cons 41 0)
           (cons 42 0)
           (cons 91 0)
           (list 10 4.443984 -2.589276)
           (cons 40 0)
           (cons 41 0)
           (cons 42 0)
           (cons 91 0)
           (list 10 3.785616 -2.589276)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.6576 0.22369272)
           (cons 40 0)
           (cons 41 0)
           (cons 42 0)
           (cons 91 0)
           (list 10 3.6576 0.55811928)
           (cons 40 0)
           (cons 41 0)
           (cons 42 0)
           (cons 91 0)
           (list 10 3.785616 0.658876)
           (cons 40 0)
           (cons 41 0)
           (cons 42 0)
           (cons 91 0)
           (list 10 4.443984 0.658876)
           (cons 40 0)
           (cons 41 0)
           (cons 42 0)
           (cons 91 0)
           (list 10 4.572 0.55811928)
           (cons 40 0)
           (cons 41 0)
           (cons 42 0)
           (cons 91 0)
           (list 10 4.572 0.22369272)
           (cons 40 0)
           (cons 41 0)
           (cons 42 0)
           (cons 91 0)
           (list 10 4.443984 0.122936)
           (cons 40 0)
           (cons 41 0)
           (cons 42 0)
           (cons 91 0)
           (list 10 3.785616 0.122936)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.6576 1.18889272)
           (cons 40 0)
           (cons 41 0)
           (cons 42 0)
           (cons 91 0)
           (list 10 3.6576 1.52331928)
           (cons 40 0)
           (cons 41 0)
           (cons 42 0)
           (cons 91 0)
           (list 10 3.785616 1.624076)
           (cons 40 0)
           (cons 41 0)
           (cons 42 0)
           (cons 91 0)
           (list 10 4.443984 1.624076)
           (cons 40 0)
           (cons 41 0)
           (cons 42 0)
           (cons 91 0)
           (list 10 4.572 1.52331928)
           (cons 40 0)
           (cons 41 0)
           (cons 42 0)
           (cons 91 0)
           (list 10 4.572 1.18889272)
           (cons 40 0)
           (cons 41 0)
           (cons 42 0)
           (cons 91 0)
           (list 10 4.443984 1.088136)
           (cons 40 0)
           (cons 41 0)
           (cons 42 0)
           (cons 91 0)
           (list 10 3.785616 1.088136)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.6576 2.15409272)
           (cons 40 0)
           (cons 41 0)
           (cons 42 0)
           (cons 91 0)
           (list 10 3.6576 2.48851928)
           (cons 40 0)
           (cons 41 0)
           (cons 42 0)
           (cons 91 0)
           (list 10 3.785616 2.589276)
           (cons 40 0)
           (cons 41 0)
           (cons 42 0)
           (cons 91 0)
           (list 10 4.443984 2.589276)
           (cons 40 0)
           (cons 41 0)
           (cons 42 0)
           (cons 91 0)
           (list 10 4.572 2.48851928)
           (cons 40 0)
           (cons 41 0)
           (cons 42 0)
           (cons 91 0)
           (list 10 4.572 2.15409272)
           (cons 40 0)
           (cons 41 0)
           (cons 42 0)
           (cons 91 0)
           (list 10 4.443984 2.053336)
           (cons 40 0)
           (cons 41 0)
           (cons 42 0)
           (cons 91 0)
           (list 10 3.785616 2.053336)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.1816 -0.55811928)
           (cons 40 0)
           (cons 41 0)
           (cons 42 0)
           (cons 91 0)
           (list 10 5.1816 -0.22369272)
           (cons 40 0)
           (cons 41 0)
           (cons 42 0)
           (cons 91 0)
           (list 10 5.309616 -0.122936)
           (cons 40 0)
           (cons 41 0)
           (cons 42 0)
           (cons 91 0)
           (list 10 5.967984 -0.122936)
           (cons 40 0)
           (cons 41 0)
           (cons 42 0)
           (cons 91 0)
           (list 10 6.096 -0.22369272)
           (cons 40 0)
           (cons 41 0)
           (cons 42 0)
           (cons 91 0)
           (list 10 6.096 -0.55811928)
           (cons 40 0)
           (cons 41 0)
           (cons 42 0)
           (cons 91 0)
           (list 10 5.967984 -0.658876)
           (cons 40 0)
           (cons 41 0)
           (cons 42 0)
           (cons 91 0)
           (list 10 5.309616 -0.658876)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.1816 -1.52331928)
           (cons 40 0)
           (cons 41 0)
           (cons 42 0)
           (cons 91 0)
           (list 10 5.1816 -1.18889272)
           (cons 40 0)
           (cons 41 0)
           (cons 42 0)
           (cons 91 0)
           (list 10 5.309616 -1.088136)
           (cons 40 0)
           (cons 41 0)
           (cons 42 0)
           (cons 91 0)
           (list 10 5.967984 -1.088136)
           (cons 40 0)
           (cons 41 0)
           (cons 42 0)
           (cons 91 0)
           (list 10 6.096 -1.18889272)
           (cons 40 0)
           (cons 41 0)
           (cons 42 0)
           (cons 91 0)
           (list 10 6.096 -1.52331928)
           (cons 40 0)
           (cons 41 0)
           (cons 42 0)
           (cons 91 0)
           (list 10 5.967984 -1.624076)
           (cons 40 0)
           (cons 41 0)
           (cons 42 0)
           (cons 91 0)
           (list 10 5.309616 -1.624076)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.1816 -2.48851928)
           (cons 40 0)
           (cons 41 0)
           (cons 42 0)
           (cons 91 0)
           (list 10 5.1816 -2.15409272)
           (cons 40 0)
           (cons 41 0)
           (cons 42 0)
           (cons 91 0)
           (list 10 5.309616 -2.053336)
           (cons 40 0)
           (cons 41 0)
           (cons 42 0)
           (cons 91 0)
           (list 10 5.967984 -2.053336)
           (cons 40 0)
           (cons 41 0)
           (cons 42 0)
           (cons 91 0)
           (list 10 6.096 -2.15409272)
           (cons 40 0)
           (cons 41 0)
           (cons 42 0)
           (cons 91 0)
           (list 10 6.096 -2.48851928)
           (cons 40 0)
           (cons 41 0)
           (cons 42 0)
           (cons 91 0)
           (list 10 5.967984 -2.589276)
           (cons 40 0)
           (cons 41 0)
           (cons 42 0)
           (cons 91 0)
           (list 10 5.309616 -2.589276)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.1816 0.22369272)
           (cons 40 0)
           (cons 41 0)
           (cons 42 0)
           (cons 91 0)
           (list 10 5.1816 0.55811928)
           (cons 40 0)
           (cons 41 0)
           (cons 42 0)
           (cons 91 0)
           (list 10 5.309616 0.658876)
           (cons 40 0)
           (cons 41 0)
           (cons 42 0)
           (cons 91 0)
           (list 10 5.967984 0.658876)
           (cons 40 0)
           (cons 41 0)
           (cons 42 0)
           (cons 91 0)
           (list 10 6.096 0.55811928)
           (cons 40 0)
           (cons 41 0)
           (cons 42 0)
           (cons 91 0)
           (list 10 6.096 0.22369272)
           (cons 40 0)
           (cons 41 0)
           (cons 42 0)
           (cons 91 0)
           (list 10 5.967984 0.122936)
           (cons 40 0)
           (cons 41 0)
           (cons 42 0)
           (cons 91 0)
           (list 10 5.309616 0.122936)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.1816 1.18889272)
           (cons 40 0)
           (cons 41 0)
           (cons 42 0)
           (cons 91 0)
           (list 10 5.1816 1.52331928)
           (cons 40 0)
           (cons 41 0)
           (cons 42 0)
           (cons 91 0)
           (list 10 5.309616 1.624076)
           (cons 40 0)
           (cons 41 0)
           (cons 42 0)
           (cons 91 0)
           (list 10 5.967984 1.624076)
           (cons 40 0)
           (cons 41 0)
           (cons 42 0)
           (cons 91 0)
           (list 10 6.096 1.52331928)
           (cons 40 0)
           (cons 41 0)
           (cons 42 0)
           (cons 91 0)
           (list 10 6.096 1.18889272)
           (cons 40 0)
           (cons 41 0)
           (cons 42 0)
           (cons 91 0)
           (list 10 5.967984 1.088136)
           (cons 40 0)
           (cons 41 0)
           (cons 42 0)
           (cons 91 0)
           (list 10 5.309616 1.088136)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.1816 2.15409272)
           (cons 40 0)
           (cons 41 0)
           (cons 42 0)
           (cons 91 0)
           (list 10 5.1816 2.48851928)
           (cons 40 0)
           (cons 41 0)
           (cons 42 0)
           (cons 91 0)
           (list 10 5.309616 2.589276)
           (cons 40 0)
           (cons 41 0)
           (cons 42 0)
           (cons 91 0)
           (list 10 5.967984 2.589276)
           (cons 40 0)
           (cons 41 0)
           (cons 42 0)
           (cons 91 0)
           (list 10 6.096 2.48851928)
           (cons 40 0)
           (cons 41 0)
           (cons 42 0)
           (cons 91 0)
           (list 10 6.096 2.15409272)
           (cons 40 0)
           (cons 41 0)
           (cons 42 0)
           (cons 91 0)
           (list 10 5.967984 2.053336)
           (cons 40 0)
           (cons 41 0)
           (cons 42 0)
           (cons 91 0)
           (list 10 5.309616 2.053336)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 2.4384 0 0)
           (cons 50 0)
          )
         )
         (entmake
          (list
           (cons 0 "POINT")
           (cons 100 "AcDbEntity")
           (cons 67 0)
           (cons 8 "0")
           (cons 100 "AcDbPoint")
           (list 10 4.8768 -2.589276 0)
           (cons 50 0)
          )
         )
         (entmake
          (list
           (cons 0 "POINT")
           (cons 100 "AcDbEntity")
           (cons 67 0)
           (cons 8 "0")
           (cons 100 "AcDbPoint")
           (list 10 4.8768 2.589276 0)
           (cons 50 0)
          )
         )
         (entmake
          (list
           (cons 0 "POINT")
           (cons 100 "AcDbEntity")
           (cons 67 0)
           (cons 8 "0")
           (cons 100 "AcDbPoint")
           (list 10 4.8768 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 3.6576 2.589276)
           (cons 40 0)
           (cons 41 0)
           (cons 42 0)
           (cons 91 0)
           (list 10 6.099048 2.589276)
           (cons 40 0)
           (cons 41 0)
           (cons 42 0)
           (cons 91 0)
           (list 10 6.099048 -2.589276)
           (cons 40 0)
           (cons 41 0)
           (cons 42 0)
           (cons 91 0)
           (list 10 3.6576 -2.589276)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 -0.3 0.56666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 0.23333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.1 0)
           (cons 40 0.2)
           (cons 1 "4.88")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.43333333 0)
           (cons 40 0.2)
           (cons 1 "2.44")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-HeavyHaul-Pup1"))
        (progn
         (entmake)
         (entmake
          (list
           (cons 0 "BLOCK")
           (cons 2 "AB_INF-HeavyHaul-Pup1")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.762 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.059936 -0.762 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.059936 -0.370332 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.641848 -0.370332 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.641848 0.370332 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.059936 0.370332 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.059936 0.762 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 0.762 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.762 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.762 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.20714208)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 4.879848 0 0)
           (cons 40 0.73979314)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 5.40296075 -0.52311275 0)
           (list 11 5.40296075 0.52311275 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.660648 -0.57479184)
           (cons 40 0)
           (cons 41 0)
           (cons 42 0)
           (cons 91 0)
           (list 10 3.660648 -0.24512016)
           (cons 40 0)
           (cons 41 0)
           (cons 42 0)
           (cons 91 0)
           (list 10 3.788664 -0.145796)
           (cons 40 0)
           (cons 41 0)
           (cons 42 0)
           (cons 91 0)
           (list 10 4.447032 -0.145796)
           (cons 40 0)
           (cons 41 0)
           (cons 42 0)
           (cons 91 0)
           (list 10 4.575048 -0.24512016)
           (cons 40 0)
           (cons 41 0)
           (cons 42 0)
           (cons 91 0)
           (list 10 4.575048 -0.57479184)
           (cons 40 0)
           (cons 41 0)
           (cons 42 0)
           (cons 91 0)
           (list 10 4.447032 -0.674116)
           (cons 40 0)
           (cons 41 0)
           (cons 42 0)
           (cons 91 0)
           (list 10 3.788664 -0.674116)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.660648 -1.53237184)
           (cons 40 0)
           (cons 41 0)
           (cons 42 0)
           (cons 91 0)
           (list 10 3.660648 -1.20270016)
           (cons 40 0)
           (cons 41 0)
           (cons 42 0)
           (cons 91 0)
           (list 10 3.788664 -1.103376)
           (cons 40 0)
           (cons 41 0)
           (cons 42 0)
           (cons 91 0)
           (list 10 4.447032 -1.103376)
           (cons 40 0)
           (cons 41 0)
           (cons 42 0)
           (cons 91 0)
           (list 10 4.575048 -1.20270016)
           (cons 40 0)
           (cons 41 0)
           (cons 42 0)
           (cons 91 0)
           (list 10 4.575048 -1.53237184)
           (cons 40 0)
           (cons 41 0)
           (cons 42 0)
           (cons 91 0)
           (list 10 4.447032 -1.631696)
           (cons 40 0)
           (cons 41 0)
           (cons 42 0)
           (cons 91 0)
           (list 10 3.788664 -1.631696)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.660648 -2.48995184)
           (cons 40 0)
           (cons 41 0)
           (cons 42 0)
           (cons 91 0)
           (list 10 3.660648 -2.16028016)
           (cons 40 0)
           (cons 41 0)
           (cons 42 0)
           (cons 91 0)
           (list 10 3.788664 -2.060956)
           (cons 40 0)
           (cons 41 0)
           (cons 42 0)
           (cons 91 0)
           (list 10 4.447032 -2.060956)
           (cons 40 0)
           (cons 41 0)
           (cons 42 0)
           (cons 91 0)
           (list 10 4.575048 -2.16028016)
           (cons 40 0)
           (cons 41 0)
           (cons 42 0)
           (cons 91 0)
           (list 10 4.575048 -2.48995184)
           (cons 40 0)
           (cons 41 0)
           (cons 42 0)
           (cons 91 0)
           (list 10 4.447032 -2.589276)
           (cons 40 0)
           (cons 41 0)
           (cons 42 0)
           (cons 91 0)
           (list 10 3.788664 -2.589276)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.660648 0.24512016)
           (cons 40 0)
           (cons 41 0)
           (cons 42 0)
           (cons 91 0)
           (list 10 3.660648 0.57479184)
           (cons 40 0)
           (cons 41 0)
           (cons 42 0)
           (cons 91 0)
           (list 10 3.788664 0.674116)
           (cons 40 0)
           (cons 41 0)
           (cons 42 0)
           (cons 91 0)
           (list 10 4.447032 0.674116)
           (cons 40 0)
           (cons 41 0)
           (cons 42 0)
           (cons 91 0)
           (list 10 4.575048 0.57479184)
           (cons 40 0)
           (cons 41 0)
           (cons 42 0)
           (cons 91 0)
           (list 10 4.575048 0.24512016)
           (cons 40 0)
           (cons 41 0)
           (cons 42 0)
           (cons 91 0)
           (list 10 4.447032 0.145796)
           (cons 40 0)
           (cons 41 0)
           (cons 42 0)
           (cons 91 0)
           (list 10 3.788664 0.145796)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.660648 1.20270016)
           (cons 40 0)
           (cons 41 0)
           (cons 42 0)
           (cons 91 0)
           (list 10 3.660648 1.53237184)
           (cons 40 0)
           (cons 41 0)
           (cons 42 0)
           (cons 91 0)
           (list 10 3.788664 1.631696)
           (cons 40 0)
           (cons 41 0)
           (cons 42 0)
           (cons 91 0)
           (list 10 4.447032 1.631696)
           (cons 40 0)
           (cons 41 0)
           (cons 42 0)
           (cons 91 0)
           (list 10 4.575048 1.53237184)
           (cons 40 0)
           (cons 41 0)
           (cons 42 0)
           (cons 91 0)
           (list 10 4.575048 1.20270016)
           (cons 40 0)
           (cons 41 0)
           (cons 42 0)
           (cons 91 0)
           (list 10 4.447032 1.103376)
           (cons 40 0)
           (cons 41 0)
           (cons 42 0)
           (cons 91 0)
           (list 10 3.788664 1.103376)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.660648 2.16028016)
           (cons 40 0)
           (cons 41 0)
           (cons 42 0)
           (cons 91 0)
           (list 10 3.660648 2.48995184)
           (cons 40 0)
           (cons 41 0)
           (cons 42 0)
           (cons 91 0)
           (list 10 3.788664 2.589276)
           (cons 40 0)
           (cons 41 0)
           (cons 42 0)
           (cons 91 0)
           (list 10 4.447032 2.589276)
           (cons 40 0)
           (cons 41 0)
           (cons 42 0)
           (cons 91 0)
           (list 10 4.575048 2.48995184)
           (cons 40 0)
           (cons 41 0)
           (cons 42 0)
           (cons 91 0)
           (list 10 4.575048 2.16028016)
           (cons 40 0)
           (cons 41 0)
           (cons 42 0)
           (cons 91 0)
           (list 10 4.447032 2.060956)
           (cons 40 0)
           (cons 41 0)
           (cons 42 0)
           (cons 91 0)
           (list 10 3.788664 2.060956)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.184648 -0.57479184)
           (cons 40 0)
           (cons 41 0)
           (cons 42 0)
           (cons 91 0)
           (list 10 5.184648 -0.24512016)
           (cons 40 0)
           (cons 41 0)
           (cons 42 0)
           (cons 91 0)
           (list 10 5.312664 -0.145796)
           (cons 40 0)
           (cons 41 0)
           (cons 42 0)
           (cons 91 0)
           (list 10 5.971032 -0.145796)
           (cons 40 0)
           (cons 41 0)
           (cons 42 0)
           (cons 91 0)
           (list 10 6.099048 -0.24512016)
           (cons 40 0)
           (cons 41 0)
           (cons 42 0)
           (cons 91 0)
           (list 10 6.099048 -0.57479184)
           (cons 40 0)
           (cons 41 0)
           (cons 42 0)
           (cons 91 0)
           (list 10 5.971032 -0.674116)
           (cons 40 0)
           (cons 41 0)
           (cons 42 0)
           (cons 91 0)
           (list 10 5.312664 -0.674116)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.184648 -1.53237184)
           (cons 40 0)
           (cons 41 0)
           (cons 42 0)
           (cons 91 0)
           (list 10 5.184648 -1.20270016)
           (cons 40 0)
           (cons 41 0)
           (cons 42 0)
           (cons 91 0)
           (list 10 5.312664 -1.103376)
           (cons 40 0)
           (cons 41 0)
           (cons 42 0)
           (cons 91 0)
           (list 10 5.971032 -1.103376)
           (cons 40 0)
           (cons 41 0)
           (cons 42 0)
           (cons 91 0)
           (list 10 6.099048 -1.20270016)
           (cons 40 0)
           (cons 41 0)
           (cons 42 0)
           (cons 91 0)
           (list 10 6.099048 -1.53237184)
           (cons 40 0)
           (cons 41 0)
           (cons 42 0)
           (cons 91 0)
           (list 10 5.971032 -1.631696)
           (cons 40 0)
           (cons 41 0)
           (cons 42 0)
           (cons 91 0)
           (list 10 5.312664 -1.631696)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.184648 -2.48995184)
           (cons 40 0)
           (cons 41 0)
           (cons 42 0)
           (cons 91 0)
           (list 10 5.184648 -2.16028016)
           (cons 40 0)
           (cons 41 0)
           (cons 42 0)
           (cons 91 0)
           (list 10 5.312664 -2.060956)
           (cons 40 0)
           (cons 41 0)
           (cons 42 0)
           (cons 91 0)
           (list 10 5.971032 -2.060956)
           (cons 40 0)
           (cons 41 0)
           (cons 42 0)
           (cons 91 0)
           (list 10 6.099048 -2.16028016)
           (cons 40 0)
           (cons 41 0)
           (cons 42 0)
           (cons 91 0)
           (list 10 6.099048 -2.48995184)
           (cons 40 0)
           (cons 41 0)
           (cons 42 0)
           (cons 91 0)
           (list 10 5.971032 -2.589276)
           (cons 40 0)
           (cons 41 0)
           (cons 42 0)
           (cons 91 0)
           (list 10 5.312664 -2.589276)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.184648 0.24512016)
           (cons 40 0)
           (cons 41 0)
           (cons 42 0)
           (cons 91 0)
           (list 10 5.184648 0.57479184)
           (cons 40 0)
           (cons 41 0)
           (cons 42 0)
           (cons 91 0)
           (list 10 5.312664 0.674116)
           (cons 40 0)
           (cons 41 0)
           (cons 42 0)
           (cons 91 0)
           (list 10 5.971032 0.674116)
           (cons 40 0)
           (cons 41 0)
           (cons 42 0)
           (cons 91 0)
           (list 10 6.099048 0.57479184)
           (cons 40 0)
           (cons 41 0)
           (cons 42 0)
           (cons 91 0)
           (list 10 6.099048 0.24512016)
           (cons 40 0)
           (cons 41 0)
           (cons 42 0)
           (cons 91 0)
           (list 10 5.971032 0.145796)
           (cons 40 0)
           (cons 41 0)
           (cons 42 0)
           (cons 91 0)
           (list 10 5.312664 0.145796)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.184648 1.20270016)
           (cons 40 0)
           (cons 41 0)
           (cons 42 0)
           (cons 91 0)
           (list 10 5.184648 1.53237184)
           (cons 40 0)
           (cons 41 0)
           (cons 42 0)
           (cons 91 0)
           (list 10 5.312664 1.631696)
           (cons 40 0)
           (cons 41 0)
           (cons 42 0)
           (cons 91 0)
           (list 10 5.971032 1.631696)
           (cons 40 0)
           (cons 41 0)
           (cons 42 0)
           (cons 91 0)
           (list 10 6.099048 1.53237184)
           (cons 40 0)
           (cons 41 0)
           (cons 42 0)
           (cons 91 0)
           (list 10 6.099048 1.20270016)
           (cons 40 0)
           (cons 41 0)
           (cons 42 0)
           (cons 91 0)
           (list 10 5.971032 1.103376)
           (cons 40 0)
           (cons 41 0)
           (cons 42 0)
           (cons 91 0)
           (list 10 5.312664 1.103376)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.184648 2.16028016)
           (cons 40 0)
           (cons 41 0)
           (cons 42 0)
           (cons 91 0)
           (list 10 5.184648 2.48995184)
           (cons 40 0)
           (cons 41 0)
           (cons 42 0)
           (cons 91 0)
           (list 10 5.312664 2.589276)
           (cons 40 0)
           (cons 41 0)
           (cons 42 0)
           (cons 91 0)
           (list 10 5.971032 2.589276)
           (cons 40 0)
           (cons 41 0)
           (cons 42 0)
           (cons 91 0)
           (list 10 6.099048 2.48995184)
           (cons 40 0)
           (cons 41 0)
           (cons 42 0)
           (cons 91 0)
           (list 10 6.099048 2.16028016)
           (cons 40 0)
           (cons 41 0)
           (cons 42 0)
           (cons 91 0)
           (list 10 5.971032 2.060956)
           (cons 40 0)
           (cons 41 0)
           (cons 42 0)
           (cons 91 0)
           (list 10 5.312664 2.060956)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 4.879848 0 0)
           (cons 50 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 3.660648 2.589276)
           (cons 40 0)
           (cons 41 0)
           (cons 42 0)
           (cons 91 0)
           (list 10 6.099048 2.589276)
           (cons 40 0)
           (cons 41 0)
           (cons 42 0)
           (cons 91 0)
           (list 10 6.099048 -2.589276)
           (cons 40 0)
           (cons 41 0)
           (cons 42 0)
           (cons 91 0)
           (list 10 3.660648 -2.589276)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 -0.3 0.56666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 0.23333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.1 0)
           (cons 40 0.2)
           (cons 1 "4.88")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.43333333 0)
           (cons 40 0.2)
           (cons 1 "4.88")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "POINT")
           (cons 100 "AcDbEntity")
           (cons 67 0)
           (cons 8 "0")
           (cons 100 "AcDbPoint")
           (list 10 4.879848 2.589276 0)
           (cons 50 0)
          )
         )
         (entmake
          (list
           (cons 0 "POINT")
           (cons 100 "AcDbEntity")
           (cons 67 0)
           (cons 8 "0")
           (cons 100 "AcDbPoint")
           (list 10 4.879848 -2.589276 0)
           (cons 50 0)
          )
         )
         (entmake
          (list
           (cons 0 "ATTDEF")
           (cons 100 "AcDbEntity")
           (cons 67 0)
           (cons 8 "0")
           (cons 100 "AcDbText")
           (list 10 -0.3 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-HeavyHaul-Truck"))
        (progn
         (entmake)
         (entmake
          (list
           (cons 0 "BLOCK")
           (cons 2 "AB_INF-HeavyHaul-Truck")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2954 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.898648 -1.2954 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.898648 -0.5842 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.7216 -0.5842 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.7216 0.5842 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.898648 0.5842 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.898648 1.2954 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.2954 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2954 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2954 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 7.0104 0 0)
           (cons 40 0.37011429)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 7.27211032 -0.26171032 0)
           (list 11 7.27211032 0.26171032 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.7912 -0.790448)
           (cons 40 0)
           (cons 41 0)
           (cons 42 0)
           (cons 91 0)
           (list 10 5.7912 -0.631952)
           (cons 40 0)
           (cons 41 0)
           (cons 42 0)
           (cons 91 0)
           (list 10 5.93344 -0.5842)
           (cons 40 0)
           (cons 41 0)
           (cons 42 0)
           (cons 91 0)
           (list 10 6.66496 -0.5842)
           (cons 40 0)
           (cons 41 0)
           (cons 42 0)
           (cons 91 0)
           (list 10 6.8072 -0.631952)
           (cons 40 0)
           (cons 41 0)
           (cons 42 0)
           (cons 91 0)
           (list 10 6.8072 -0.790448)
           (cons 40 0)
           (cons 41 0)
           (cons 42 0)
           (cons 91 0)
           (list 10 6.66496 -0.8382)
           (cons 40 0)
           (cons 41 0)
           (cons 42 0)
           (cons 91 0)
           (list 10 5.93344 -0.8382)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.7912 -1.247648)
           (cons 40 0)
           (cons 41 0)
           (cons 42 0)
           (cons 91 0)
           (list 10 5.7912 -1.089152)
           (cons 40 0)
           (cons 41 0)
           (cons 42 0)
           (cons 91 0)
           (list 10 5.93344 -1.0414)
           (cons 40 0)
           (cons 41 0)
           (cons 42 0)
           (cons 91 0)
           (list 10 6.66496 -1.0414)
           (cons 40 0)
           (cons 41 0)
           (cons 42 0)
           (cons 91 0)
           (list 10 6.8072 -1.089152)
           (cons 40 0)
           (cons 41 0)
           (cons 42 0)
           (cons 91 0)
           (list 10 6.8072 -1.247648)
           (cons 40 0)
           (cons 41 0)
           (cons 42 0)
           (cons 91 0)
           (list 10 6.66496 -1.2954)
           (cons 40 0)
           (cons 41 0)
           (cons 42 0)
           (cons 91 0)
           (list 10 5.93344 -1.2954)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.7912 0.631952)
           (cons 40 0)
           (cons 41 0)
           (cons 42 0)
           (cons 91 0)
           (list 10 5.7912 0.790448)
           (cons 40 0)
           (cons 41 0)
           (cons 42 0)
           (cons 91 0)
           (list 10 5.93344 0.8382)
           (cons 40 0)
           (cons 41 0)
           (cons 42 0)
           (cons 91 0)
           (list 10 6.66496 0.8382)
           (cons 40 0)
           (cons 41 0)
           (cons 42 0)
           (cons 91 0)
           (list 10 6.8072 0.790448)
           (cons 40 0)
           (cons 41 0)
           (cons 42 0)
           (cons 91 0)
           (list 10 6.8072 0.631952)
           (cons 40 0)
           (cons 41 0)
           (cons 42 0)
           (cons 91 0)
           (list 10 6.66496 0.5842)
           (cons 40 0)
           (cons 41 0)
           (cons 42 0)
           (cons 91 0)
           (list 10 5.93344 0.5842)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.7912 1.089152)
           (cons 40 0)
           (cons 41 0)
           (cons 42 0)
           (cons 91 0)
           (list 10 5.7912 1.247648)
           (cons 40 0)
           (cons 41 0)
           (cons 42 0)
           (cons 91 0)
           (list 10 5.93344 1.2954)
           (cons 40 0)
           (cons 41 0)
           (cons 42 0)
           (cons 91 0)
           (list 10 6.66496 1.2954)
           (cons 40 0)
           (cons 41 0)
           (cons 42 0)
           (cons 91 0)
           (list 10 6.8072 1.247648)
           (cons 40 0)
           (cons 41 0)
           (cons 42 0)
           (cons 91 0)
           (list 10 6.8072 1.089152)
           (cons 40 0)
           (cons 41 0)
           (cons 42 0)
           (cons 91 0)
           (list 10 6.66496 1.0414)
           (cons 40 0)
           (cons 41 0)
           (cons 42 0)
           (cons 91 0)
           (list 10 5.93344 1.0414)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.2136 -0.790448)
           (cons 40 0)
           (cons 41 0)
           (cons 42 0)
           (cons 91 0)
           (list 10 7.2136 -0.631952)
           (cons 40 0)
           (cons 41 0)
           (cons 42 0)
           (cons 91 0)
           (list 10 7.35584 -0.5842)
           (cons 40 0)
           (cons 41 0)
           (cons 42 0)
           (cons 91 0)
           (list 10 8.08736 -0.5842)
           (cons 40 0)
           (cons 41 0)
           (cons 42 0)
           (cons 91 0)
           (list 10 8.2296 -0.631952)
           (cons 40 0)
           (cons 41 0)
           (cons 42 0)
           (cons 91 0)
           (list 10 8.2296 -0.790448)
           (cons 40 0)
           (cons 41 0)
           (cons 42 0)
           (cons 91 0)
           (list 10 8.08736 -0.8382)
           (cons 40 0)
           (cons 41 0)
           (cons 42 0)
           (cons 91 0)
           (list 10 7.35584 -0.8382)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.2136 -1.247648)
           (cons 40 0)
           (cons 41 0)
           (cons 42 0)
           (cons 91 0)
           (list 10 7.2136 -1.089152)
           (cons 40 0)
           (cons 41 0)
           (cons 42 0)
           (cons 91 0)
           (list 10 7.35584 -1.0414)
           (cons 40 0)
           (cons 41 0)
           (cons 42 0)
           (cons 91 0)
           (list 10 8.08736 -1.0414)
           (cons 40 0)
           (cons 41 0)
           (cons 42 0)
           (cons 91 0)
           (list 10 8.2296 -1.089152)
           (cons 40 0)
           (cons 41 0)
           (cons 42 0)
           (cons 91 0)
           (list 10 8.2296 -1.247648)
           (cons 40 0)
           (cons 41 0)
           (cons 42 0)
           (cons 91 0)
           (list 10 8.08736 -1.2954)
           (cons 40 0)
           (cons 41 0)
           (cons 42 0)
           (cons 91 0)
           (list 10 7.35584 -1.2954)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.2136 0.631952)
           (cons 40 0)
           (cons 41 0)
           (cons 42 0)
           (cons 91 0)
           (list 10 7.2136 0.790448)
           (cons 40 0)
           (cons 41 0)
           (cons 42 0)
           (cons 91 0)
           (list 10 7.35584 0.8382)
           (cons 40 0)
           (cons 41 0)
           (cons 42 0)
           (cons 91 0)
           (list 10 8.08736 0.8382)
           (cons 40 0)
           (cons 41 0)
           (cons 42 0)
           (cons 91 0)
           (list 10 8.2296 0.790448)
           (cons 40 0)
           (cons 41 0)
           (cons 42 0)
           (cons 91 0)
           (list 10 8.2296 0.631952)
           (cons 40 0)
           (cons 41 0)
           (cons 42 0)
           (cons 91 0)
           (list 10 8.08736 0.5842)
           (cons 40 0)
           (cons 41 0)
           (cons 42 0)
           (cons 91 0)
           (list 10 7.35584 0.5842)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.2136 1.089152)
           (cons 40 0)
           (cons 41 0)
           (cons 42 0)
           (cons 91 0)
           (list 10 7.2136 1.247648)
           (cons 40 0)
           (cons 41 0)
           (cons 42 0)
           (cons 91 0)
           (list 10 7.35584 1.2954)
           (cons 40 0)
           (cons 41 0)
           (cons 42 0)
           (cons 91 0)
           (list 10 8.08736 1.2954)
           (cons 40 0)
           (cons 41 0)
           (cons 42 0)
           (cons 91 0)
           (list 10 8.2296 1.247648)
           (cons 40 0)
           (cons 41 0)
           (cons 42 0)
           (cons 91 0)
           (list 10 8.2296 1.089152)
           (cons 40 0)
           (cons 41 0)
           (cons 42 0)
           (cons 91 0)
           (list 10 8.08736 1.0414)
           (cons 40 0)
           (cons 41 0)
           (cons 42 0)
           (cons 91 0)
           (list 10 7.35584 1.0414)
           (cons 40 0)
           (cons 41 0)
           (cons 42 0)
           (cons 91 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.2954)
           (cons 40 0)
           (cons 41 0)
           (cons 42 0)
           (cons 91 0)
           (list 10 7.7216 -1.2954)
           (cons 40 0)
           (cons 41 0)
           (cons 42 0)
           (cons 91 0)
           (list 10 7.7216 1.2954)
           (cons 40 0)
           (cons 41 0)
           (cons 42 0)
           (cons 91 0)
           (list 10 0 1.2954)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0.813816 0 0)
           (cons 50 0)
          )
         )
         (entmake
          (list
           (cons 0 "POINT")
           (cons 100 "AcDbEntity")
           (cons 67 0)
           (cons 8 "0")
           (cons 100 "AcDbPoint")
           (list 10 0.813816 1.2954 0)
           (cons 50 0)
          )
         )
         (entmake
          (list
           (cons 0 "POINT")
           (cons 100 "AcDbEntity")
           (cons 67 0)
           (cons 8 "0")
           (cons 100 "AcDbPoint")
           (list 10 0.813816 -1.2954 0)
           (cons 50 0)
          )
         )
         (entmake
          (list
           (cons 0 "POINT")
           (cons 100 "AcDbEntity")
           (cons 67 0)
           (cons 8 "0")
           (cons 100 "AcDbPoint")
           (list 10 7.0104 -1.2954 0)
           (cons 50 0)
          )
         )
         (entmake
          (list
           (cons 0 "POINT")
           (cons 100 "AcDbEntity")
           (cons 67 0)
           (cons 8 "0")
           (cons 100 "AcDbPoint")
           (list 10 7.0104 1.2954 0)
           (cons 50 0)
          )
         )
         (entmake
          (list
           (cons 0 "POINT")
           (cons 100 "AcDbEntity")
           (cons 67 0)
           (cons 8 "0")
           (cons 100 "AcDbPoint")
           (list 10 0 1.2954 0)
           (cons 50 0)
          )
         )
         (entmake
          (list
           (cons 0 "POINT")
           (cons 100 "AcDbEntity")
           (cons 67 0)
           (cons 8 "0")
           (cons 100 "AcDbPoint")
           (list 10 0 -1.2954 0)
           (cons 50 0)
          )
         )
         (entmake
          (list
           (cons 0 "POINT")
           (cons 100 "AcDbEntity")
           (cons 67 0)
           (cons 8 "0")
           (cons 100 "AcDbPoint")
           (list 10 7.0104 0 0)
           (cons 50 0)
          )
         )
         (entmake
          (list
           (cons 0 "ATTDEF")
           (cons 100 "AcDbEntity")
           (cons 67 0)
           (cons 8 "0")
           (cons 100 "AcDbText")
           (list 10 0.513816 0.56666667 0)
           (cons 40 0.2)
           (cons 1 "0.81")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.513816 0.23333333 0)
           (cons 40 0.2)
           (cons 1 "0.81")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.513816 -0.1 0)
           (cons 40 0.2)
           (cons 1 "7.01")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.513816 -0.43333333 0)
           (cons 40 0.2)
           (cons 1 "7.01")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.513816 -0.76666667 0)
           (cons 40 0.2)
           (cons 1 "16.8")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelLeftM2")
           (list 10 0.813816 -1.0414 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM2")
           (list 10 0.813816 1.0414 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "AB_INF-BUS"))
        (progn
         (entmake)
         (entmake
          (list
           (cons 0 "BLOCK")
           (cons 2 "AB_INF-BUS")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 12.1 -1.3)
           (cons 40 0)
           (cons 41 0)
           (cons 42 0)
           (cons 91 0)
           (list 10 12.1 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 12.1 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 12.1 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.892 -1.252248)
           (cons 40 0)
           (cons 41 0)
           (cons 42 0)
           (cons 91 0)
           (list 10 8.892 -1.093752)
           (cons 40 0)
           (cons 41 0)
           (cons 42 0)
           (cons 91 0)
           (list 10 9.03424 -1.046)
           (cons 40 0)
           (cons 41 0)
           (cons 42 0)
           (cons 91 0)
           (list 10 9.76576 -1.046)
           (cons 40 0)
           (cons 41 0)
           (cons 42 0)
           (cons 91 0)
           (list 10 9.908 -1.093752)
           (cons 40 0)
           (cons 41 0)
           (cons 42 0)
           (cons 91 0)
           (list 10 9.908 -1.252248)
           (cons 40 0)
           (cons 41 0)
           (cons 42 0)
           (cons 91 0)
           (list 10 9.76576 -1.3)
           (cons 40 0)
           (cons 41 0)
           (cons 42 0)
           (cons 91 0)
           (list 10 9.03424 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.892 1.093752)
           (cons 40 0)
           (cons 41 0)
           (cons 42 0)
           (cons 91 0)
           (list 10 8.892 1.252248)
           (cons 40 0)
           (cons 41 0)
           (cons 42 0)
           (cons 91 0)
           (list 10 9.03424 1.3)
           (cons 40 0)
           (cons 41 0)
           (cons 42 0)
           (cons 91 0)
           (list 10 9.76576 1.3)
           (cons 40 0)
           (cons 41 0)
           (cons 42 0)
           (cons 91 0)
           (list 10 9.908 1.252248)
           (cons 40 0)
           (cons 41 0)
           (cons 42 0)
           (cons 91 0)
           (list 10 9.908 1.093752)
           (cons 40 0)
           (cons 41 0)
           (cons 42 0)
           (cons 91 0)
           (list 10 9.76576 1.046)
           (cons 40 0)
           (cons 41 0)
           (cons 42 0)
           (cons 91 0)
           (list 10 9.03424 1.046)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 2.1 0 0)
           (cons 50 0)
          )
         )
         (entmake
          (list
           (cons 0 "INSERT")
           (cons 100 "AcDbEntity")
           (cons 67 0)
           (cons 8 "0")
           (cons 100 "AcDbBlockReference")
           (cons 2 "WheelLeftM2")
           (list 10 2.1 -1.046 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM2")
           (list 10 2.1 1.046 0)
           (cons 41 1)
           (cons 42 1)
           (cons 43 1)
           (cons 50 0)
           (cons 70 0)
           (cons 71 0)
           (cons 44 0)
           (cons 45 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 2.1 -1.3 0)
           (cons 50 0)
          )
         )
         (entmake
          (list
           (cons 0 "POINT")
           (cons 100 "AcDbEntity")
           (cons 67 0)
           (cons 8 "0")
           (cons 100 "AcDbPoint")
           (list 10 9.4 -1.3 0)
           (cons 50 0)
          )
         )
         (entmake
          (list
           (cons 0 "POINT")
           (cons 100 "AcDbEntity")
           (cons 67 0)
           (cons 8 "0")
           (cons 100 "AcDbPoint")
           (list 10 12.1 -1.3 0)
           (cons 50 0)
          )
         )
         (entmake
          (list
           (cons 0 "POINT")
           (cons 100 "AcDbEntity")
           (cons 67 0)
           (cons 8 "0")
           (cons 100 "AcDbPoint")
           (list 10 12.1 1.3 0)
           (cons 50 0)
          )
         )
         (entmake
          (list
           (cons 0 "POINT")
           (cons 100 "AcDbEntity")
           (cons 67 0)
           (cons 8 "0")
           (cons 100 "AcDbPoint")
           (list 10 9.4 1.3 0)
           (cons 50 0)
          )
         )
         (entmake
          (list
           (cons 0 "POINT")
           (cons 100 "AcDbEntity")
           (cons 67 0)
           (cons 8 "0")
           (cons 100 "AcDbPoint")
           (list 10 2.1 1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "ATTDEF")
           (cons 100 "AcDbEntity")
           (cons 67 0)
           (cons 8 "0")
           (cons 100 "AcDbText")
           (list 10 1.4 0.56666667 0)
           (cons 40 0.2)
           (cons 1 "2.100")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.4 0.23333333 0)
           (cons 40 0.2)
           (cons 1 "2.100")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.4 -0.1 0)
           (cons 40 0.2)
           (cons 1 "9.400")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.4 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.4 -0.76666667 0)
           (cons 40 0.2)
           (cons 1 "40.7")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-ABus-Rear"))
        (progn
         (entmake)
         (entmake
          (list
           (cons 0 "BLOCK")
           (cons 2 "AB_INF-ABus-Rear")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 5)
           (cons 70 129)
           (cons 43 0)
           (cons 38 0)
           (cons 39 0)
           (list 10 0 0)
           (cons 40 0)
           (cons 41 0)
           (cons 42 0)
           (cons 91 0)
           (list 10 0.6 -1.3)
           (cons 40 0)
           (cons 41 0)
           (cons 42 0)
           (cons 91 0)
           (list 10 8.7 -1.3)
           (cons 40 0)
           (cons 41 0)
           (cons 42 0)
           (cons 91 0)
           (list 10 8.7 1.3)
           (cons 40 0)
           (cons 41 0)
           (cons 42 0)
           (cons 91 0)
           (list 10 0.6 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0.6 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.7 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.7 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0.6 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0.6 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0.6 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 0.6 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.17333333)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.292 -1.252248)
           (cons 40 0)
           (cons 41 0)
           (cons 42 0)
           (cons 91 0)
           (list 10 5.292 -1.093752)
           (cons 40 0)
           (cons 41 0)
           (cons 42 0)
           (cons 91 0)
           (list 10 5.43424 -1.046)
           (cons 40 0)
           (cons 41 0)
           (cons 42 0)
           (cons 91 0)
           (list 10 6.16576 -1.046)
           (cons 40 0)
           (cons 41 0)
           (cons 42 0)
           (cons 91 0)
           (list 10 6.308 -1.093752)
           (cons 40 0)
           (cons 41 0)
           (cons 42 0)
           (cons 91 0)
           (list 10 6.308 -1.252248)
           (cons 40 0)
           (cons 41 0)
           (cons 42 0)
           (cons 91 0)
           (list 10 6.16576 -1.3)
           (cons 40 0)
           (cons 41 0)
           (cons 42 0)
           (cons 91 0)
           (list 10 5.43424 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.292 1.093752)
           (cons 40 0)
           (cons 41 0)
           (cons 42 0)
           (cons 91 0)
           (list 10 5.292 1.252248)
           (cons 40 0)
           (cons 41 0)
           (cons 42 0)
           (cons 91 0)
           (list 10 5.43424 1.3)
           (cons 40 0)
           (cons 41 0)
           (cons 42 0)
           (cons 91 0)
           (list 10 6.16576 1.3)
           (cons 40 0)
           (cons 41 0)
           (cons 42 0)
           (cons 91 0)
           (list 10 6.308 1.252248)
           (cons 40 0)
           (cons 41 0)
           (cons 42 0)
           (cons 91 0)
           (list 10 6.308 1.093752)
           (cons 40 0)
           (cons 41 0)
           (cons 42 0)
           (cons 91 0)
           (list 10 6.16576 1.046)
           (cons 40 0)
           (cons 41 0)
           (cons 42 0)
           (cons 91 0)
           (list 10 5.43424 1.046)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 0.6 -1.3 0)
           (cons 50 0)
          )
         )
         (entmake
          (list
           (cons 0 "POINT")
           (cons 100 "AcDbEntity")
           (cons 67 0)
           (cons 8 "0")
           (cons 100 "AcDbPoint")
           (list 10 0.6 1.3 0)
           (cons 50 0)
          )
         )
         (entmake
          (list
           (cons 0 "POINT")
           (cons 100 "AcDbEntity")
           (cons 67 0)
           (cons 8 "0")
           (cons 100 "AcDbPoint")
           (list 10 8.7 1.3 0)
           (cons 50 0)
          )
         )
         (entmake
          (list
           (cons 0 "POINT")
           (cons 100 "AcDbEntity")
           (cons 67 0)
           (cons 8 "0")
           (cons 100 "AcDbPoint")
           (list 10 8.7 -1.3 0)
           (cons 50 0)
          )
         )
         (entmake
          (list
           (cons 0 "POINT")
           (cons 100 "AcDbEntity")
           (cons 67 0)
           (cons 8 "0")
           (cons 100 "AcDbPoint")
           (list 10 5.8 -1.3 0)
           (cons 50 0)
          )
         )
         (entmake
          (list
           (cons 0 "POINT")
           (cons 100 "AcDbEntity")
           (cons 67 0)
           (cons 8 "0")
           (cons 100 "AcDbPoint")
           (list 10 5.8 1.3 0)
           (cons 50 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "5.800")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-ABus-Front"))
        (progn
         (entmake)
         (entmake
          (list
           (cons 0 "BLOCK")
           (cons 2 "AB_INF-ABus-Front")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 5)
           (cons 70 129)
           (cons 43 0)
           (cons 38 0)
           (cons 39 0)
           (list 10 0 -1.3)
           (cons 40 0)
           (cons 41 0)
           (cons 42 0)
           (cons 91 0)
           (list 10 9.1 -1.3)
           (cons 40 0)
           (cons 41 0)
           (cons 42 0)
           (cons 91 0)
           (list 10 9.7 0)
           (cons 40 0)
           (cons 41 0)
           (cons 42 0)
           (cons 91 0)
           (list 10 9.1 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.1 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.1 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 9.1 0 0)
           (list 11 9.7 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 9.7 0 0)
           (cons 40 0.1016)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.092 -1.252248)
           (cons 40 0)
           (cons 41 0)
           (cons 42 0)
           (cons 91 0)
           (list 10 7.092 -1.093752)
           (cons 40 0)
           (cons 41 0)
           (cons 42 0)
           (cons 91 0)
           (list 10 7.23424 -1.046)
           (cons 40 0)
           (cons 41 0)
           (cons 42 0)
           (cons 91 0)
           (list 10 7.96576 -1.046)
           (cons 40 0)
           (cons 41 0)
           (cons 42 0)
           (cons 91 0)
           (list 10 8.108 -1.093752)
           (cons 40 0)
           (cons 41 0)
           (cons 42 0)
           (cons 91 0)
           (list 10 8.108 -1.252248)
           (cons 40 0)
           (cons 41 0)
           (cons 42 0)
           (cons 91 0)
           (list 10 7.96576 -1.3)
           (cons 40 0)
           (cons 41 0)
           (cons 42 0)
           (cons 91 0)
           (list 10 7.23424 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.092 1.093752)
           (cons 40 0)
           (cons 41 0)
           (cons 42 0)
           (cons 91 0)
           (list 10 7.092 1.252248)
           (cons 40 0)
           (cons 41 0)
           (cons 42 0)
           (cons 91 0)
           (list 10 7.23424 1.3)
           (cons 40 0)
           (cons 41 0)
           (cons 42 0)
           (cons 91 0)
           (list 10 7.96576 1.3)
           (cons 40 0)
           (cons 41 0)
           (cons 42 0)
           (cons 91 0)
           (list 10 8.108 1.252248)
           (cons 40 0)
           (cons 41 0)
           (cons 42 0)
           (cons 91 0)
           (list 10 8.108 1.093752)
           (cons 40 0)
           (cons 41 0)
           (cons 42 0)
           (cons 91 0)
           (list 10 7.96576 1.046)
           (cons 40 0)
           (cons 41 0)
           (cons 42 0)
           (cons 91 0)
           (list 10 7.23424 1.046)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelRightM2")
           (list 10 2.5 1.046 0)
           (cons 41 1)
           (cons 42 1)
           (cons 43 1)
           (cons 50 0)
           (cons 70 0)
           (cons 71 0)
           (cons 44 0)
           (cons 45 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 9.1 -1.3 0)
           (cons 50 0)
          )
         )
         (entmake
          (list
           (cons 0 "POINT")
           (cons 100 "AcDbEntity")
           (cons 67 0)
           (cons 8 "0")
           (cons 100 "AcDbPoint")
           (list 10 9.1 1.3 0)
           (cons 50 0)
          )
         )
         (entmake
          (list
           (cons 0 "POINT")
           (cons 100 "AcDbEntity")
           (cons 67 0)
           (cons 8 "0")
           (cons 100 "AcDbPoint")
           (list 10 7.6 1.3 0)
           (cons 50 0)
          )
         )
         (entmake
          (list
           (cons 0 "POINT")
           (cons 100 "AcDbEntity")
           (cons 67 0)
           (cons 8 "0")
           (cons 100 "AcDbPoint")
           (list 10 7.6 -1.3 0)
           (cons 50 0)
          )
         )
         (entmake
          (list
           (cons 0 "POINT")
           (cons 100 "AcDbEntity")
           (cons 67 0)
           (cons 8 "0")
           (cons 100 "AcDbPoint")
           (list 10 2.5 -1.3 0)
           (cons 50 0)
          )
         )
         (entmake
          (list
           (cons 0 "POINT")
           (cons 100 "AcDbEntity")
           (cons 67 0)
           (cons 8 "0")
           (cons 100 "AcDbPoint")
           (list 10 2.5 1.3 0)
           (cons 50 0)
          )
         )
         (entmake
          (list
           (cons 0 "POINT")
           (cons 100 "AcDbEntity")
           (cons 67 0)
           (cons 8 "0")
           (cons 100 "AcDbPoint")
           (list 10 2.5 0.0127 0)
           (cons 50 0)
          )
         )
         (entmake
          (list
           (cons 0 "POINT")
           (cons 100 "AcDbEntity")
           (cons 67 0)
           (cons 8 "0")
           (cons 100 "AcDbPoint")
           (list 10 9.7 0 0)
           (cons 50 0)
          )
         )
         (entmake
          (list
           (cons 0 "ATTDEF")
           (cons 100 "AcDbEntity")
           (cons 67 0)
           (cons 8 "0")
           (cons 100 "AcDbText")
           (list 10 1.8 0.57936667 0)
           (cons 40 0.2)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.8 0.24603333 0)
           (cons 40 0.2)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.8 -0.0873 0)
           (cons 40 0.2)
           (cons 1 "7.600")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.8 -0.42063333 0)
           (cons 40 0.2)
           (cons 1 "9.700")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.8 -0.75396667 0)
           (cons 40 0.2)
           (cons 1 "27.500")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelLeftM2")
           (list 10 2.5 -1.046 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "AB_INF-5Axle-Trailer"))
        (progn
         (entmake)
         (entmake
          (list
           (cons 0 "BLOCK")
           (cons 2 "AB_INF-5Axle-Trailer")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.6)
           (cons 40 0)
           (cons 41 0)
           (cons 42 0)
           (cons 91 0)
           (list 10 26.45 -1.6)
           (cons 40 0)
           (cons 41 0)
           (cons 42 0)
           (cons 91 0)
           (list 10 26.45 1.6)
           (cons 40 0)
           (cons 41 0)
           (cons 42 0)
           (cons 91 0)
           (list 10 0 1.6)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.6 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 26.45 -1.6 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 26.45 1.6 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.6 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.6 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.6 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 3.1 0 0)
           (cons 40 0.104)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 15.491 -0.744548)
           (cons 40 0)
           (cons 41 0)
           (cons 42 0)
           (cons 91 0)
           (list 10 15.491 -0.570452)
           (cons 40 0)
           (cons 41 0)
           (cons 42 0)
           (cons 91 0)
           (list 10 15.64752 -0.518)
           (cons 40 0)
           (cons 41 0)
           (cons 42 0)
           (cons 91 0)
           (list 10 16.45248 -0.518)
           (cons 40 0)
           (cons 41 0)
           (cons 42 0)
           (cons 91 0)
           (list 10 16.609 -0.570452)
           (cons 40 0)
           (cons 41 0)
           (cons 42 0)
           (cons 91 0)
           (list 10 16.609 -0.744548)
           (cons 40 0)
           (cons 41 0)
           (cons 42 0)
           (cons 91 0)
           (list 10 16.45248 -0.797)
           (cons 40 0)
           (cons 41 0)
           (cons 42 0)
           (cons 91 0)
           (list 10 15.64752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 15.491 -1.247548)
           (cons 40 0)
           (cons 41 0)
           (cons 42 0)
           (cons 91 0)
           (list 10 15.491 -1.073452)
           (cons 40 0)
           (cons 41 0)
           (cons 42 0)
           (cons 91 0)
           (list 10 15.64752 -1.021)
           (cons 40 0)
           (cons 41 0)
           (cons 42 0)
           (cons 91 0)
           (list 10 16.45248 -1.021)
           (cons 40 0)
           (cons 41 0)
           (cons 42 0)
           (cons 91 0)
           (list 10 16.609 -1.073452)
           (cons 40 0)
           (cons 41 0)
           (cons 42 0)
           (cons 91 0)
           (list 10 16.609 -1.247548)
           (cons 40 0)
           (cons 41 0)
           (cons 42 0)
           (cons 91 0)
           (list 10 16.45248 -1.3)
           (cons 40 0)
           (cons 41 0)
           (cons 42 0)
           (cons 91 0)
           (list 10 15.64752 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 15.491 0.570452)
           (cons 40 0)
           (cons 41 0)
           (cons 42 0)
           (cons 91 0)
           (list 10 15.491 0.744548)
           (cons 40 0)
           (cons 41 0)
           (cons 42 0)
           (cons 91 0)
           (list 10 15.64752 0.797)
           (cons 40 0)
           (cons 41 0)
           (cons 42 0)
           (cons 91 0)
           (list 10 16.45248 0.797)
           (cons 40 0)
           (cons 41 0)
           (cons 42 0)
           (cons 91 0)
           (list 10 16.609 0.744548)
           (cons 40 0)
           (cons 41 0)
           (cons 42 0)
           (cons 91 0)
           (list 10 16.609 0.570452)
           (cons 40 0)
           (cons 41 0)
           (cons 42 0)
           (cons 91 0)
           (list 10 16.45248 0.518)
           (cons 40 0)
           (cons 41 0)
           (cons 42 0)
           (cons 91 0)
           (list 10 15.64752 0.518)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 15.491 1.073452)
           (cons 40 0)
           (cons 41 0)
           (cons 42 0)
           (cons 91 0)
           (list 10 15.491 1.247548)
           (cons 40 0)
           (cons 41 0)
           (cons 42 0)
           (cons 91 0)
           (list 10 15.64752 1.3)
           (cons 40 0)
           (cons 41 0)
           (cons 42 0)
           (cons 91 0)
           (list 10 16.45248 1.3)
           (cons 40 0)
           (cons 41 0)
           (cons 42 0)
           (cons 91 0)
           (list 10 16.609 1.247548)
           (cons 40 0)
           (cons 41 0)
           (cons 42 0)
           (cons 91 0)
           (list 10 16.609 1.073452)
           (cons 40 0)
           (cons 41 0)
           (cons 42 0)
           (cons 91 0)
           (list 10 16.45248 1.021)
           (cons 40 0)
           (cons 41 0)
           (cons 42 0)
           (cons 91 0)
           (list 10 15.64752 1.021)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 16.891 -0.744548)
           (cons 40 0)
           (cons 41 0)
           (cons 42 0)
           (cons 91 0)
           (list 10 16.891 -0.570452)
           (cons 40 0)
           (cons 41 0)
           (cons 42 0)
           (cons 91 0)
           (list 10 17.04752 -0.518)
           (cons 40 0)
           (cons 41 0)
           (cons 42 0)
           (cons 91 0)
           (list 10 17.85248 -0.518)
           (cons 40 0)
           (cons 41 0)
           (cons 42 0)
           (cons 91 0)
           (list 10 18.009 -0.570452)
           (cons 40 0)
           (cons 41 0)
           (cons 42 0)
           (cons 91 0)
           (list 10 18.009 -0.744548)
           (cons 40 0)
           (cons 41 0)
           (cons 42 0)
           (cons 91 0)
           (list 10 17.85248 -0.797)
           (cons 40 0)
           (cons 41 0)
           (cons 42 0)
           (cons 91 0)
           (list 10 17.04752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 16.891 -1.247548)
           (cons 40 0)
           (cons 41 0)
           (cons 42 0)
           (cons 91 0)
           (list 10 16.891 -1.073452)
           (cons 40 0)
           (cons 41 0)
           (cons 42 0)
           (cons 91 0)
           (list 10 17.04752 -1.021)
           (cons 40 0)
           (cons 41 0)
           (cons 42 0)
           (cons 91 0)
           (list 10 17.85248 -1.021)
           (cons 40 0)
           (cons 41 0)
           (cons 42 0)
           (cons 91 0)
           (list 10 18.009 -1.073452)
           (cons 40 0)
           (cons 41 0)
           (cons 42 0)
           (cons 91 0)
           (list 10 18.009 -1.247548)
           (cons 40 0)
           (cons 41 0)
           (cons 42 0)
           (cons 91 0)
           (list 10 17.85248 -1.3)
           (cons 40 0)
           (cons 41 0)
           (cons 42 0)
           (cons 91 0)
           (list 10 17.04752 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 16.891 0.570452)
           (cons 40 0)
           (cons 41 0)
           (cons 42 0)
           (cons 91 0)
           (list 10 16.891 0.744548)
           (cons 40 0)
           (cons 41 0)
           (cons 42 0)
           (cons 91 0)
           (list 10 17.04752 0.797)
           (cons 40 0)
           (cons 41 0)
           (cons 42 0)
           (cons 91 0)
           (list 10 17.85248 0.797)
           (cons 40 0)
           (cons 41 0)
           (cons 42 0)
           (cons 91 0)
           (list 10 18.009 0.744548)
           (cons 40 0)
           (cons 41 0)
           (cons 42 0)
           (cons 91 0)
           (list 10 18.009 0.570452)
           (cons 40 0)
           (cons 41 0)
           (cons 42 0)
           (cons 91 0)
           (list 10 17.85248 0.518)
           (cons 40 0)
           (cons 41 0)
           (cons 42 0)
           (cons 91 0)
           (list 10 17.04752 0.518)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 16.891 1.073452)
           (cons 40 0)
           (cons 41 0)
           (cons 42 0)
           (cons 91 0)
           (list 10 16.891 1.247548)
           (cons 40 0)
           (cons 41 0)
           (cons 42 0)
           (cons 91 0)
           (list 10 17.04752 1.3)
           (cons 40 0)
           (cons 41 0)
           (cons 42 0)
           (cons 91 0)
           (list 10 17.85248 1.3)
           (cons 40 0)
           (cons 41 0)
           (cons 42 0)
           (cons 91 0)
           (list 10 18.009 1.247548)
           (cons 40 0)
           (cons 41 0)
           (cons 42 0)
           (cons 91 0)
           (list 10 18.009 1.073452)
           (cons 40 0)
           (cons 41 0)
           (cons 42 0)
           (cons 91 0)
           (list 10 17.85248 1.021)
           (cons 40 0)
           (cons 41 0)
           (cons 42 0)
           (cons 91 0)
           (list 10 17.04752 1.021)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 1.6 0)
           (cons 50 0)
          )
         )
         (entmake
          (list
           (cons 0 "POINT")
           (cons 100 "AcDbEntity")
           (cons 67 0)
           (cons 8 "0")
           (cons 100 "AcDbPoint")
           (list 10 0 -1.6 0)
           (cons 50 0)
          )
         )
         (entmake
          (list
           (cons 0 "POINT")
           (cons 100 "AcDbEntity")
           (cons 67 0)
           (cons 8 "0")
           (cons 100 "AcDbPoint")
           (list 10 26.45 -1.6 0)
           (cons 50 0)
          )
         )
         (entmake
          (list
           (cons 0 "POINT")
           (cons 100 "AcDbEntity")
           (cons 67 0)
           (cons 8 "0")
           (cons 100 "AcDbPoint")
           (list 10 26.45 1.6 0)
           (cons 50 0)
          )
         )
         (entmake
          (list
           (cons 0 "POINT")
           (cons 100 "AcDbEntity")
           (cons 67 0)
           (cons 8 "0")
           (cons 100 "AcDbPoint")
           (list 10 3.1 0 0)
           (cons 50 0)
          )
         )
         (entmake
          (list
           (cons 0 "POINT")
           (cons 100 "AcDbEntity")
           (cons 67 0)
           (cons 8 "0")
           (cons 100 "AcDbPoint")
           (list 10 16.75 1.3 0)
           (cons 50 0)
          )
         )
         (entmake
          (list
           (cons 0 "POINT")
           (cons 100 "AcDbEntity")
           (cons 67 0)
           (cons 8 "0")
           (cons 100 "AcDbPoint")
           (list 10 16.75 -1.3 0)
           (cons 50 0)
          )
         )
         (entmake
          (list
           (cons 0 "ATTDEF")
           (cons 100 "AcDbEntity")
           (cons 67 0)
           (cons 8 "0")
           (cons 100 "AcDbText")
           (list 10 2.4 0.56666667 0)
           (cons 40 0.2)
           (cons 1 "3.100")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 2.4 0.23333333 0)
           (cons 40 0.2)
           (cons 1 "3.100")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 2.4 -0.1 0)
           (cons 40 0.2)
           (cons 1 "8.700")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 2.4 -0.43333333 0)
           (cons 40 0.2)
           (cons 1 "16.750")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 2.4 -0.76666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-5Axle-Truck"))
        (progn
         (entmake)
         (entmake
          (list
           (cons 0 "BLOCK")
           (cons 2 "AB_INF-5Axle-Truck")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 7.85 -1.3)
           (cons 40 0)
           (cons 41 0)
           (cons 42 0)
           (cons 91 0)
           (list 10 7.85 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.85 -0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.85 0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 7.15 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 7.41263966 -0.26263966 0)
           (list 11 7.41263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.891 -0.744548)
           (cons 40 0)
           (cons 41 0)
           (cons 42 0)
           (cons 91 0)
           (list 10 5.891 -0.570452)
           (cons 40 0)
           (cons 41 0)
           (cons 42 0)
           (cons 91 0)
           (list 10 6.04752 -0.518)
           (cons 40 0)
           (cons 41 0)
           (cons 42 0)
           (cons 91 0)
           (list 10 6.85248 -0.518)
           (cons 40 0)
           (cons 41 0)
           (cons 42 0)
           (cons 91 0)
           (list 10 7.009 -0.570452)
           (cons 40 0)
           (cons 41 0)
           (cons 42 0)
           (cons 91 0)
           (list 10 7.009 -0.744548)
           (cons 40 0)
           (cons 41 0)
           (cons 42 0)
           (cons 91 0)
           (list 10 6.85248 -0.797)
           (cons 40 0)
           (cons 41 0)
           (cons 42 0)
           (cons 91 0)
           (list 10 6.04752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.891 -1.247548)
           (cons 40 0)
           (cons 41 0)
           (cons 42 0)
           (cons 91 0)
           (list 10 5.891 -1.073452)
           (cons 40 0)
           (cons 41 0)
           (cons 42 0)
           (cons 91 0)
           (list 10 6.04752 -1.021)
           (cons 40 0)
           (cons 41 0)
           (cons 42 0)
           (cons 91 0)
           (list 10 6.85248 -1.021)
           (cons 40 0)
           (cons 41 0)
           (cons 42 0)
           (cons 91 0)
           (list 10 7.009 -1.073452)
           (cons 40 0)
           (cons 41 0)
           (cons 42 0)
           (cons 91 0)
           (list 10 7.009 -1.247548)
           (cons 40 0)
           (cons 41 0)
           (cons 42 0)
           (cons 91 0)
           (list 10 6.85248 -1.3)
           (cons 40 0)
           (cons 41 0)
           (cons 42 0)
           (cons 91 0)
           (list 10 6.04752 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.891 0.570452)
           (cons 40 0)
           (cons 41 0)
           (cons 42 0)
           (cons 91 0)
           (list 10 5.891 0.744548)
           (cons 40 0)
           (cons 41 0)
           (cons 42 0)
           (cons 91 0)
           (list 10 6.04752 0.797)
           (cons 40 0)
           (cons 41 0)
           (cons 42 0)
           (cons 91 0)
           (list 10 6.85248 0.797)
           (cons 40 0)
           (cons 41 0)
           (cons 42 0)
           (cons 91 0)
           (list 10 7.009 0.744548)
           (cons 40 0)
           (cons 41 0)
           (cons 42 0)
           (cons 91 0)
           (list 10 7.009 0.570452)
           (cons 40 0)
           (cons 41 0)
           (cons 42 0)
           (cons 91 0)
           (list 10 6.85248 0.518)
           (cons 40 0)
           (cons 41 0)
           (cons 42 0)
           (cons 91 0)
           (list 10 6.04752 0.518)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.891 1.073452)
           (cons 40 0)
           (cons 41 0)
           (cons 42 0)
           (cons 91 0)
           (list 10 5.891 1.247548)
           (cons 40 0)
           (cons 41 0)
           (cons 42 0)
           (cons 91 0)
           (list 10 6.04752 1.3)
           (cons 40 0)
           (cons 41 0)
           (cons 42 0)
           (cons 91 0)
           (list 10 6.85248 1.3)
           (cons 40 0)
           (cons 41 0)
           (cons 42 0)
           (cons 91 0)
           (list 10 7.009 1.247548)
           (cons 40 0)
           (cons 41 0)
           (cons 42 0)
           (cons 91 0)
           (list 10 7.009 1.073452)
           (cons 40 0)
           (cons 41 0)
           (cons 42 0)
           (cons 91 0)
           (list 10 6.85248 1.021)
           (cons 40 0)
           (cons 41 0)
           (cons 42 0)
           (cons 91 0)
           (list 10 6.04752 1.021)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.291 -0.744548)
           (cons 40 0)
           (cons 41 0)
           (cons 42 0)
           (cons 91 0)
           (list 10 7.291 -0.570452)
           (cons 40 0)
           (cons 41 0)
           (cons 42 0)
           (cons 91 0)
           (list 10 7.44752 -0.518)
           (cons 40 0)
           (cons 41 0)
           (cons 42 0)
           (cons 91 0)
           (list 10 8.25248 -0.518)
           (cons 40 0)
           (cons 41 0)
           (cons 42 0)
           (cons 91 0)
           (list 10 8.409 -0.570452)
           (cons 40 0)
           (cons 41 0)
           (cons 42 0)
           (cons 91 0)
           (list 10 8.409 -0.744548)
           (cons 40 0)
           (cons 41 0)
           (cons 42 0)
           (cons 91 0)
           (list 10 8.25248 -0.797)
           (cons 40 0)
           (cons 41 0)
           (cons 42 0)
           (cons 91 0)
           (list 10 7.44752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.291 -1.247548)
           (cons 40 0)
           (cons 41 0)
           (cons 42 0)
           (cons 91 0)
           (list 10 7.291 -1.073452)
           (cons 40 0)
           (cons 41 0)
           (cons 42 0)
           (cons 91 0)
           (list 10 7.44752 -1.021)
           (cons 40 0)
           (cons 41 0)
           (cons 42 0)
           (cons 91 0)
           (list 10 8.25248 -1.021)
           (cons 40 0)
           (cons 41 0)
           (cons 42 0)
           (cons 91 0)
           (list 10 8.409 -1.073452)
           (cons 40 0)
           (cons 41 0)
           (cons 42 0)
           (cons 91 0)
           (list 10 8.409 -1.247548)
           (cons 40 0)
           (cons 41 0)
           (cons 42 0)
           (cons 91 0)
           (list 10 8.25248 -1.3)
           (cons 40 0)
           (cons 41 0)
           (cons 42 0)
           (cons 91 0)
           (list 10 7.44752 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.291 0.570452)
           (cons 40 0)
           (cons 41 0)
           (cons 42 0)
           (cons 91 0)
           (list 10 7.291 0.744548)
           (cons 40 0)
           (cons 41 0)
           (cons 42 0)
           (cons 91 0)
           (list 10 7.44752 0.797)
           (cons 40 0)
           (cons 41 0)
           (cons 42 0)
           (cons 91 0)
           (list 10 8.25248 0.797)
           (cons 40 0)
           (cons 41 0)
           (cons 42 0)
           (cons 91 0)
           (list 10 8.409 0.744548)
           (cons 40 0)
           (cons 41 0)
           (cons 42 0)
           (cons 91 0)
           (list 10 8.409 0.570452)
           (cons 40 0)
           (cons 41 0)
           (cons 42 0)
           (cons 91 0)
           (list 10 8.25248 0.518)
           (cons 40 0)
           (cons 41 0)
           (cons 42 0)
           (cons 91 0)
           (list 10 7.44752 0.518)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.291 1.073452)
           (cons 40 0)
           (cons 41 0)
           (cons 42 0)
           (cons 91 0)
           (list 10 7.291 1.247548)
           (cons 40 0)
           (cons 41 0)
           (cons 42 0)
           (cons 91 0)
           (list 10 7.44752 1.3)
           (cons 40 0)
           (cons 41 0)
           (cons 42 0)
           (cons 91 0)
           (list 10 8.25248 1.3)
           (cons 40 0)
           (cons 41 0)
           (cons 42 0)
           (cons 91 0)
           (list 10 8.409 1.247548)
           (cons 40 0)
           (cons 41 0)
           (cons 42 0)
           (cons 91 0)
           (list 10 8.409 1.073452)
           (cons 40 0)
           (cons 41 0)
           (cons 42 0)
           (cons 91 0)
           (list 10 8.25248 1.021)
           (cons 40 0)
           (cons 41 0)
           (cons 42 0)
           (cons 91 0)
           (list 10 7.44752 1.021)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelLeftM1")
           (list 10 1 -1.021 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM1")
           (list 10 1 1.021 0)
           (cons 41 1)
           (cons 42 1)
           (cons 43 1)
           (cons 50 0)
           (cons 70 0)
           (cons 71 0)
           (cons 44 0)
           (cons 45 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 1 0 0)
           (cons 50 0)
          )
         )
         (entmake
          (list
           (cons 0 "POINT")
           (cons 100 "AcDbEntity")
           (cons 67 0)
           (cons 8 "0")
           (cons 100 "AcDbPoint")
           (list 10 7.15 0 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 7.15 1.3 0)
           (cons 50 0)
          )
         )
         (entmake
          (list
           (cons 0 "POINT")
           (cons 100 "AcDbEntity")
           (cons 67 0)
           (cons 8 "0")
           (cons 100 "AcDbPoint")
           (list 10 7.15 -1.3 0)
           (cons 50 0)
          )
         )
         (entmake
          (list
           (cons 0 "ATTDEF")
           (cons 100 "AcDbEntity")
           (cons 67 0)
           (cons 8 "0")
           (cons 100 "AcDbText")
           (list 10 0.3 0.56666667 0)
           (cons 40 0.2)
           (cons 1 "1.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 0.23333333 0)
           (cons 40 0.2)
           (cons 1 "1.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.1 0)
           (cons 40 0.2)
           (cons 1 "7.150")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.43333333 0)
           (cons 40 0.2)
           (cons 1 "7.150")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.76666667 0)
           (cons 40 0.2)
           (cons 1 "26.4")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "Special-19HeavyHaul-Pup4"))
        (progn
         (entmake)
         (entmake
          (list
           (cons 0 "BLOCK")
           (cons 2 "Special-19HeavyHaul-Pup4")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 11.5824 -0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 11.5824 0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.3048 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 6.096 0 0)
           (cons 40 0.16256)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.2804 -0.714248)
           (cons 40 0)
           (cons 41 0)
           (cons 42 0)
           (cons 91 0)
           (list 10 8.2804 -0.555752)
           (cons 40 0)
           (cons 41 0)
           (cons 42 0)
           (cons 91 0)
           (list 10 8.42264 -0.508)
           (cons 40 0)
           (cons 41 0)
           (cons 42 0)
           (cons 91 0)
           (list 10 9.15416 -0.508)
           (cons 40 0)
           (cons 41 0)
           (cons 42 0)
           (cons 91 0)
           (list 10 9.2964 -0.555752)
           (cons 40 0)
           (cons 41 0)
           (cons 42 0)
           (cons 91 0)
           (list 10 9.2964 -0.714248)
           (cons 40 0)
           (cons 41 0)
           (cons 42 0)
           (cons 91 0)
           (list 10 9.15416 -0.762)
           (cons 40 0)
           (cons 41 0)
           (cons 42 0)
           (cons 91 0)
           (list 10 8.42264 -0.762)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.2804 -1.171448)
           (cons 40 0)
           (cons 41 0)
           (cons 42 0)
           (cons 91 0)
           (list 10 8.2804 -1.012952)
           (cons 40 0)
           (cons 41 0)
           (cons 42 0)
           (cons 91 0)
           (list 10 8.42264 -0.9652)
           (cons 40 0)
           (cons 41 0)
           (cons 42 0)
           (cons 91 0)
           (list 10 9.15416 -0.9652)
           (cons 40 0)
           (cons 41 0)
           (cons 42 0)
           (cons 91 0)
           (list 10 9.2964 -1.012952)
           (cons 40 0)
           (cons 41 0)
           (cons 42 0)
           (cons 91 0)
           (list 10 9.2964 -1.171448)
           (cons 40 0)
           (cons 41 0)
           (cons 42 0)
           (cons 91 0)
           (list 10 9.15416 -1.2192)
           (cons 40 0)
           (cons 41 0)
           (cons 42 0)
           (cons 91 0)
           (list 10 8.42264 -1.2192)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.2804 0.555752)
           (cons 40 0)
           (cons 41 0)
           (cons 42 0)
           (cons 91 0)
           (list 10 8.2804 0.714248)
           (cons 40 0)
           (cons 41 0)
           (cons 42 0)
           (cons 91 0)
           (list 10 8.42264 0.762)
           (cons 40 0)
           (cons 41 0)
           (cons 42 0)
           (cons 91 0)
           (list 10 9.15416 0.762)
           (cons 40 0)
           (cons 41 0)
           (cons 42 0)
           (cons 91 0)
           (list 10 9.2964 0.714248)
           (cons 40 0)
           (cons 41 0)
           (cons 42 0)
           (cons 91 0)
           (list 10 9.2964 0.555752)
           (cons 40 0)
           (cons 41 0)
           (cons 42 0)
           (cons 91 0)
           (list 10 9.15416 0.508)
           (cons 40 0)
           (cons 41 0)
           (cons 42 0)
           (cons 91 0)
           (list 10 8.42264 0.508)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.2804 1.012952)
           (cons 40 0)
           (cons 41 0)
           (cons 42 0)
           (cons 91 0)
           (list 10 8.2804 1.171448)
           (cons 40 0)
           (cons 41 0)
           (cons 42 0)
           (cons 91 0)
           (list 10 8.42264 1.2192)
           (cons 40 0)
           (cons 41 0)
           (cons 42 0)
           (cons 91 0)
           (list 10 9.15416 1.2192)
           (cons 40 0)
           (cons 41 0)
           (cons 42 0)
           (cons 91 0)
           (list 10 9.2964 1.171448)
           (cons 40 0)
           (cons 41 0)
           (cons 42 0)
           (cons 91 0)
           (list 10 9.2964 1.012952)
           (cons 40 0)
           (cons 41 0)
           (cons 42 0)
           (cons 91 0)
           (list 10 9.15416 0.9652)
           (cons 40 0)
           (cons 41 0)
           (cons 42 0)
           (cons 91 0)
           (list 10 8.42264 0.9652)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.5504 -0.714248)
           (cons 40 0)
           (cons 41 0)
           (cons 42 0)
           (cons 91 0)
           (list 10 9.5504 -0.555752)
           (cons 40 0)
           (cons 41 0)
           (cons 42 0)
           (cons 91 0)
           (list 10 9.69264 -0.508)
           (cons 40 0)
           (cons 41 0)
           (cons 42 0)
           (cons 91 0)
           (list 10 10.42416 -0.508)
           (cons 40 0)
           (cons 41 0)
           (cons 42 0)
           (cons 91 0)
           (list 10 10.5664 -0.555752)
           (cons 40 0)
           (cons 41 0)
           (cons 42 0)
           (cons 91 0)
           (list 10 10.5664 -0.714248)
           (cons 40 0)
           (cons 41 0)
           (cons 42 0)
           (cons 91 0)
           (list 10 10.42416 -0.762)
           (cons 40 0)
           (cons 41 0)
           (cons 42 0)
           (cons 91 0)
           (list 10 9.69264 -0.762)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.5504 -1.171448)
           (cons 40 0)
           (cons 41 0)
           (cons 42 0)
           (cons 91 0)
           (list 10 9.5504 -1.012952)
           (cons 40 0)
           (cons 41 0)
           (cons 42 0)
           (cons 91 0)
           (list 10 9.69264 -0.9652)
           (cons 40 0)
           (cons 41 0)
           (cons 42 0)
           (cons 91 0)
           (list 10 10.42416 -0.9652)
           (cons 40 0)
           (cons 41 0)
           (cons 42 0)
           (cons 91 0)
           (list 10 10.5664 -1.012952)
           (cons 40 0)
           (cons 41 0)
           (cons 42 0)
           (cons 91 0)
           (list 10 10.5664 -1.171448)
           (cons 40 0)
           (cons 41 0)
           (cons 42 0)
           (cons 91 0)
           (list 10 10.42416 -1.2192)
           (cons 40 0)
           (cons 41 0)
           (cons 42 0)
           (cons 91 0)
           (list 10 9.69264 -1.2192)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.5504 0.555752)
           (cons 40 0)
           (cons 41 0)
           (cons 42 0)
           (cons 91 0)
           (list 10 9.5504 0.714248)
           (cons 40 0)
           (cons 41 0)
           (cons 42 0)
           (cons 91 0)
           (list 10 9.69264 0.762)
           (cons 40 0)
           (cons 41 0)
           (cons 42 0)
           (cons 91 0)
           (list 10 10.42416 0.762)
           (cons 40 0)
           (cons 41 0)
           (cons 42 0)
           (cons 91 0)
           (list 10 10.5664 0.714248)
           (cons 40 0)
           (cons 41 0)
           (cons 42 0)
           (cons 91 0)
           (list 10 10.5664 0.555752)
           (cons 40 0)
           (cons 41 0)
           (cons 42 0)
           (cons 91 0)
           (list 10 10.42416 0.508)
           (cons 40 0)
           (cons 41 0)
           (cons 42 0)
           (cons 91 0)
           (list 10 9.69264 0.508)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.5504 1.012952)
           (cons 40 0)
           (cons 41 0)
           (cons 42 0)
           (cons 91 0)
           (list 10 9.5504 1.171448)
           (cons 40 0)
           (cons 41 0)
           (cons 42 0)
           (cons 91 0)
           (list 10 9.69264 1.2192)
           (cons 40 0)
           (cons 41 0)
           (cons 42 0)
           (cons 91 0)
           (list 10 10.42416 1.2192)
           (cons 40 0)
           (cons 41 0)
           (cons 42 0)
           (cons 91 0)
           (list 10 10.5664 1.171448)
           (cons 40 0)
           (cons 41 0)
           (cons 42 0)
           (cons 91 0)
           (list 10 10.5664 1.012952)
           (cons 40 0)
           (cons 41 0)
           (cons 42 0)
           (cons 91 0)
           (list 10 10.42416 0.9652)
           (cons 40 0)
           (cons 41 0)
           (cons 42 0)
           (cons 91 0)
           (list 10 9.69264 0.9652)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.8204 -0.714248)
           (cons 40 0)
           (cons 41 0)
           (cons 42 0)
           (cons 91 0)
           (list 10 10.8204 -0.555752)
           (cons 40 0)
           (cons 41 0)
           (cons 42 0)
           (cons 91 0)
           (list 10 10.96264 -0.508)
           (cons 40 0)
           (cons 41 0)
           (cons 42 0)
           (cons 91 0)
           (list 10 11.69416 -0.508)
           (cons 40 0)
           (cons 41 0)
           (cons 42 0)
           (cons 91 0)
           (list 10 11.8364 -0.555752)
           (cons 40 0)
           (cons 41 0)
           (cons 42 0)
           (cons 91 0)
           (list 10 11.8364 -0.714248)
           (cons 40 0)
           (cons 41 0)
           (cons 42 0)
           (cons 91 0)
           (list 10 11.69416 -0.762)
           (cons 40 0)
           (cons 41 0)
           (cons 42 0)
           (cons 91 0)
           (list 10 10.96264 -0.762)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.8204 -1.171448)
           (cons 40 0)
           (cons 41 0)
           (cons 42 0)
           (cons 91 0)
           (list 10 10.8204 -1.012952)
           (cons 40 0)
           (cons 41 0)
           (cons 42 0)
           (cons 91 0)
           (list 10 10.96264 -0.9652)
           (cons 40 0)
           (cons 41 0)
           (cons 42 0)
           (cons 91 0)
           (list 10 11.69416 -0.9652)
           (cons 40 0)
           (cons 41 0)
           (cons 42 0)
           (cons 91 0)
           (list 10 11.8364 -1.012952)
           (cons 40 0)
           (cons 41 0)
           (cons 42 0)
           (cons 91 0)
           (list 10 11.8364 -1.171448)
           (cons 40 0)
           (cons 41 0)
           (cons 42 0)
           (cons 91 0)
           (list 10 11.69416 -1.2192)
           (cons 40 0)
           (cons 41 0)
           (cons 42 0)
           (cons 91 0)
           (list 10 10.96264 -1.2192)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.8204 0.555752)
           (cons 40 0)
           (cons 41 0)
           (cons 42 0)
           (cons 91 0)
           (list 10 10.8204 0.714248)
           (cons 40 0)
           (cons 41 0)
           (cons 42 0)
           (cons 91 0)
           (list 10 10.96264 0.762)
           (cons 40 0)
           (cons 41 0)
           (cons 42 0)
           (cons 91 0)
           (list 10 11.69416 0.762)
           (cons 40 0)
           (cons 41 0)
           (cons 42 0)
           (cons 91 0)
           (list 10 11.8364 0.714248)
           (cons 40 0)
           (cons 41 0)
           (cons 42 0)
           (cons 91 0)
           (list 10 11.8364 0.555752)
           (cons 40 0)
           (cons 41 0)
           (cons 42 0)
           (cons 91 0)
           (list 10 11.69416 0.508)
           (cons 40 0)
           (cons 41 0)
           (cons 42 0)
           (cons 91 0)
           (list 10 10.96264 0.508)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.8204 1.012952)
           (cons 40 0)
           (cons 41 0)
           (cons 42 0)
           (cons 91 0)
           (list 10 10.8204 1.171448)
           (cons 40 0)
           (cons 41 0)
           (cons 42 0)
           (cons 91 0)
           (list 10 10.96264 1.2192)
           (cons 40 0)
           (cons 41 0)
           (cons 42 0)
           (cons 91 0)
           (list 10 11.69416 1.2192)
           (cons 40 0)
           (cons 41 0)
           (cons 42 0)
           (cons 91 0)
           (list 10 11.8364 1.171448)
           (cons 40 0)
           (cons 41 0)
           (cons 42 0)
           (cons 91 0)
           (list 10 11.8364 1.012952)
           (cons 40 0)
           (cons 41 0)
           (cons 42 0)
           (cons 91 0)
           (list 10 11.69416 0.9652)
           (cons 40 0)
           (cons 41 0)
           (cons 42 0)
           (cons 91 0)
           (list 10 10.96264 0.9652)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 1.524 1.2192 0)
           (cons 50 0)
          )
         )
         (entmake
          (list
           (cons 0 "POINT")
           (cons 100 "AcDbEntity")
           (cons 67 0)
           (cons 8 "0")
           (cons 100 "AcDbPoint")
           (list 10 1.524 -1.2192 0)
           (cons 50 0)
          )
         )
         (entmake
          (list
           (cons 0 "POINT")
           (cons 100 "AcDbEntity")
           (cons 67 0)
           (cons 8 "0")
           (cons 100 "AcDbPoint")
           (list 10 10.0584 -1.2192 0)
           (cons 50 0)
          )
         )
         (entmake
          (list
           (cons 0 "POINT")
           (cons 100 "AcDbEntity")
           (cons 67 0)
           (cons 8 "0")
           (cons 100 "AcDbPoint")
           (list 10 10.0584 1.2192 0)
           (cons 50 0)
          )
         )
         (entmake
          (list
           (cons 0 "POINT")
           (cons 100 "AcDbEntity")
           (cons 67 0)
           (cons 8 "0")
           (cons 62 3)
           (cons 100 "AcDbPoint")
           (list 10 6.096 0 0)
           (cons 50 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "6.10")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "1.52")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "10.05")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "TEXT")
           (cons 100 "AcDbEntity")
           (cons 67 0)
           (cons 8 "0")
           (cons 100 "AcDbText")
           (list 10 6.9412381 -0.25 0)
           (cons 40 0.5)
           (cons 1 "6")
           (cons 50 0)
           (cons 41 1)
           (cons 51 0)
           (cons 7 "Standard")
           (cons 71 0)
           (cons 72 4)
           (list 11 7.096 0 0)
           (cons 100 "AcDbText")
           (cons 73 0)
          )
         )
         (entmake
          (list
           (cons 0 "LWPOLYLINE")
           (cons 100 "AcDbEntity")
           (cons 67 0)
           (cons 8 "Defpoints")
           (cons 100 "AcDbPolyline")
           (cons 90 12)
           (cons 70 129)
           (cons 43 0)
           (cons 38 0)
           (cons 39 0)
           (list 10 8.2804 1.2192)
           (cons 40 0)
           (cons 41 0)
           (cons 42 0)
           (cons 91 0)
           (list 10 11.8364 1.2192)
           (cons 40 0)
           (cons 41 0)
           (cons 42 0)
           (cons 91 0)
           (list 10 11.8364 -1.2192)
           (cons 40 0)
           (cons 41 0)
           (cons 42 0)
           (cons 91 0)
           (list 10 8.2804 -1.2192)
           (cons 40 0)
           (cons 41 0)
           (cons 42 0)
           (cons 91 0)
           (list 10 8.2804 -0.3048)
           (cons 40 0)
           (cons 41 0)
           (cons 42 0)
           (cons 91 0)
           (list 10 3.302 -0.3048)
           (cons 40 0)
           (cons 41 0)
           (cons 42 0)
           (cons 91 0)
           (list 10 3.302 -1.2192)
           (cons 40 0)
           (cons 41 0)
           (cons 42 0)
           (cons 91 0)
           (list 10 -0.254 -1.2192)
           (cons 40 0)
           (cons 41 0)
           (cons 42 0)
           (cons 91 0)
           (list 10 -0.254 1.2192)
           (cons 40 0)
           (cons 41 0)
           (cons 42 0)
           (cons 91 0)
           (list 10 3.302 1.2192)
           (cons 40 0)
           (cons 41 0)
           (cons 42 0)
           (cons 91 0)
           (list 10 3.302 0.3048)
           (cons 40 0)
           (cons 41 0)
           (cons 42 0)
           (cons 91 0)
           (list 10 8.2804 0.3048)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelLeftM6")
           (list 10 0.254 -0.508 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM6")
           (list 10 1.524 -0.508 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM6")
           (list 10 2.794 -0.508 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM6")
           (list 10 0.254 0.508 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM6")
           (list 10 1.524 0.508 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM6")
           (list 10 2.794 0.508 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "Special-19HeavyHaul-Pup3"))
        (progn
         (entmake)
         (entmake
          (list
           (cons 0 "BLOCK")
           (cons 2 "Special-19HeavyHaul-Pup3")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 13.1064 -0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 13.1064 0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.3048 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 3.9624 0 0)
           (cons 40 0.16256)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.8044 -0.714248)
           (cons 40 0)
           (cons 41 0)
           (cons 42 0)
           (cons 91 0)
           (list 10 9.8044 -0.555752)
           (cons 40 0)
           (cons 41 0)
           (cons 42 0)
           (cons 91 0)
           (list 10 9.94664 -0.508)
           (cons 40 0)
           (cons 41 0)
           (cons 42 0)
           (cons 91 0)
           (list 10 10.67816 -0.508)
           (cons 40 0)
           (cons 41 0)
           (cons 42 0)
           (cons 91 0)
           (list 10 10.8204 -0.555752)
           (cons 40 0)
           (cons 41 0)
           (cons 42 0)
           (cons 91 0)
           (list 10 10.8204 -0.714248)
           (cons 40 0)
           (cons 41 0)
           (cons 42 0)
           (cons 91 0)
           (list 10 10.67816 -0.762)
           (cons 40 0)
           (cons 41 0)
           (cons 42 0)
           (cons 91 0)
           (list 10 9.94664 -0.762)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.8044 -1.171448)
           (cons 40 0)
           (cons 41 0)
           (cons 42 0)
           (cons 91 0)
           (list 10 9.8044 -1.012952)
           (cons 40 0)
           (cons 41 0)
           (cons 42 0)
           (cons 91 0)
           (list 10 9.94664 -0.9652)
           (cons 40 0)
           (cons 41 0)
           (cons 42 0)
           (cons 91 0)
           (list 10 10.67816 -0.9652)
           (cons 40 0)
           (cons 41 0)
           (cons 42 0)
           (cons 91 0)
           (list 10 10.8204 -1.012952)
           (cons 40 0)
           (cons 41 0)
           (cons 42 0)
           (cons 91 0)
           (list 10 10.8204 -1.171448)
           (cons 40 0)
           (cons 41 0)
           (cons 42 0)
           (cons 91 0)
           (list 10 10.67816 -1.2192)
           (cons 40 0)
           (cons 41 0)
           (cons 42 0)
           (cons 91 0)
           (list 10 9.94664 -1.2192)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.8044 0.555752)
           (cons 40 0)
           (cons 41 0)
           (cons 42 0)
           (cons 91 0)
           (list 10 9.8044 0.714248)
           (cons 40 0)
           (cons 41 0)
           (cons 42 0)
           (cons 91 0)
           (list 10 9.94664 0.762)
           (cons 40 0)
           (cons 41 0)
           (cons 42 0)
           (cons 91 0)
           (list 10 10.67816 0.762)
           (cons 40 0)
           (cons 41 0)
           (cons 42 0)
           (cons 91 0)
           (list 10 10.8204 0.714248)
           (cons 40 0)
           (cons 41 0)
           (cons 42 0)
           (cons 91 0)
           (list 10 10.8204 0.555752)
           (cons 40 0)
           (cons 41 0)
           (cons 42 0)
           (cons 91 0)
           (list 10 10.67816 0.508)
           (cons 40 0)
           (cons 41 0)
           (cons 42 0)
           (cons 91 0)
           (list 10 9.94664 0.508)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.8044 1.012952)
           (cons 40 0)
           (cons 41 0)
           (cons 42 0)
           (cons 91 0)
           (list 10 9.8044 1.171448)
           (cons 40 0)
           (cons 41 0)
           (cons 42 0)
           (cons 91 0)
           (list 10 9.94664 1.2192)
           (cons 40 0)
           (cons 41 0)
           (cons 42 0)
           (cons 91 0)
           (list 10 10.67816 1.2192)
           (cons 40 0)
           (cons 41 0)
           (cons 42 0)
           (cons 91 0)
           (list 10 10.8204 1.171448)
           (cons 40 0)
           (cons 41 0)
           (cons 42 0)
           (cons 91 0)
           (list 10 10.8204 1.012952)
           (cons 40 0)
           (cons 41 0)
           (cons 42 0)
           (cons 91 0)
           (list 10 10.67816 0.9652)
           (cons 40 0)
           (cons 41 0)
           (cons 42 0)
           (cons 91 0)
           (list 10 9.94664 0.9652)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.0744 -0.714248)
           (cons 40 0)
           (cons 41 0)
           (cons 42 0)
           (cons 91 0)
           (list 10 11.0744 -0.555752)
           (cons 40 0)
           (cons 41 0)
           (cons 42 0)
           (cons 91 0)
           (list 10 11.21664 -0.508)
           (cons 40 0)
           (cons 41 0)
           (cons 42 0)
           (cons 91 0)
           (list 10 11.94816 -0.508)
           (cons 40 0)
           (cons 41 0)
           (cons 42 0)
           (cons 91 0)
           (list 10 12.0904 -0.555752)
           (cons 40 0)
           (cons 41 0)
           (cons 42 0)
           (cons 91 0)
           (list 10 12.0904 -0.714248)
           (cons 40 0)
           (cons 41 0)
           (cons 42 0)
           (cons 91 0)
           (list 10 11.94816 -0.762)
           (cons 40 0)
           (cons 41 0)
           (cons 42 0)
           (cons 91 0)
           (list 10 11.21664 -0.762)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.0744 -1.171448)
           (cons 40 0)
           (cons 41 0)
           (cons 42 0)
           (cons 91 0)
           (list 10 11.0744 -1.012952)
           (cons 40 0)
           (cons 41 0)
           (cons 42 0)
           (cons 91 0)
           (list 10 11.21664 -0.9652)
           (cons 40 0)
           (cons 41 0)
           (cons 42 0)
           (cons 91 0)
           (list 10 11.94816 -0.9652)
           (cons 40 0)
           (cons 41 0)
           (cons 42 0)
           (cons 91 0)
           (list 10 12.0904 -1.012952)
           (cons 40 0)
           (cons 41 0)
           (cons 42 0)
           (cons 91 0)
           (list 10 12.0904 -1.171448)
           (cons 40 0)
           (cons 41 0)
           (cons 42 0)
           (cons 91 0)
           (list 10 11.94816 -1.2192)
           (cons 40 0)
           (cons 41 0)
           (cons 42 0)
           (cons 91 0)
           (list 10 11.21664 -1.2192)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.0744 0.555752)
           (cons 40 0)
           (cons 41 0)
           (cons 42 0)
           (cons 91 0)
           (list 10 11.0744 0.714248)
           (cons 40 0)
           (cons 41 0)
           (cons 42 0)
           (cons 91 0)
           (list 10 11.21664 0.762)
           (cons 40 0)
           (cons 41 0)
           (cons 42 0)
           (cons 91 0)
           (list 10 11.94816 0.762)
           (cons 40 0)
           (cons 41 0)
           (cons 42 0)
           (cons 91 0)
           (list 10 12.0904 0.714248)
           (cons 40 0)
           (cons 41 0)
           (cons 42 0)
           (cons 91 0)
           (list 10 12.0904 0.555752)
           (cons 40 0)
           (cons 41 0)
           (cons 42 0)
           (cons 91 0)
           (list 10 11.94816 0.508)
           (cons 40 0)
           (cons 41 0)
           (cons 42 0)
           (cons 91 0)
           (list 10 11.21664 0.508)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.0744 1.012952)
           (cons 40 0)
           (cons 41 0)
           (cons 42 0)
           (cons 91 0)
           (list 10 11.0744 1.171448)
           (cons 40 0)
           (cons 41 0)
           (cons 42 0)
           (cons 91 0)
           (list 10 11.21664 1.2192)
           (cons 40 0)
           (cons 41 0)
           (cons 42 0)
           (cons 91 0)
           (list 10 11.94816 1.2192)
           (cons 40 0)
           (cons 41 0)
           (cons 42 0)
           (cons 91 0)
           (list 10 12.0904 1.171448)
           (cons 40 0)
           (cons 41 0)
           (cons 42 0)
           (cons 91 0)
           (list 10 12.0904 1.012952)
           (cons 40 0)
           (cons 41 0)
           (cons 42 0)
           (cons 91 0)
           (list 10 11.94816 0.9652)
           (cons 40 0)
           (cons 41 0)
           (cons 42 0)
           (cons 91 0)
           (list 10 11.21664 0.9652)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.3444 -0.714248)
           (cons 40 0)
           (cons 41 0)
           (cons 42 0)
           (cons 91 0)
           (list 10 12.3444 -0.555752)
           (cons 40 0)
           (cons 41 0)
           (cons 42 0)
           (cons 91 0)
           (list 10 12.48664 -0.508)
           (cons 40 0)
           (cons 41 0)
           (cons 42 0)
           (cons 91 0)
           (list 10 13.21816 -0.508)
           (cons 40 0)
           (cons 41 0)
           (cons 42 0)
           (cons 91 0)
           (list 10 13.3604 -0.555752)
           (cons 40 0)
           (cons 41 0)
           (cons 42 0)
           (cons 91 0)
           (list 10 13.3604 -0.714248)
           (cons 40 0)
           (cons 41 0)
           (cons 42 0)
           (cons 91 0)
           (list 10 13.21816 -0.762)
           (cons 40 0)
           (cons 41 0)
           (cons 42 0)
           (cons 91 0)
           (list 10 12.48664 -0.762)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.3444 -1.171448)
           (cons 40 0)
           (cons 41 0)
           (cons 42 0)
           (cons 91 0)
           (list 10 12.3444 -1.012952)
           (cons 40 0)
           (cons 41 0)
           (cons 42 0)
           (cons 91 0)
           (list 10 12.48664 -0.9652)
           (cons 40 0)
           (cons 41 0)
           (cons 42 0)
           (cons 91 0)
           (list 10 13.21816 -0.9652)
           (cons 40 0)
           (cons 41 0)
           (cons 42 0)
           (cons 91 0)
           (list 10 13.3604 -1.012952)
           (cons 40 0)
           (cons 41 0)
           (cons 42 0)
           (cons 91 0)
           (list 10 13.3604 -1.171448)
           (cons 40 0)
           (cons 41 0)
           (cons 42 0)
           (cons 91 0)
           (list 10 13.21816 -1.2192)
           (cons 40 0)
           (cons 41 0)
           (cons 42 0)
           (cons 91 0)
           (list 10 12.48664 -1.2192)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.3444 0.555752)
           (cons 40 0)
           (cons 41 0)
           (cons 42 0)
           (cons 91 0)
           (list 10 12.3444 0.714248)
           (cons 40 0)
           (cons 41 0)
           (cons 42 0)
           (cons 91 0)
           (list 10 12.48664 0.762)
           (cons 40 0)
           (cons 41 0)
           (cons 42 0)
           (cons 91 0)
           (list 10 13.21816 0.762)
           (cons 40 0)
           (cons 41 0)
           (cons 42 0)
           (cons 91 0)
           (list 10 13.3604 0.714248)
           (cons 40 0)
           (cons 41 0)
           (cons 42 0)
           (cons 91 0)
           (list 10 13.3604 0.555752)
           (cons 40 0)
           (cons 41 0)
           (cons 42 0)
           (cons 91 0)
           (list 10 13.21816 0.508)
           (cons 40 0)
           (cons 41 0)
           (cons 42 0)
           (cons 91 0)
           (list 10 12.48664 0.508)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.3444 1.012952)
           (cons 40 0)
           (cons 41 0)
           (cons 42 0)
           (cons 91 0)
           (list 10 12.3444 1.171448)
           (cons 40 0)
           (cons 41 0)
           (cons 42 0)
           (cons 91 0)
           (list 10 12.48664 1.2192)
           (cons 40 0)
           (cons 41 0)
           (cons 42 0)
           (cons 91 0)
           (list 10 13.21816 1.2192)
           (cons 40 0)
           (cons 41 0)
           (cons 42 0)
           (cons 91 0)
           (list 10 13.3604 1.171448)
           (cons 40 0)
           (cons 41 0)
           (cons 42 0)
           (cons 91 0)
           (list 10 13.3604 1.012952)
           (cons 40 0)
           (cons 41 0)
           (cons 42 0)
           (cons 91 0)
           (list 10 13.21816 0.9652)
           (cons 40 0)
           (cons 41 0)
           (cons 42 0)
           (cons 91 0)
           (list 10 12.48664 0.9652)
           (cons 40 0)
           (cons 41 0)
           (cons 42 0)
           (cons 91 0)
          )
         )
         (entmake
          (list
           (cons 0 "POINT")
           (cons 100 "AcDbEntity")
           (cons 67 0)
           (cons 8 "0")
           (cons 62 3)
           (cons 100 "AcDbPoint")
           (list 10 3.9624 0 0)
           (cons 50 0)
          )
         )
         (entmake
          (list
           (cons 0 "POINT")
           (cons 100 "AcDbEntity")
           (cons 67 0)
           (cons 8 "0")
           (cons 100 "AcDbPoint")
           (list 10 11.5824 1.2192 0)
           (cons 50 0)
          )
         )
         (entmake
          (list
           (cons 0 "POINT")
           (cons 100 "AcDbEntity")
           (cons 67 0)
           (cons 8 "0")
           (cons 100 "AcDbPoint")
           (list 10 11.5824 -1.2192 0)
           (cons 50 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "3.96")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "3.96")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "11.58")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "0.0001")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "POINT")
           (cons 100 "AcDbEntity")
           (cons 67 0)
           (cons 8 "0")
           (cons 62 1)
           (cons 100 "AcDbPoint")
           (list 10 0 0 0)
           (cons 50 0)
          )
         )
         (entmake
          (list
           (cons 0 "TEXT")
           (cons 100 "AcDbEntity")
           (cons 67 0)
           (cons 8 "0")
           (cons 100 "AcDbText")
           (list 10 4.79573333 -0.25 0)
           (cons 40 0.5)
           (cons 1 "5")
           (cons 50 0)
           (cons 41 1)
           (cons 51 0)
           (cons 7 "Standard")
           (cons 71 0)
           (cons 72 4)
           (list 11 4.9624 0 0)
           (cons 100 "AcDbText")
           (cons 73 0)
          )
         )
         (entmake
          (list
           (cons 0 "LWPOLYLINE")
           (cons 100 "AcDbEntity")
           (cons 67 0)
           (cons 8 "Defpoints")
           (cons 100 "AcDbPolyline")
           (cons 90 8)
           (cons 70 129)
           (cons 43 0)
           (cons 38 0)
           (cons 39 0)
           (list 10 9.8044 1.2192)
           (cons 40 0)
           (cons 41 0)
           (cons 42 0)
           (cons 91 0)
           (list 10 13.3604 1.2192)
           (cons 40 0)
           (cons 41 0)
           (cons 42 0)
           (cons 91 0)
           (list 10 13.3604 -1.2192)
           (cons 40 0)
           (cons 41 0)
           (cons 42 0)
           (cons 91 0)
           (list 10 9.8044 -1.2192)
           (cons 40 0)
           (cons 41 0)
           (cons 42 0)
           (cons 91 0)
           (list 10 9.8044 -0.3048)
           (cons 40 0)
           (cons 41 0)
           (cons 42 0)
           (cons 91 0)
           (list 10 0 -0.3048)
           (cons 40 0)
           (cons 41 0)
           (cons 42 0)
           (cons 91 0)
           (list 10 0 0.3048)
           (cons 40 0)
           (cons 41 0)
           (cons 42 0)
           (cons 91 0)
           (list 10 9.8044 0.3048)
           (cons 40 0)
           (cons 41 0)
           (cons 42 0)
           (cons 91 0)
          )
         )
         (entmake (list (cons 0 "ENDBLK")))
        )
       )
       ((= (strcase BLKNAME) (strcase "Special-19HeavyHaul-Trailer"))
        (progn
         (entmake)
         (entmake
          (list
           (cons 0 "BLOCK")
           (cons 2 "Special-19HeavyHaul-Trailer")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.8288 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 35.9664 -1.8288 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 35.9664 1.8288 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.8288 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.8288 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.8288 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "POINT")
           (cons 100 "AcDbEntity")
           (cons 67 0)
           (cons 8 "0")
           (cons 100 "AcDbPoint")
           (list 10 18.288 0 0)
           (cons 50 0)
          )
         )
         (entmake
          (list
           (cons 0 "POINT")
           (cons 100 "AcDbEntity")
           (cons 67 0)
           (cons 8 "0")
           (cons 100 "AcDbPoint")
           (list 10 0 -1.8288 0)
           (cons 50 0)
          )
         )
         (entmake
          (list
           (cons 0 "POINT")
           (cons 100 "AcDbEntity")
           (cons 67 0)
           (cons 8 "0")
           (cons 100 "AcDbPoint")
           (list 10 35.9664 -1.8288 0)
           (cons 50 0)
          )
         )
         (entmake
          (list
           (cons 0 "POINT")
           (cons 100 "AcDbEntity")
           (cons 67 0)
           (cons 8 "0")
           (cons 100 "AcDbPoint")
           (list 10 35.9664 1.8288 0)
           (cons 50 0)
          )
         )
         (entmake
          (list
           (cons 0 "POINT")
           (cons 100 "AcDbEntity")
           (cons 67 0)
           (cons 8 "0")
           (cons 100 "AcDbPoint")
           (list 10 0 1.8288 0)
           (cons 50 0)
          )
         )
         (entmake
          (list
           (cons 0 "POINT")
           (cons 100 "AcDbEntity")
           (cons 67 0)
           (cons 8 "0")
           (cons 62 3)
           (cons 100 "AcDbPoint")
           (list 10 0 0 0)
           (cons 50 0)
          )
         )
         (entmake
          (list
           (cons 0 "POINT")
           (cons 100 "AcDbEntity")
           (cons 67 0)
           (cons 8 "0")
           (cons 62 1)
           (cons 100 "AcDbPoint")
           (list 10 35.9664 0 0)
           (cons 50 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "0.00")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "0.00")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "18.29")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "35.97")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "TEXT")
           (cons 100 "AcDbEntity")
           (cons 67 0)
           (cons 8 "0")
           (cons 100 "AcDbText")
           (list 10 0.82142857 -0.25 0)
           (cons 40 0.5)
           (cons 1 "4")
           (cons 50 0)
           (cons 41 1)
           (cons 51 0)
           (cons 7 "Standard")
           (cons 71 0)
           (cons 72 4)
           (list 11 1 0 0)
           (cons 100 "AcDbText")
           (cons 73 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 1.8288)
           (cons 40 0)
           (cons 41 0)
           (cons 42 0)
           (cons 91 0)
           (list 10 35.9664 1.8288)
           (cons 40 0)
           (cons 41 0)
           (cons 42 0)
           (cons 91 0)
           (list 10 35.9664 -1.8288)
           (cons 40 0)
           (cons 41 0)
           (cons 42 0)
           (cons 91 0)
           (list 10 0 -1.8288)
           (cons 40 0)
           (cons 41 0)
           (cons 42 0)
           (cons 91 0)
          )
         )
         (entmake (list (cons 0 "ENDBLK")))
        )
       )
       ((= (strcase BLKNAME) (strcase "Special-19HeavyHaul-Pup2"))
        (progn
         (entmake)
         (entmake
          (list
           (cons 0 "BLOCK")
           (cons 2 "Special-19HeavyHaul-Pup2")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15.24 -0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15.24 -0.508 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15.9004 -0.508 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15.9004 0.508 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15.24 0.508 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15.24 0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.3048 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 1.8288 0 0)
           (cons 40 0.097536)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 5.4864 0 0)
           (cons 40 0.34834286)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 5.7327156 -0.2463156 0)
           (list 11 5.7327156 0.2463156 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.8524 -0.714248)
           (cons 40 0)
           (cons 41 0)
           (cons 42 0)
           (cons 91 0)
           (list 10 12.8524 -0.555752)
           (cons 40 0)
           (cons 41 0)
           (cons 42 0)
           (cons 91 0)
           (list 10 12.99464 -0.508)
           (cons 40 0)
           (cons 41 0)
           (cons 42 0)
           (cons 91 0)
           (list 10 13.72616 -0.508)
           (cons 40 0)
           (cons 41 0)
           (cons 42 0)
           (cons 91 0)
           (list 10 13.8684 -0.555752)
           (cons 40 0)
           (cons 41 0)
           (cons 42 0)
           (cons 91 0)
           (list 10 13.8684 -0.714248)
           (cons 40 0)
           (cons 41 0)
           (cons 42 0)
           (cons 91 0)
           (list 10 13.72616 -0.762)
           (cons 40 0)
           (cons 41 0)
           (cons 42 0)
           (cons 91 0)
           (list 10 12.99464 -0.762)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.8524 -1.171448)
           (cons 40 0)
           (cons 41 0)
           (cons 42 0)
           (cons 91 0)
           (list 10 12.8524 -1.012952)
           (cons 40 0)
           (cons 41 0)
           (cons 42 0)
           (cons 91 0)
           (list 10 12.99464 -0.9652)
           (cons 40 0)
           (cons 41 0)
           (cons 42 0)
           (cons 91 0)
           (list 10 13.72616 -0.9652)
           (cons 40 0)
           (cons 41 0)
           (cons 42 0)
           (cons 91 0)
           (list 10 13.8684 -1.012952)
           (cons 40 0)
           (cons 41 0)
           (cons 42 0)
           (cons 91 0)
           (list 10 13.8684 -1.171448)
           (cons 40 0)
           (cons 41 0)
           (cons 42 0)
           (cons 91 0)
           (list 10 13.72616 -1.2192)
           (cons 40 0)
           (cons 41 0)
           (cons 42 0)
           (cons 91 0)
           (list 10 12.99464 -1.2192)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.8524 0.555752)
           (cons 40 0)
           (cons 41 0)
           (cons 42 0)
           (cons 91 0)
           (list 10 12.8524 0.714248)
           (cons 40 0)
           (cons 41 0)
           (cons 42 0)
           (cons 91 0)
           (list 10 12.99464 0.762)
           (cons 40 0)
           (cons 41 0)
           (cons 42 0)
           (cons 91 0)
           (list 10 13.72616 0.762)
           (cons 40 0)
           (cons 41 0)
           (cons 42 0)
           (cons 91 0)
           (list 10 13.8684 0.714248)
           (cons 40 0)
           (cons 41 0)
           (cons 42 0)
           (cons 91 0)
           (list 10 13.8684 0.555752)
           (cons 40 0)
           (cons 41 0)
           (cons 42 0)
           (cons 91 0)
           (list 10 13.72616 0.508)
           (cons 40 0)
           (cons 41 0)
           (cons 42 0)
           (cons 91 0)
           (list 10 12.99464 0.508)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.8524 1.012952)
           (cons 40 0)
           (cons 41 0)
           (cons 42 0)
           (cons 91 0)
           (list 10 12.8524 1.171448)
           (cons 40 0)
           (cons 41 0)
           (cons 42 0)
           (cons 91 0)
           (list 10 12.99464 1.2192)
           (cons 40 0)
           (cons 41 0)
           (cons 42 0)
           (cons 91 0)
           (list 10 13.72616 1.2192)
           (cons 40 0)
           (cons 41 0)
           (cons 42 0)
           (cons 91 0)
           (list 10 13.8684 1.171448)
           (cons 40 0)
           (cons 41 0)
           (cons 42 0)
           (cons 91 0)
           (list 10 13.8684 1.012952)
           (cons 40 0)
           (cons 41 0)
           (cons 42 0)
           (cons 91 0)
           (list 10 13.72616 0.9652)
           (cons 40 0)
           (cons 41 0)
           (cons 42 0)
           (cons 91 0)
           (list 10 12.99464 0.9652)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.1224 -0.714248)
           (cons 40 0)
           (cons 41 0)
           (cons 42 0)
           (cons 91 0)
           (list 10 14.1224 -0.555752)
           (cons 40 0)
           (cons 41 0)
           (cons 42 0)
           (cons 91 0)
           (list 10 14.26464 -0.508)
           (cons 40 0)
           (cons 41 0)
           (cons 42 0)
           (cons 91 0)
           (list 10 14.99616 -0.508)
           (cons 40 0)
           (cons 41 0)
           (cons 42 0)
           (cons 91 0)
           (list 10 15.1384 -0.555752)
           (cons 40 0)
           (cons 41 0)
           (cons 42 0)
           (cons 91 0)
           (list 10 15.1384 -0.714248)
           (cons 40 0)
           (cons 41 0)
           (cons 42 0)
           (cons 91 0)
           (list 10 14.99616 -0.762)
           (cons 40 0)
           (cons 41 0)
           (cons 42 0)
           (cons 91 0)
           (list 10 14.26464 -0.762)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.1224 -1.171448)
           (cons 40 0)
           (cons 41 0)
           (cons 42 0)
           (cons 91 0)
           (list 10 14.1224 -1.012952)
           (cons 40 0)
           (cons 41 0)
           (cons 42 0)
           (cons 91 0)
           (list 10 14.26464 -0.9652)
           (cons 40 0)
           (cons 41 0)
           (cons 42 0)
           (cons 91 0)
           (list 10 14.99616 -0.9652)
           (cons 40 0)
           (cons 41 0)
           (cons 42 0)
           (cons 91 0)
           (list 10 15.1384 -1.012952)
           (cons 40 0)
           (cons 41 0)
           (cons 42 0)
           (cons 91 0)
           (list 10 15.1384 -1.171448)
           (cons 40 0)
           (cons 41 0)
           (cons 42 0)
           (cons 91 0)
           (list 10 14.99616 -1.2192)
           (cons 40 0)
           (cons 41 0)
           (cons 42 0)
           (cons 91 0)
           (list 10 14.26464 -1.2192)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.1224 0.555752)
           (cons 40 0)
           (cons 41 0)
           (cons 42 0)
           (cons 91 0)
           (list 10 14.1224 0.714248)
           (cons 40 0)
           (cons 41 0)
           (cons 42 0)
           (cons 91 0)
           (list 10 14.26464 0.762)
           (cons 40 0)
           (cons 41 0)
           (cons 42 0)
           (cons 91 0)
           (list 10 14.99616 0.762)
           (cons 40 0)
           (cons 41 0)
           (cons 42 0)
           (cons 91 0)
           (list 10 15.1384 0.714248)
           (cons 40 0)
           (cons 41 0)
           (cons 42 0)
           (cons 91 0)
           (list 10 15.1384 0.555752)
           (cons 40 0)
           (cons 41 0)
           (cons 42 0)
           (cons 91 0)
           (list 10 14.99616 0.508)
           (cons 40 0)
           (cons 41 0)
           (cons 42 0)
           (cons 91 0)
           (list 10 14.26464 0.508)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.1224 1.012952)
           (cons 40 0)
           (cons 41 0)
           (cons 42 0)
           (cons 91 0)
           (list 10 14.1224 1.171448)
           (cons 40 0)
           (cons 41 0)
           (cons 42 0)
           (cons 91 0)
           (list 10 14.26464 1.2192)
           (cons 40 0)
           (cons 41 0)
           (cons 42 0)
           (cons 91 0)
           (list 10 14.99616 1.2192)
           (cons 40 0)
           (cons 41 0)
           (cons 42 0)
           (cons 91 0)
           (list 10 15.1384 1.171448)
           (cons 40 0)
           (cons 41 0)
           (cons 42 0)
           (cons 91 0)
           (list 10 15.1384 1.012952)
           (cons 40 0)
           (cons 41 0)
           (cons 42 0)
           (cons 91 0)
           (list 10 14.99616 0.9652)
           (cons 40 0)
           (cons 41 0)
           (cons 42 0)
           (cons 91 0)
           (list 10 14.26464 0.9652)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 15.3924 -0.714248)
           (cons 40 0)
           (cons 41 0)
           (cons 42 0)
           (cons 91 0)
           (list 10 15.3924 -0.555752)
           (cons 40 0)
           (cons 41 0)
           (cons 42 0)
           (cons 91 0)
           (list 10 15.53464 -0.508)
           (cons 40 0)
           (cons 41 0)
           (cons 42 0)
           (cons 91 0)
           (list 10 16.26616 -0.508)
           (cons 40 0)
           (cons 41 0)
           (cons 42 0)
           (cons 91 0)
           (list 10 16.4084 -0.555752)
           (cons 40 0)
           (cons 41 0)
           (cons 42 0)
           (cons 91 0)
           (list 10 16.4084 -0.714248)
           (cons 40 0)
           (cons 41 0)
           (cons 42 0)
           (cons 91 0)
           (list 10 16.26616 -0.762)
           (cons 40 0)
           (cons 41 0)
           (cons 42 0)
           (cons 91 0)
           (list 10 15.53464 -0.762)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 15.3924 -1.171448)
           (cons 40 0)
           (cons 41 0)
           (cons 42 0)
           (cons 91 0)
           (list 10 15.3924 -1.012952)
           (cons 40 0)
           (cons 41 0)
           (cons 42 0)
           (cons 91 0)
           (list 10 15.53464 -0.9652)
           (cons 40 0)
           (cons 41 0)
           (cons 42 0)
           (cons 91 0)
           (list 10 16.26616 -0.9652)
           (cons 40 0)
           (cons 41 0)
           (cons 42 0)
           (cons 91 0)
           (list 10 16.4084 -1.012952)
           (cons 40 0)
           (cons 41 0)
           (cons 42 0)
           (cons 91 0)
           (list 10 16.4084 -1.171448)
           (cons 40 0)
           (cons 41 0)
           (cons 42 0)
           (cons 91 0)
           (list 10 16.26616 -1.2192)
           (cons 40 0)
           (cons 41 0)
           (cons 42 0)
           (cons 91 0)
           (list 10 15.53464 -1.2192)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 15.3924 0.555752)
           (cons 40 0)
           (cons 41 0)
           (cons 42 0)
           (cons 91 0)
           (list 10 15.3924 0.714248)
           (cons 40 0)
           (cons 41 0)
           (cons 42 0)
           (cons 91 0)
           (list 10 15.53464 0.762)
           (cons 40 0)
           (cons 41 0)
           (cons 42 0)
           (cons 91 0)
           (list 10 16.26616 0.762)
           (cons 40 0)
           (cons 41 0)
           (cons 42 0)
           (cons 91 0)
           (list 10 16.4084 0.714248)
           (cons 40 0)
           (cons 41 0)
           (cons 42 0)
           (cons 91 0)
           (list 10 16.4084 0.555752)
           (cons 40 0)
           (cons 41 0)
           (cons 42 0)
           (cons 91 0)
           (list 10 16.26616 0.508)
           (cons 40 0)
           (cons 41 0)
           (cons 42 0)
           (cons 91 0)
           (list 10 15.53464 0.508)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 15.3924 1.012952)
           (cons 40 0)
           (cons 41 0)
           (cons 42 0)
           (cons 91 0)
           (list 10 15.3924 1.171448)
           (cons 40 0)
           (cons 41 0)
           (cons 42 0)
           (cons 91 0)
           (list 10 15.53464 1.2192)
           (cons 40 0)
           (cons 41 0)
           (cons 42 0)
           (cons 91 0)
           (list 10 16.26616 1.2192)
           (cons 40 0)
           (cons 41 0)
           (cons 42 0)
           (cons 91 0)
           (list 10 16.4084 1.171448)
           (cons 40 0)
           (cons 41 0)
           (cons 42 0)
           (cons 91 0)
           (list 10 16.4084 1.012952)
           (cons 40 0)
           (cons 41 0)
           (cons 42 0)
           (cons 91 0)
           (list 10 16.26616 0.9652)
           (cons 40 0)
           (cons 41 0)
           (cons 42 0)
           (cons 91 0)
           (list 10 15.53464 0.9652)
           (cons 40 0)
           (cons 41 0)
           (cons 42 0)
           (cons 91 0)
          )
         )
         (entmake
          (list
           (cons 0 "POINT")
           (cons 100 "AcDbEntity")
           (cons 67 0)
           (cons 8 "0")
           (cons 62 3)
           (cons 100 "AcDbPoint")
           (list 10 1.8288 0 0)
           (cons 50 0)
          )
         )
         (entmake
          (list
           (cons 0 "POINT")
           (cons 100 "AcDbEntity")
           (cons 67 0)
           (cons 8 "0")
           (cons 62 1)
           (cons 100 "AcDbPoint")
           (list 10 5.4864 0 0)
           (cons 50 0)
          )
         )
         (entmake
          (list
           (cons 0 "POINT")
           (cons 100 "AcDbEntity")
           (cons 67 0)
           (cons 8 "0")
           (cons 100 "AcDbPoint")
           (list 10 14.6304 1.2192 0)
           (cons 50 0)
          )
         )
         (entmake
          (list
           (cons 0 "POINT")
           (cons 100 "AcDbEntity")
           (cons 67 0)
           (cons 8 "0")
           (cons 100 "AcDbPoint")
           (list 10 14.6304 -1.2192 0)
           (cons 50 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "1.83")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "1.83")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "14.63")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "5.49")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "TEXT")
           (cons 100 "AcDbEntity")
           (cons 67 0)
           (cons 8 "0")
           (cons 100 "AcDbText")
           (list 10 2.66213333 -0.25 0)
           (cons 40 0.5)
           (cons 1 "3")
           (cons 50 0)
           (cons 41 1)
           (cons 51 0)
           (cons 7 "Standard")
           (cons 71 0)
           (cons 72 4)
           (list 11 2.8288 0 0)
           (cons 100 "AcDbText")
           (cons 73 0)
          )
         )
         (entmake
          (list
           (cons 0 "LWPOLYLINE")
           (cons 100 "AcDbEntity")
           (cons 67 0)
           (cons 8 "Defpoints")
           (cons 100 "AcDbPolyline")
           (cons 90 8)
           (cons 70 129)
           (cons 43 0)
           (cons 38 0)
           (cons 39 0)
           (list 10 12.8524 1.2192)
           (cons 40 0)
           (cons 41 0)
           (cons 42 0)
           (cons 91 0)
           (list 10 16.4084 1.2192)
           (cons 40 0)
           (cons 41 0)
           (cons 42 0)
           (cons 91 0)
           (list 10 16.4084 -1.2192)
           (cons 40 0)
           (cons 41 0)
           (cons 42 0)
           (cons 91 0)
           (list 10 12.8524 -1.2192)
           (cons 40 0)
           (cons 41 0)
           (cons 42 0)
           (cons 91 0)
           (list 10 12.8524 -0.3048)
           (cons 40 0)
           (cons 41 0)
           (cons 42 0)
           (cons 91 0)
           (list 10 0 -0.3048)
           (cons 40 0)
           (cons 41 0)
           (cons 42 0)
           (cons 91 0)
           (list 10 0 0.3048)
           (cons 40 0)
           (cons 41 0)
           (cons 42 0)
           (cons 91 0)
           (list 10 12.8524 0.3048)
           (cons 40 0)
           (cons 41 0)
           (cons 42 0)
           (cons 91 0)
          )
         )
         (entmake (list (cons 0 "ENDBLK")))
        )
       )
       ((= (strcase BLKNAME) (strcase "Special-19HeavyHaul-Pup1"))
        (progn
         (entmake)
         (entmake
          (list
           (cons 0 "BLOCK")
           (cons 2 "Special-19HeavyHaul-Pup1")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 10.3632 -0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 10.3632 -0.508 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 11.0236 -0.508 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 11.0236 0.508 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 10.3632 0.508 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 10.3632 0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.3048 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 1.8288 0 0)
           (cons 40 0.097536)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 6.096 0 0)
           (cons 40 0.34834286)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 6.3423156 -0.2463156 0)
           (list 11 6.3423156 0.2463156 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.9756 -0.714248)
           (cons 40 0)
           (cons 41 0)
           (cons 42 0)
           (cons 91 0)
           (list 10 7.9756 -0.555752)
           (cons 40 0)
           (cons 41 0)
           (cons 42 0)
           (cons 91 0)
           (list 10 8.11784 -0.508)
           (cons 40 0)
           (cons 41 0)
           (cons 42 0)
           (cons 91 0)
           (list 10 8.84936 -0.508)
           (cons 40 0)
           (cons 41 0)
           (cons 42 0)
           (cons 91 0)
           (list 10 8.9916 -0.555752)
           (cons 40 0)
           (cons 41 0)
           (cons 42 0)
           (cons 91 0)
           (list 10 8.9916 -0.714248)
           (cons 40 0)
           (cons 41 0)
           (cons 42 0)
           (cons 91 0)
           (list 10 8.84936 -0.762)
           (cons 40 0)
           (cons 41 0)
           (cons 42 0)
           (cons 91 0)
           (list 10 8.11784 -0.762)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.9756 -1.171448)
           (cons 40 0)
           (cons 41 0)
           (cons 42 0)
           (cons 91 0)
           (list 10 7.9756 -1.012952)
           (cons 40 0)
           (cons 41 0)
           (cons 42 0)
           (cons 91 0)
           (list 10 8.11784 -0.9652)
           (cons 40 0)
           (cons 41 0)
           (cons 42 0)
           (cons 91 0)
           (list 10 8.84936 -0.9652)
           (cons 40 0)
           (cons 41 0)
           (cons 42 0)
           (cons 91 0)
           (list 10 8.9916 -1.012952)
           (cons 40 0)
           (cons 41 0)
           (cons 42 0)
           (cons 91 0)
           (list 10 8.9916 -1.171448)
           (cons 40 0)
           (cons 41 0)
           (cons 42 0)
           (cons 91 0)
           (list 10 8.84936 -1.2192)
           (cons 40 0)
           (cons 41 0)
           (cons 42 0)
           (cons 91 0)
           (list 10 8.11784 -1.2192)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.9756 0.555752)
           (cons 40 0)
           (cons 41 0)
           (cons 42 0)
           (cons 91 0)
           (list 10 7.9756 0.714248)
           (cons 40 0)
           (cons 41 0)
           (cons 42 0)
           (cons 91 0)
           (list 10 8.11784 0.762)
           (cons 40 0)
           (cons 41 0)
           (cons 42 0)
           (cons 91 0)
           (list 10 8.84936 0.762)
           (cons 40 0)
           (cons 41 0)
           (cons 42 0)
           (cons 91 0)
           (list 10 8.9916 0.714248)
           (cons 40 0)
           (cons 41 0)
           (cons 42 0)
           (cons 91 0)
           (list 10 8.9916 0.555752)
           (cons 40 0)
           (cons 41 0)
           (cons 42 0)
           (cons 91 0)
           (list 10 8.84936 0.508)
           (cons 40 0)
           (cons 41 0)
           (cons 42 0)
           (cons 91 0)
           (list 10 8.11784 0.508)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.9756 1.012952)
           (cons 40 0)
           (cons 41 0)
           (cons 42 0)
           (cons 91 0)
           (list 10 7.9756 1.171448)
           (cons 40 0)
           (cons 41 0)
           (cons 42 0)
           (cons 91 0)
           (list 10 8.11784 1.2192)
           (cons 40 0)
           (cons 41 0)
           (cons 42 0)
           (cons 91 0)
           (list 10 8.84936 1.2192)
           (cons 40 0)
           (cons 41 0)
           (cons 42 0)
           (cons 91 0)
           (list 10 8.9916 1.171448)
           (cons 40 0)
           (cons 41 0)
           (cons 42 0)
           (cons 91 0)
           (list 10 8.9916 1.012952)
           (cons 40 0)
           (cons 41 0)
           (cons 42 0)
           (cons 91 0)
           (list 10 8.84936 0.9652)
           (cons 40 0)
           (cons 41 0)
           (cons 42 0)
           (cons 91 0)
           (list 10 8.11784 0.9652)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.2456 -0.714248)
           (cons 40 0)
           (cons 41 0)
           (cons 42 0)
           (cons 91 0)
           (list 10 9.2456 -0.555752)
           (cons 40 0)
           (cons 41 0)
           (cons 42 0)
           (cons 91 0)
           (list 10 9.38784 -0.508)
           (cons 40 0)
           (cons 41 0)
           (cons 42 0)
           (cons 91 0)
           (list 10 10.11936 -0.508)
           (cons 40 0)
           (cons 41 0)
           (cons 42 0)
           (cons 91 0)
           (list 10 10.2616 -0.555752)
           (cons 40 0)
           (cons 41 0)
           (cons 42 0)
           (cons 91 0)
           (list 10 10.2616 -0.714248)
           (cons 40 0)
           (cons 41 0)
           (cons 42 0)
           (cons 91 0)
           (list 10 10.11936 -0.762)
           (cons 40 0)
           (cons 41 0)
           (cons 42 0)
           (cons 91 0)
           (list 10 9.38784 -0.762)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.2456 -1.171448)
           (cons 40 0)
           (cons 41 0)
           (cons 42 0)
           (cons 91 0)
           (list 10 9.2456 -1.012952)
           (cons 40 0)
           (cons 41 0)
           (cons 42 0)
           (cons 91 0)
           (list 10 9.38784 -0.9652)
           (cons 40 0)
           (cons 41 0)
           (cons 42 0)
           (cons 91 0)
           (list 10 10.11936 -0.9652)
           (cons 40 0)
           (cons 41 0)
           (cons 42 0)
           (cons 91 0)
           (list 10 10.2616 -1.012952)
           (cons 40 0)
           (cons 41 0)
           (cons 42 0)
           (cons 91 0)
           (list 10 10.2616 -1.171448)
           (cons 40 0)
           (cons 41 0)
           (cons 42 0)
           (cons 91 0)
           (list 10 10.11936 -1.2192)
           (cons 40 0)
           (cons 41 0)
           (cons 42 0)
           (cons 91 0)
           (list 10 9.38784 -1.2192)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.2456 0.555752)
           (cons 40 0)
           (cons 41 0)
           (cons 42 0)
           (cons 91 0)
           (list 10 9.2456 0.714248)
           (cons 40 0)
           (cons 41 0)
           (cons 42 0)
           (cons 91 0)
           (list 10 9.38784 0.762)
           (cons 40 0)
           (cons 41 0)
           (cons 42 0)
           (cons 91 0)
           (list 10 10.11936 0.762)
           (cons 40 0)
           (cons 41 0)
           (cons 42 0)
           (cons 91 0)
           (list 10 10.2616 0.714248)
           (cons 40 0)
           (cons 41 0)
           (cons 42 0)
           (cons 91 0)
           (list 10 10.2616 0.555752)
           (cons 40 0)
           (cons 41 0)
           (cons 42 0)
           (cons 91 0)
           (list 10 10.11936 0.508)
           (cons 40 0)
           (cons 41 0)
           (cons 42 0)
           (cons 91 0)
           (list 10 9.38784 0.508)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.2456 1.012952)
           (cons 40 0)
           (cons 41 0)
           (cons 42 0)
           (cons 91 0)
           (list 10 9.2456 1.171448)
           (cons 40 0)
           (cons 41 0)
           (cons 42 0)
           (cons 91 0)
           (list 10 9.38784 1.2192)
           (cons 40 0)
           (cons 41 0)
           (cons 42 0)
           (cons 91 0)
           (list 10 10.11936 1.2192)
           (cons 40 0)
           (cons 41 0)
           (cons 42 0)
           (cons 91 0)
           (list 10 10.2616 1.171448)
           (cons 40 0)
           (cons 41 0)
           (cons 42 0)
           (cons 91 0)
           (list 10 10.2616 1.012952)
           (cons 40 0)
           (cons 41 0)
           (cons 42 0)
           (cons 91 0)
           (list 10 10.11936 0.9652)
           (cons 40 0)
           (cons 41 0)
           (cons 42 0)
           (cons 91 0)
           (list 10 9.38784 0.9652)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.5156 -0.714248)
           (cons 40 0)
           (cons 41 0)
           (cons 42 0)
           (cons 91 0)
           (list 10 10.5156 -0.555752)
           (cons 40 0)
           (cons 41 0)
           (cons 42 0)
           (cons 91 0)
           (list 10 10.65784 -0.508)
           (cons 40 0)
           (cons 41 0)
           (cons 42 0)
           (cons 91 0)
           (list 10 11.38936 -0.508)
           (cons 40 0)
           (cons 41 0)
           (cons 42 0)
           (cons 91 0)
           (list 10 11.5316 -0.555752)
           (cons 40 0)
           (cons 41 0)
           (cons 42 0)
           (cons 91 0)
           (list 10 11.5316 -0.714248)
           (cons 40 0)
           (cons 41 0)
           (cons 42 0)
           (cons 91 0)
           (list 10 11.38936 -0.762)
           (cons 40 0)
           (cons 41 0)
           (cons 42 0)
           (cons 91 0)
           (list 10 10.65784 -0.762)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.5156 -1.171448)
           (cons 40 0)
           (cons 41 0)
           (cons 42 0)
           (cons 91 0)
           (list 10 10.5156 -1.012952)
           (cons 40 0)
           (cons 41 0)
           (cons 42 0)
           (cons 91 0)
           (list 10 10.65784 -0.9652)
           (cons 40 0)
           (cons 41 0)
           (cons 42 0)
           (cons 91 0)
           (list 10 11.38936 -0.9652)
           (cons 40 0)
           (cons 41 0)
           (cons 42 0)
           (cons 91 0)
           (list 10 11.5316 -1.012952)
           (cons 40 0)
           (cons 41 0)
           (cons 42 0)
           (cons 91 0)
           (list 10 11.5316 -1.171448)
           (cons 40 0)
           (cons 41 0)
           (cons 42 0)
           (cons 91 0)
           (list 10 11.38936 -1.2192)
           (cons 40 0)
           (cons 41 0)
           (cons 42 0)
           (cons 91 0)
           (list 10 10.65784 -1.2192)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.5156 0.555752)
           (cons 40 0)
           (cons 41 0)
           (cons 42 0)
           (cons 91 0)
           (list 10 10.5156 0.714248)
           (cons 40 0)
           (cons 41 0)
           (cons 42 0)
           (cons 91 0)
           (list 10 10.65784 0.762)
           (cons 40 0)
           (cons 41 0)
           (cons 42 0)
           (cons 91 0)
           (list 10 11.38936 0.762)
           (cons 40 0)
           (cons 41 0)
           (cons 42 0)
           (cons 91 0)
           (list 10 11.5316 0.714248)
           (cons 40 0)
           (cons 41 0)
           (cons 42 0)
           (cons 91 0)
           (list 10 11.5316 0.555752)
           (cons 40 0)
           (cons 41 0)
           (cons 42 0)
           (cons 91 0)
           (list 10 11.38936 0.508)
           (cons 40 0)
           (cons 41 0)
           (cons 42 0)
           (cons 91 0)
           (list 10 10.65784 0.508)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.5156 1.012952)
           (cons 40 0)
           (cons 41 0)
           (cons 42 0)
           (cons 91 0)
           (list 10 10.5156 1.171448)
           (cons 40 0)
           (cons 41 0)
           (cons 42 0)
           (cons 91 0)
           (list 10 10.65784 1.2192)
           (cons 40 0)
           (cons 41 0)
           (cons 42 0)
           (cons 91 0)
           (list 10 11.38936 1.2192)
           (cons 40 0)
           (cons 41 0)
           (cons 42 0)
           (cons 91 0)
           (list 10 11.5316 1.171448)
           (cons 40 0)
           (cons 41 0)
           (cons 42 0)
           (cons 91 0)
           (list 10 11.5316 1.012952)
           (cons 40 0)
           (cons 41 0)
           (cons 42 0)
           (cons 91 0)
           (list 10 11.38936 0.9652)
           (cons 40 0)
           (cons 41 0)
           (cons 42 0)
           (cons 91 0)
           (list 10 10.65784 0.9652)
           (cons 40 0)
           (cons 41 0)
           (cons 42 0)
           (cons 91 0)
          )
         )
         (entmake
          (list
           (cons 0 "POINT")
           (cons 100 "AcDbEntity")
           (cons 67 0)
           (cons 8 "0")
           (cons 62 3)
           (cons 100 "AcDbPoint")
           (list 10 1.8288 0 0)
           (cons 50 0)
          )
         )
         (entmake
          (list
           (cons 0 "POINT")
           (cons 100 "AcDbEntity")
           (cons 67 0)
           (cons 8 "0")
           (cons 62 1)
           (cons 100 "AcDbPoint")
           (list 10 6.096 0 0)
           (cons 50 0)
          )
         )
         (entmake
          (list
           (cons 0 "POINT")
           (cons 100 "AcDbEntity")
           (cons 67 0)
           (cons 8 "0")
           (cons 100 "AcDbPoint")
           (list 10 9.7536 1.2192 0)
           (cons 50 0)
          )
         )
         (entmake
          (list
           (cons 0 "POINT")
           (cons 100 "AcDbEntity")
           (cons 67 0)
           (cons 8 "0")
           (cons 100 "AcDbPoint")
           (list 10 9.7536 -1.2192 0)
           (cons 50 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "1.83")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "1.83")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "9.75")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "6.09")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "TEXT")
           (cons 100 "AcDbEntity")
           (cons 67 0)
           (cons 8 "0")
           (cons 100 "AcDbText")
           (list 10 2.66213333 -0.25 0)
           (cons 40 0.5)
           (cons 1 "2")
           (cons 50 0)
           (cons 41 1)
           (cons 51 0)
           (cons 7 "Standard")
           (cons 71 0)
           (cons 72 4)
           (list 11 2.8288 0 0)
           (cons 100 "AcDbText")
           (cons 73 0)
          )
         )
         (entmake
          (list
           (cons 0 "LWPOLYLINE")
           (cons 100 "AcDbEntity")
           (cons 67 0)
           (cons 8 "Defpoints")
           (cons 100 "AcDbPolyline")
           (cons 90 8)
           (cons 70 129)
           (cons 43 0)
           (cons 38 0)
           (cons 39 0)
           (list 10 7.9756 1.2192)
           (cons 40 0)
           (cons 41 0)
           (cons 42 0)
           (cons 91 0)
           (list 10 11.5316 1.2192)
           (cons 40 0)
           (cons 41 0)
           (cons 42 0)
           (cons 91 0)
           (list 10 11.5316 -1.2192)
           (cons 40 0)
           (cons 41 0)
           (cons 42 0)
           (cons 91 0)
           (list 10 7.9756 -1.2192)
           (cons 40 0)
           (cons 41 0)
           (cons 42 0)
           (cons 91 0)
           (list 10 7.9756 -0.3048)
           (cons 40 0)
           (cons 41 0)
           (cons 42 0)
           (cons 91 0)
           (list 10 0 -0.3048)
           (cons 40 0)
           (cons 41 0)
           (cons 42 0)
           (cons 91 0)
           (list 10 0 0.3048)
           (cons 40 0)
           (cons 41 0)
           (cons 42 0)
           (cons 91 0)
           (list 10 7.9756 0.3048)
           (cons 40 0)
           (cons 41 0)
           (cons 42 0)
           (cons 91 0)
          )
         )
         (entmake (list (cons 0 "ENDBLK")))
        )
       )
       ((= (strcase BLKNAME) (strcase "Special-19HeavyHaul-Truck"))
        (progn
         (entmake)
         (entmake
          (list
           (cons 0 "BLOCK")
           (cons 2 "Special-19HeavyHaul-Truck")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.524 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.1816 -1.524 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.1816 -0.5842 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.89 -0.5842 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.89 0.5842 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.1816 0.5842 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.1816 1.524 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.524 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.524 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.524 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 7.62 0 0)
           (cons 40 0.37011429)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 7.88171032 -0.26171032 0)
           (list 11 7.88171032 0.26171032 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.842 -0.790448)
           (cons 40 0)
           (cons 41 0)
           (cons 42 0)
           (cons 91 0)
           (list 10 5.842 -0.631952)
           (cons 40 0)
           (cons 41 0)
           (cons 42 0)
           (cons 91 0)
           (list 10 5.98424 -0.5842)
           (cons 40 0)
           (cons 41 0)
           (cons 42 0)
           (cons 91 0)
           (list 10 6.71576 -0.5842)
           (cons 40 0)
           (cons 41 0)
           (cons 42 0)
           (cons 91 0)
           (list 10 6.858 -0.631952)
           (cons 40 0)
           (cons 41 0)
           (cons 42 0)
           (cons 91 0)
           (list 10 6.858 -0.790448)
           (cons 40 0)
           (cons 41 0)
           (cons 42 0)
           (cons 91 0)
           (list 10 6.71576 -0.8382)
           (cons 40 0)
           (cons 41 0)
           (cons 42 0)
           (cons 91 0)
           (list 10 5.98424 -0.8382)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.842 -1.247648)
           (cons 40 0)
           (cons 41 0)
           (cons 42 0)
           (cons 91 0)
           (list 10 5.842 -1.089152)
           (cons 40 0)
           (cons 41 0)
           (cons 42 0)
           (cons 91 0)
           (list 10 5.98424 -1.0414)
           (cons 40 0)
           (cons 41 0)
           (cons 42 0)
           (cons 91 0)
           (list 10 6.71576 -1.0414)
           (cons 40 0)
           (cons 41 0)
           (cons 42 0)
           (cons 91 0)
           (list 10 6.858 -1.089152)
           (cons 40 0)
           (cons 41 0)
           (cons 42 0)
           (cons 91 0)
           (list 10 6.858 -1.247648)
           (cons 40 0)
           (cons 41 0)
           (cons 42 0)
           (cons 91 0)
           (list 10 6.71576 -1.2954)
           (cons 40 0)
           (cons 41 0)
           (cons 42 0)
           (cons 91 0)
           (list 10 5.98424 -1.2954)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.842 0.631952)
           (cons 40 0)
           (cons 41 0)
           (cons 42 0)
           (cons 91 0)
           (list 10 5.842 0.790448)
           (cons 40 0)
           (cons 41 0)
           (cons 42 0)
           (cons 91 0)
           (list 10 5.98424 0.8382)
           (cons 40 0)
           (cons 41 0)
           (cons 42 0)
           (cons 91 0)
           (list 10 6.71576 0.8382)
           (cons 40 0)
           (cons 41 0)
           (cons 42 0)
           (cons 91 0)
           (list 10 6.858 0.790448)
           (cons 40 0)
           (cons 41 0)
           (cons 42 0)
           (cons 91 0)
           (list 10 6.858 0.631952)
           (cons 40 0)
           (cons 41 0)
           (cons 42 0)
           (cons 91 0)
           (list 10 6.71576 0.5842)
           (cons 40 0)
           (cons 41 0)
           (cons 42 0)
           (cons 91 0)
           (list 10 5.98424 0.5842)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.842 1.089152)
           (cons 40 0)
           (cons 41 0)
           (cons 42 0)
           (cons 91 0)
           (list 10 5.842 1.247648)
           (cons 40 0)
           (cons 41 0)
           (cons 42 0)
           (cons 91 0)
           (list 10 5.98424 1.2954)
           (cons 40 0)
           (cons 41 0)
           (cons 42 0)
           (cons 91 0)
           (list 10 6.71576 1.2954)
           (cons 40 0)
           (cons 41 0)
           (cons 42 0)
           (cons 91 0)
           (list 10 6.858 1.247648)
           (cons 40 0)
           (cons 41 0)
           (cons 42 0)
           (cons 91 0)
           (list 10 6.858 1.089152)
           (cons 40 0)
           (cons 41 0)
           (cons 42 0)
           (cons 91 0)
           (list 10 6.71576 1.0414)
           (cons 40 0)
           (cons 41 0)
           (cons 42 0)
           (cons 91 0)
           (list 10 5.98424 1.0414)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.112 -0.790448)
           (cons 40 0)
           (cons 41 0)
           (cons 42 0)
           (cons 91 0)
           (list 10 7.112 -0.631952)
           (cons 40 0)
           (cons 41 0)
           (cons 42 0)
           (cons 91 0)
           (list 10 7.25424 -0.5842)
           (cons 40 0)
           (cons 41 0)
           (cons 42 0)
           (cons 91 0)
           (list 10 7.98576 -0.5842)
           (cons 40 0)
           (cons 41 0)
           (cons 42 0)
           (cons 91 0)
           (list 10 8.128 -0.631952)
           (cons 40 0)
           (cons 41 0)
           (cons 42 0)
           (cons 91 0)
           (list 10 8.128 -0.790448)
           (cons 40 0)
           (cons 41 0)
           (cons 42 0)
           (cons 91 0)
           (list 10 7.98576 -0.8382)
           (cons 40 0)
           (cons 41 0)
           (cons 42 0)
           (cons 91 0)
           (list 10 7.25424 -0.8382)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.112 -1.247648)
           (cons 40 0)
           (cons 41 0)
           (cons 42 0)
           (cons 91 0)
           (list 10 7.112 -1.089152)
           (cons 40 0)
           (cons 41 0)
           (cons 42 0)
           (cons 91 0)
           (list 10 7.25424 -1.0414)
           (cons 40 0)
           (cons 41 0)
           (cons 42 0)
           (cons 91 0)
           (list 10 7.98576 -1.0414)
           (cons 40 0)
           (cons 41 0)
           (cons 42 0)
           (cons 91 0)
           (list 10 8.128 -1.089152)
           (cons 40 0)
           (cons 41 0)
           (cons 42 0)
           (cons 91 0)
           (list 10 8.128 -1.247648)
           (cons 40 0)
           (cons 41 0)
           (cons 42 0)
           (cons 91 0)
           (list 10 7.98576 -1.2954)
           (cons 40 0)
           (cons 41 0)
           (cons 42 0)
           (cons 91 0)
           (list 10 7.25424 -1.2954)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.112 0.631952)
           (cons 40 0)
           (cons 41 0)
           (cons 42 0)
           (cons 91 0)
           (list 10 7.112 0.790448)
           (cons 40 0)
           (cons 41 0)
           (cons 42 0)
           (cons 91 0)
           (list 10 7.25424 0.8382)
           (cons 40 0)
           (cons 41 0)
           (cons 42 0)
           (cons 91 0)
           (list 10 7.98576 0.8382)
           (cons 40 0)
           (cons 41 0)
           (cons 42 0)
           (cons 91 0)
           (list 10 8.128 0.790448)
           (cons 40 0)
           (cons 41 0)
           (cons 42 0)
           (cons 91 0)
           (list 10 8.128 0.631952)
           (cons 40 0)
           (cons 41 0)
           (cons 42 0)
           (cons 91 0)
           (list 10 7.98576 0.5842)
           (cons 40 0)
           (cons 41 0)
           (cons 42 0)
           (cons 91 0)
           (list 10 7.25424 0.5842)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.112 1.089152)
           (cons 40 0)
           (cons 41 0)
           (cons 42 0)
           (cons 91 0)
           (list 10 7.112 1.247648)
           (cons 40 0)
           (cons 41 0)
           (cons 42 0)
           (cons 91 0)
           (list 10 7.25424 1.2954)
           (cons 40 0)
           (cons 41 0)
           (cons 42 0)
           (cons 91 0)
           (list 10 7.98576 1.2954)
           (cons 40 0)
           (cons 41 0)
           (cons 42 0)
           (cons 91 0)
           (list 10 8.128 1.247648)
           (cons 40 0)
           (cons 41 0)
           (cons 42 0)
           (cons 91 0)
           (list 10 8.128 1.089152)
           (cons 40 0)
           (cons 41 0)
           (cons 42 0)
           (cons 91 0)
           (list 10 7.98576 1.0414)
           (cons 40 0)
           (cons 41 0)
           (cons 42 0)
           (cons 91 0)
           (list 10 7.25424 1.0414)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.382 -0.790448)
           (cons 40 0)
           (cons 41 0)
           (cons 42 0)
           (cons 91 0)
           (list 10 8.382 -0.631952)
           (cons 40 0)
           (cons 41 0)
           (cons 42 0)
           (cons 91 0)
           (list 10 8.52424 -0.5842)
           (cons 40 0)
           (cons 41 0)
           (cons 42 0)
           (cons 91 0)
           (list 10 9.25576 -0.5842)
           (cons 40 0)
           (cons 41 0)
           (cons 42 0)
           (cons 91 0)
           (list 10 9.398 -0.631952)
           (cons 40 0)
           (cons 41 0)
           (cons 42 0)
           (cons 91 0)
           (list 10 9.398 -0.790448)
           (cons 40 0)
           (cons 41 0)
           (cons 42 0)
           (cons 91 0)
           (list 10 9.25576 -0.8382)
           (cons 40 0)
           (cons 41 0)
           (cons 42 0)
           (cons 91 0)
           (list 10 8.52424 -0.8382)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.382 -1.247648)
           (cons 40 0)
           (cons 41 0)
           (cons 42 0)
           (cons 91 0)
           (list 10 8.382 -1.089152)
           (cons 40 0)
           (cons 41 0)
           (cons 42 0)
           (cons 91 0)
           (list 10 8.52424 -1.0414)
           (cons 40 0)
           (cons 41 0)
           (cons 42 0)
           (cons 91 0)
           (list 10 9.25576 -1.0414)
           (cons 40 0)
           (cons 41 0)
           (cons 42 0)
           (cons 91 0)
           (list 10 9.398 -1.089152)
           (cons 40 0)
           (cons 41 0)
           (cons 42 0)
           (cons 91 0)
           (list 10 9.398 -1.247648)
           (cons 40 0)
           (cons 41 0)
           (cons 42 0)
           (cons 91 0)
           (list 10 9.25576 -1.2954)
           (cons 40 0)
           (cons 41 0)
           (cons 42 0)
           (cons 91 0)
           (list 10 8.52424 -1.2954)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.382 0.631952)
           (cons 40 0)
           (cons 41 0)
           (cons 42 0)
           (cons 91 0)
           (list 10 8.382 0.790448)
           (cons 40 0)
           (cons 41 0)
           (cons 42 0)
           (cons 91 0)
           (list 10 8.52424 0.8382)
           (cons 40 0)
           (cons 41 0)
           (cons 42 0)
           (cons 91 0)
           (list 10 9.25576 0.8382)
           (cons 40 0)
           (cons 41 0)
           (cons 42 0)
           (cons 91 0)
           (list 10 9.398 0.790448)
           (cons 40 0)
           (cons 41 0)
           (cons 42 0)
           (cons 91 0)
           (list 10 9.398 0.631952)
           (cons 40 0)
           (cons 41 0)
           (cons 42 0)
           (cons 91 0)
           (list 10 9.25576 0.5842)
           (cons 40 0)
           (cons 41 0)
           (cons 42 0)
           (cons 91 0)
           (list 10 8.52424 0.5842)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.382 1.089152)
           (cons 40 0)
           (cons 41 0)
           (cons 42 0)
           (cons 91 0)
           (list 10 8.382 1.247648)
           (cons 40 0)
           (cons 41 0)
           (cons 42 0)
           (cons 91 0)
           (list 10 8.52424 1.2954)
           (cons 40 0)
           (cons 41 0)
           (cons 42 0)
           (cons 91 0)
           (list 10 9.25576 1.2954)
           (cons 40 0)
           (cons 41 0)
           (cons 42 0)
           (cons 91 0)
           (list 10 9.398 1.247648)
           (cons 40 0)
           (cons 41 0)
           (cons 42 0)
           (cons 91 0)
           (list 10 9.398 1.089152)
           (cons 40 0)
           (cons 41 0)
           (cons 42 0)
           (cons 91 0)
           (list 10 9.25576 1.0414)
           (cons 40 0)
           (cons 41 0)
           (cons 42 0)
           (cons 91 0)
           (list 10 8.52424 1.0414)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0.9144 1.2954 0)
           (cons 50 0)
          )
         )
         (entmake
          (list
           (cons 0 "POINT")
           (cons 100 "AcDbEntity")
           (cons 67 0)
           (cons 8 "0")
           (cons 100 "AcDbPoint")
           (list 10 0.9144 -1.2954 0)
           (cons 50 0)
          )
         )
         (entmake
          (list
           (cons 0 "POINT")
           (cons 100 "AcDbEntity")
           (cons 67 0)
           (cons 8 "0")
           (cons 100 "AcDbPoint")
           (list 10 0 1.524 0)
           (cons 50 0)
          )
         )
         (entmake
          (list
           (cons 0 "POINT")
           (cons 100 "AcDbEntity")
           (cons 67 0)
           (cons 8 "0")
           (cons 100 "AcDbPoint")
           (list 10 0 -1.524 0)
           (cons 50 0)
          )
         )
         (entmake
          (list
           (cons 0 "POINT")
           (cons 100 "AcDbEntity")
           (cons 67 0)
           (cons 8 "0")
           (cons 100 "AcDbPoint")
           (list 10 7.62 -1.2954 0)
           (cons 50 0)
          )
         )
         (entmake
          (list
           (cons 0 "POINT")
           (cons 100 "AcDbEntity")
           (cons 67 0)
           (cons 8 "0")
           (cons 100 "AcDbPoint")
           (list 10 7.62 1.2954 0)
           (cons 50 0)
          )
         )
         (entmake
          (list
           (cons 0 "POINT")
           (cons 100 "AcDbEntity")
           (cons 67 0)
           (cons 8 "0")
           (cons 62 1)
           (cons 100 "AcDbPoint")
           (list 10 7.62 0 0)
           (cons 50 0)
          )
         )
         (entmake
          (list
           (cons 0 "POINT")
           (cons 100 "AcDbEntity")
           (cons 67 0)
           (cons 8 "0")
           (cons 62 3)
           (cons 100 "AcDbPoint")
           (list 10 0.9144 0 0)
           (cons 50 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "0.91")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "0.91")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "7.62")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "7.62")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "40.0")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "TEXT")
           (cons 100 "AcDbEntity")
           (cons 67 0)
           (cons 8 "0")
           (cons 100 "AcDbText")
           (list 10 1.85487619 -0.25 0)
           (cons 40 0.5)
           (cons 1 "1")
           (cons 50 0)
           (cons 41 1)
           (cons 51 0)
           (cons 7 "Standard")
           (cons 71 0)
           (cons 72 4)
           (list 11 1.9144 0 0)
           (cons 100 "AcDbText")
           (cons 73 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 1.524)
           (cons 40 0)
           (cons 41 0)
           (cons 42 0)
           (cons 91 0)
           (list 10 8.89 1.524)
           (cons 40 0)
           (cons 41 0)
           (cons 42 0)
           (cons 91 0)
           (list 10 8.89 -1.524)
           (cons 40 0)
           (cons 41 0)
           (cons 42 0)
           (cons 91 0)
           (list 10 0 -1.524)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelRightM2")
           (list 10 0.9144 1.0414 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM2")
           (list 10 0.9144 -1.0414 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "TAC-1999-WB-20-TRAILER"))
        (progn
         (entmake)
         (entmake
          (list
           (cons 0 "BLOCK")
           (cons 2 "TAC-1999-WB-20-TRAILER")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 17 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 17 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 1.3 0 0)
           (cons 40 0.104)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.5062 -0.7445528)
           (cons 40 0)
           (cons 41 0)
           (cons 42 0)
           (cons 91 0)
           (list 10 12.5062 -0.5702072)
           (cons 40 0)
           (cons 41 0)
           (cons 42 0)
           (cons 91 0)
           (list 10 12.662664 -0.51768)
           (cons 40 0)
           (cons 41 0)
           (cons 42 0)
           (cons 91 0)
           (list 10 13.467336 -0.51768)
           (cons 40 0)
           (cons 41 0)
           (cons 42 0)
           (cons 91 0)
           (list 10 13.6238 -0.5702072)
           (cons 40 0)
           (cons 41 0)
           (cons 42 0)
           (cons 91 0)
           (list 10 13.6238 -0.7445528)
           (cons 40 0)
           (cons 41 0)
           (cons 42 0)
           (cons 91 0)
           (list 10 13.467336 -0.79708)
           (cons 40 0)
           (cons 41 0)
           (cons 42 0)
           (cons 91 0)
           (list 10 12.662664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.5062 -1.2474728)
           (cons 40 0)
           (cons 41 0)
           (cons 42 0)
           (cons 91 0)
           (list 10 12.5062 -1.0731272)
           (cons 40 0)
           (cons 41 0)
           (cons 42 0)
           (cons 91 0)
           (list 10 12.662664 -1.0206)
           (cons 40 0)
           (cons 41 0)
           (cons 42 0)
           (cons 91 0)
           (list 10 13.467336 -1.0206)
           (cons 40 0)
           (cons 41 0)
           (cons 42 0)
           (cons 91 0)
           (list 10 13.6238 -1.0731272)
           (cons 40 0)
           (cons 41 0)
           (cons 42 0)
           (cons 91 0)
           (list 10 13.6238 -1.2474728)
           (cons 40 0)
           (cons 41 0)
           (cons 42 0)
           (cons 91 0)
           (list 10 13.467336 -1.3)
           (cons 40 0)
           (cons 41 0)
           (cons 42 0)
           (cons 91 0)
           (list 10 12.662664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.5062 0.5702072)
           (cons 40 0)
           (cons 41 0)
           (cons 42 0)
           (cons 91 0)
           (list 10 12.5062 0.7445528)
           (cons 40 0)
           (cons 41 0)
           (cons 42 0)
           (cons 91 0)
           (list 10 12.662664 0.79708)
           (cons 40 0)
           (cons 41 0)
           (cons 42 0)
           (cons 91 0)
           (list 10 13.467336 0.79708)
           (cons 40 0)
           (cons 41 0)
           (cons 42 0)
           (cons 91 0)
           (list 10 13.6238 0.7445528)
           (cons 40 0)
           (cons 41 0)
           (cons 42 0)
           (cons 91 0)
           (list 10 13.6238 0.5702072)
           (cons 40 0)
           (cons 41 0)
           (cons 42 0)
           (cons 91 0)
           (list 10 13.467336 0.51768)
           (cons 40 0)
           (cons 41 0)
           (cons 42 0)
           (cons 91 0)
           (list 10 12.662664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.5062 1.0731272)
           (cons 40 0)
           (cons 41 0)
           (cons 42 0)
           (cons 91 0)
           (list 10 12.5062 1.2474728)
           (cons 40 0)
           (cons 41 0)
           (cons 42 0)
           (cons 91 0)
           (list 10 12.662664 1.3)
           (cons 40 0)
           (cons 41 0)
           (cons 42 0)
           (cons 91 0)
           (list 10 13.467336 1.3)
           (cons 40 0)
           (cons 41 0)
           (cons 42 0)
           (cons 91 0)
           (list 10 13.6238 1.2474728)
           (cons 40 0)
           (cons 41 0)
           (cons 42 0)
           (cons 91 0)
           (list 10 13.6238 1.0731272)
           (cons 40 0)
           (cons 41 0)
           (cons 42 0)
           (cons 91 0)
           (list 10 13.467336 1.0206)
           (cons 40 0)
           (cons 41 0)
           (cons 42 0)
           (cons 91 0)
           (list 10 12.662664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.7762 -0.7445528)
           (cons 40 0)
           (cons 41 0)
           (cons 42 0)
           (cons 91 0)
           (list 10 13.7762 -0.5702072)
           (cons 40 0)
           (cons 41 0)
           (cons 42 0)
           (cons 91 0)
           (list 10 13.932664 -0.51768)
           (cons 40 0)
           (cons 41 0)
           (cons 42 0)
           (cons 91 0)
           (list 10 14.737336 -0.51768)
           (cons 40 0)
           (cons 41 0)
           (cons 42 0)
           (cons 91 0)
           (list 10 14.8938 -0.5702072)
           (cons 40 0)
           (cons 41 0)
           (cons 42 0)
           (cons 91 0)
           (list 10 14.8938 -0.7445528)
           (cons 40 0)
           (cons 41 0)
           (cons 42 0)
           (cons 91 0)
           (list 10 14.737336 -0.79708)
           (cons 40 0)
           (cons 41 0)
           (cons 42 0)
           (cons 91 0)
           (list 10 13.932664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.7762 -1.2474728)
           (cons 40 0)
           (cons 41 0)
           (cons 42 0)
           (cons 91 0)
           (list 10 13.7762 -1.0731272)
           (cons 40 0)
           (cons 41 0)
           (cons 42 0)
           (cons 91 0)
           (list 10 13.932664 -1.0206)
           (cons 40 0)
           (cons 41 0)
           (cons 42 0)
           (cons 91 0)
           (list 10 14.737336 -1.0206)
           (cons 40 0)
           (cons 41 0)
           (cons 42 0)
           (cons 91 0)
           (list 10 14.8938 -1.0731272)
           (cons 40 0)
           (cons 41 0)
           (cons 42 0)
           (cons 91 0)
           (list 10 14.8938 -1.2474728)
           (cons 40 0)
           (cons 41 0)
           (cons 42 0)
           (cons 91 0)
           (list 10 14.737336 -1.3)
           (cons 40 0)
           (cons 41 0)
           (cons 42 0)
           (cons 91 0)
           (list 10 13.932664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.7762 0.5702072)
           (cons 40 0)
           (cons 41 0)
           (cons 42 0)
           (cons 91 0)
           (list 10 13.7762 0.7445528)
           (cons 40 0)
           (cons 41 0)
           (cons 42 0)
           (cons 91 0)
           (list 10 13.932664 0.79708)
           (cons 40 0)
           (cons 41 0)
           (cons 42 0)
           (cons 91 0)
           (list 10 14.737336 0.79708)
           (cons 40 0)
           (cons 41 0)
           (cons 42 0)
           (cons 91 0)
           (list 10 14.8938 0.7445528)
           (cons 40 0)
           (cons 41 0)
           (cons 42 0)
           (cons 91 0)
           (list 10 14.8938 0.5702072)
           (cons 40 0)
           (cons 41 0)
           (cons 42 0)
           (cons 91 0)
           (list 10 14.737336 0.51768)
           (cons 40 0)
           (cons 41 0)
           (cons 42 0)
           (cons 91 0)
           (list 10 13.932664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.7762 1.0731272)
           (cons 40 0)
           (cons 41 0)
           (cons 42 0)
           (cons 91 0)
           (list 10 13.7762 1.2474728)
           (cons 40 0)
           (cons 41 0)
           (cons 42 0)
           (cons 91 0)
           (list 10 13.932664 1.3)
           (cons 40 0)
           (cons 41 0)
           (cons 42 0)
           (cons 91 0)
           (list 10 14.737336 1.3)
           (cons 40 0)
           (cons 41 0)
           (cons 42 0)
           (cons 91 0)
           (list 10 14.8938 1.2474728)
           (cons 40 0)
           (cons 41 0)
           (cons 42 0)
           (cons 91 0)
           (list 10 14.8938 1.0731272)
           (cons 40 0)
           (cons 41 0)
           (cons 42 0)
           (cons 91 0)
           (list 10 14.737336 1.0206)
           (cons 40 0)
           (cons 41 0)
           (cons 42 0)
           (cons 91 0)
           (list 10 13.932664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 1.3 0 0)
           (cons 50 0)
          )
         )
         (entmake
          (list
           (cons 0 "POINT")
           (cons 100 "AcDbEntity")
           (cons 67 0)
           (cons 8 "0")
           (cons 100 "AcDbPoint")
           (list 10 13.7 -1.3 0)
           (cons 50 0)
          )
         )
         (entmake
          (list
           (cons 0 "POINT")
           (cons 100 "AcDbEntity")
           (cons 67 0)
           (cons 8 "0")
           (cons 100 "AcDbPoint")
           (list 10 13.7 1.3 0)
           (cons 50 0)
          )
         )
         (entmake
          (list
           (cons 0 "POINT")
           (cons 100 "AcDbEntity")
           (cons 67 0)
           (cons 8 "0")
           (cons 100 "AcDbPoint")
           (list 10 17 1.3 0)
           (cons 50 0)
          )
         )
         (entmake
          (list
           (cons 0 "POINT")
           (cons 100 "AcDbEntity")
           (cons 67 0)
           (cons 8 "0")
           (cons 100 "AcDbPoint")
           (list 10 17 -1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 17 -1.3)
           (cons 40 0)
           (cons 41 0)
           (cons 42 0)
           (cons 91 0)
           (list 10 17 1.3)
           (cons 40 0)
           (cons 41 0)
           (cons 42 0)
           (cons 91 0)
           (list 10 0 1.3)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.6 0.56666667 0)
           (cons 40 0.2)
           (cons 1 "1.30")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 0.23333333 0)
           (cons 40 0.2)
           (cons 1 "1.30")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.1 0)
           (cons 40 0.2)
           (cons 1 "13.70")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.43333333 0)
           (cons 40 0.2)
           (cons 1 "0.00")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "TAC-1999-WB-20-TRUCK"))
        (progn
         (entmake)
         (entmake
          (list
           (cons 0 "BLOCK")
           (cons 2 "TAC-1999-WB-20-TRUCK")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.635 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.635 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 7 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 7.26263966 -0.26263966 0)
           (list 11 7.26263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.8062 -0.7445528)
           (cons 40 0)
           (cons 41 0)
           (cons 42 0)
           (cons 91 0)
           (list 10 5.8062 -0.5702072)
           (cons 40 0)
           (cons 41 0)
           (cons 42 0)
           (cons 91 0)
           (list 10 5.962664 -0.51768)
           (cons 40 0)
           (cons 41 0)
           (cons 42 0)
           (cons 91 0)
           (list 10 6.767336 -0.51768)
           (cons 40 0)
           (cons 41 0)
           (cons 42 0)
           (cons 91 0)
           (list 10 6.9238 -0.5702072)
           (cons 40 0)
           (cons 41 0)
           (cons 42 0)
           (cons 91 0)
           (list 10 6.9238 -0.7445528)
           (cons 40 0)
           (cons 41 0)
           (cons 42 0)
           (cons 91 0)
           (list 10 6.767336 -0.79708)
           (cons 40 0)
           (cons 41 0)
           (cons 42 0)
           (cons 91 0)
           (list 10 5.962664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.8062 -1.2474728)
           (cons 40 0)
           (cons 41 0)
           (cons 42 0)
           (cons 91 0)
           (list 10 5.8062 -1.0731272)
           (cons 40 0)
           (cons 41 0)
           (cons 42 0)
           (cons 91 0)
           (list 10 5.962664 -1.0206)
           (cons 40 0)
           (cons 41 0)
           (cons 42 0)
           (cons 91 0)
           (list 10 6.767336 -1.0206)
           (cons 40 0)
           (cons 41 0)
           (cons 42 0)
           (cons 91 0)
           (list 10 6.9238 -1.0731272)
           (cons 40 0)
           (cons 41 0)
           (cons 42 0)
           (cons 91 0)
           (list 10 6.9238 -1.2474728)
           (cons 40 0)
           (cons 41 0)
           (cons 42 0)
           (cons 91 0)
           (list 10 6.767336 -1.3)
           (cons 40 0)
           (cons 41 0)
           (cons 42 0)
           (cons 91 0)
           (list 10 5.962664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.8062 0.5702072)
           (cons 40 0)
           (cons 41 0)
           (cons 42 0)
           (cons 91 0)
           (list 10 5.8062 0.7445528)
           (cons 40 0)
           (cons 41 0)
           (cons 42 0)
           (cons 91 0)
           (list 10 5.962664 0.79708)
           (cons 40 0)
           (cons 41 0)
           (cons 42 0)
           (cons 91 0)
           (list 10 6.767336 0.79708)
           (cons 40 0)
           (cons 41 0)
           (cons 42 0)
           (cons 91 0)
           (list 10 6.9238 0.7445528)
           (cons 40 0)
           (cons 41 0)
           (cons 42 0)
           (cons 91 0)
           (list 10 6.9238 0.5702072)
           (cons 40 0)
           (cons 41 0)
           (cons 42 0)
           (cons 91 0)
           (list 10 6.767336 0.51768)
           (cons 40 0)
           (cons 41 0)
           (cons 42 0)
           (cons 91 0)
           (list 10 5.962664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.8062 1.0731272)
           (cons 40 0)
           (cons 41 0)
           (cons 42 0)
           (cons 91 0)
           (list 10 5.8062 1.2474728)
           (cons 40 0)
           (cons 41 0)
           (cons 42 0)
           (cons 91 0)
           (list 10 5.962664 1.3)
           (cons 40 0)
           (cons 41 0)
           (cons 42 0)
           (cons 91 0)
           (list 10 6.767336 1.3)
           (cons 40 0)
           (cons 41 0)
           (cons 42 0)
           (cons 91 0)
           (list 10 6.9238 1.2474728)
           (cons 40 0)
           (cons 41 0)
           (cons 42 0)
           (cons 91 0)
           (list 10 6.9238 1.0731272)
           (cons 40 0)
           (cons 41 0)
           (cons 42 0)
           (cons 91 0)
           (list 10 6.767336 1.0206)
           (cons 40 0)
           (cons 41 0)
           (cons 42 0)
           (cons 91 0)
           (list 10 5.962664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.0762 -0.7445528)
           (cons 40 0)
           (cons 41 0)
           (cons 42 0)
           (cons 91 0)
           (list 10 7.0762 -0.5702072)
           (cons 40 0)
           (cons 41 0)
           (cons 42 0)
           (cons 91 0)
           (list 10 7.232664 -0.51768)
           (cons 40 0)
           (cons 41 0)
           (cons 42 0)
           (cons 91 0)
           (list 10 8.037336 -0.51768)
           (cons 40 0)
           (cons 41 0)
           (cons 42 0)
           (cons 91 0)
           (list 10 8.1938 -0.5702072)
           (cons 40 0)
           (cons 41 0)
           (cons 42 0)
           (cons 91 0)
           (list 10 8.1938 -0.7445528)
           (cons 40 0)
           (cons 41 0)
           (cons 42 0)
           (cons 91 0)
           (list 10 8.037336 -0.79708)
           (cons 40 0)
           (cons 41 0)
           (cons 42 0)
           (cons 91 0)
           (list 10 7.232664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.0762 -1.2474728)
           (cons 40 0)
           (cons 41 0)
           (cons 42 0)
           (cons 91 0)
           (list 10 7.0762 -1.0731272)
           (cons 40 0)
           (cons 41 0)
           (cons 42 0)
           (cons 91 0)
           (list 10 7.232664 -1.0206)
           (cons 40 0)
           (cons 41 0)
           (cons 42 0)
           (cons 91 0)
           (list 10 8.037336 -1.0206)
           (cons 40 0)
           (cons 41 0)
           (cons 42 0)
           (cons 91 0)
           (list 10 8.1938 -1.0731272)
           (cons 40 0)
           (cons 41 0)
           (cons 42 0)
           (cons 91 0)
           (list 10 8.1938 -1.2474728)
           (cons 40 0)
           (cons 41 0)
           (cons 42 0)
           (cons 91 0)
           (list 10 8.037336 -1.3)
           (cons 40 0)
           (cons 41 0)
           (cons 42 0)
           (cons 91 0)
           (list 10 7.232664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.0762 0.5702072)
           (cons 40 0)
           (cons 41 0)
           (cons 42 0)
           (cons 91 0)
           (list 10 7.0762 0.7445528)
           (cons 40 0)
           (cons 41 0)
           (cons 42 0)
           (cons 91 0)
           (list 10 7.232664 0.79708)
           (cons 40 0)
           (cons 41 0)
           (cons 42 0)
           (cons 91 0)
           (list 10 8.037336 0.79708)
           (cons 40 0)
           (cons 41 0)
           (cons 42 0)
           (cons 91 0)
           (list 10 8.1938 0.7445528)
           (cons 40 0)
           (cons 41 0)
           (cons 42 0)
           (cons 91 0)
           (list 10 8.1938 0.5702072)
           (cons 40 0)
           (cons 41 0)
           (cons 42 0)
           (cons 91 0)
           (list 10 8.037336 0.51768)
           (cons 40 0)
           (cons 41 0)
           (cons 42 0)
           (cons 91 0)
           (list 10 7.232664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.0762 1.0731272)
           (cons 40 0)
           (cons 41 0)
           (cons 42 0)
           (cons 91 0)
           (list 10 7.0762 1.2474728)
           (cons 40 0)
           (cons 41 0)
           (cons 42 0)
           (cons 91 0)
           (list 10 7.232664 1.3)
           (cons 40 0)
           (cons 41 0)
           (cons 42 0)
           (cons 91 0)
           (list 10 8.037336 1.3)
           (cons 40 0)
           (cons 41 0)
           (cons 42 0)
           (cons 91 0)
           (list 10 8.1938 1.2474728)
           (cons 40 0)
           (cons 41 0)
           (cons 42 0)
           (cons 91 0)
           (list 10 8.1938 1.0731272)
           (cons 40 0)
           (cons 41 0)
           (cons 42 0)
           (cons 91 0)
           (list 10 8.037336 1.0206)
           (cons 40 0)
           (cons 41 0)
           (cons 42 0)
           (cons 91 0)
           (list 10 7.232664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0.8 0 0)
           (cons 50 0)
          )
         )
         (entmake
          (list
           (cons 0 "POINT")
           (cons 100 "AcDbEntity")
           (cons 67 0)
           (cons 8 "0")
           (cons 100 "AcDbPoint")
           (list 10 7 -1.3 0)
           (cons 50 0)
          )
         )
         (entmake
          (list
           (cons 0 "POINT")
           (cons 100 "AcDbEntity")
           (cons 67 0)
           (cons 8 "0")
           (cons 100 "AcDbPoint")
           (list 10 7 1.3 0)
           (cons 50 0)
          )
         )
         (entmake
          (list
           (cons 0 "POINT")
           (cons 100 "AcDbEntity")
           (cons 67 0)
           (cons 8 "0")
           (cons 100 "AcDbPoint")
           (list 10 7 0 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0.8 -1.3 0)
           (cons 50 0)
          )
         )
         (entmake
          (list
           (cons 0 "POINT")
           (cons 100 "AcDbEntity")
           (cons 67 0)
           (cons 8 "0")
           (cons 100 "AcDbPoint")
           (list 10 0.8 1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 7.635 -1.3)
           (cons 40 0)
           (cons 41 0)
           (cons 42 0)
           (cons 91 0)
           (list 10 7.635 1.3)
           (cons 40 0)
           (cons 41 0)
           (cons 42 0)
           (cons 91 0)
           (list 10 0 1.3)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.1 0.56666667 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 0.23333333 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.1 0)
           (cons 40 0.2)
           (cons 1 "7.00")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.43333333 0)
           (cons 40 0.2)
           (cons 1 "7.00")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.76666667 0)
           (cons 40 0.2)
           (cons 1 "28.3")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelLeftM1")
           (list 10 0.8 -1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM1")
           (list 10 0.8 1.0206 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "TAC-1999-WB-19-TRAILER"))
        (progn
         (entmake)
         (entmake
          (list
           (cons 0 "BLOCK")
           (cons 2 "TAC-1999-WB-19-TRAILER")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 1.3 0 0)
           (cons 40 0.104)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.1062 -0.7445528)
           (cons 40 0)
           (cons 41 0)
           (cons 42 0)
           (cons 91 0)
           (list 10 12.1062 -0.5702072)
           (cons 40 0)
           (cons 41 0)
           (cons 42 0)
           (cons 91 0)
           (list 10 12.262664 -0.51768)
           (cons 40 0)
           (cons 41 0)
           (cons 42 0)
           (cons 91 0)
           (list 10 13.067336 -0.51768)
           (cons 40 0)
           (cons 41 0)
           (cons 42 0)
           (cons 91 0)
           (list 10 13.2238 -0.5702072)
           (cons 40 0)
           (cons 41 0)
           (cons 42 0)
           (cons 91 0)
           (list 10 13.2238 -0.7445528)
           (cons 40 0)
           (cons 41 0)
           (cons 42 0)
           (cons 91 0)
           (list 10 13.067336 -0.79708)
           (cons 40 0)
           (cons 41 0)
           (cons 42 0)
           (cons 91 0)
           (list 10 12.262664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.1062 -1.2474728)
           (cons 40 0)
           (cons 41 0)
           (cons 42 0)
           (cons 91 0)
           (list 10 12.1062 -1.0731272)
           (cons 40 0)
           (cons 41 0)
           (cons 42 0)
           (cons 91 0)
           (list 10 12.262664 -1.0206)
           (cons 40 0)
           (cons 41 0)
           (cons 42 0)
           (cons 91 0)
           (list 10 13.067336 -1.0206)
           (cons 40 0)
           (cons 41 0)
           (cons 42 0)
           (cons 91 0)
           (list 10 13.2238 -1.0731272)
           (cons 40 0)
           (cons 41 0)
           (cons 42 0)
           (cons 91 0)
           (list 10 13.2238 -1.2474728)
           (cons 40 0)
           (cons 41 0)
           (cons 42 0)
           (cons 91 0)
           (list 10 13.067336 -1.3)
           (cons 40 0)
           (cons 41 0)
           (cons 42 0)
           (cons 91 0)
           (list 10 12.262664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.1062 0.5702072)
           (cons 40 0)
           (cons 41 0)
           (cons 42 0)
           (cons 91 0)
           (list 10 12.1062 0.7445528)
           (cons 40 0)
           (cons 41 0)
           (cons 42 0)
           (cons 91 0)
           (list 10 12.262664 0.79708)
           (cons 40 0)
           (cons 41 0)
           (cons 42 0)
           (cons 91 0)
           (list 10 13.067336 0.79708)
           (cons 40 0)
           (cons 41 0)
           (cons 42 0)
           (cons 91 0)
           (list 10 13.2238 0.7445528)
           (cons 40 0)
           (cons 41 0)
           (cons 42 0)
           (cons 91 0)
           (list 10 13.2238 0.5702072)
           (cons 40 0)
           (cons 41 0)
           (cons 42 0)
           (cons 91 0)
           (list 10 13.067336 0.51768)
           (cons 40 0)
           (cons 41 0)
           (cons 42 0)
           (cons 91 0)
           (list 10 12.262664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.1062 1.0731272)
           (cons 40 0)
           (cons 41 0)
           (cons 42 0)
           (cons 91 0)
           (list 10 12.1062 1.2474728)
           (cons 40 0)
           (cons 41 0)
           (cons 42 0)
           (cons 91 0)
           (list 10 12.262664 1.3)
           (cons 40 0)
           (cons 41 0)
           (cons 42 0)
           (cons 91 0)
           (list 10 13.067336 1.3)
           (cons 40 0)
           (cons 41 0)
           (cons 42 0)
           (cons 91 0)
           (list 10 13.2238 1.2474728)
           (cons 40 0)
           (cons 41 0)
           (cons 42 0)
           (cons 91 0)
           (list 10 13.2238 1.0731272)
           (cons 40 0)
           (cons 41 0)
           (cons 42 0)
           (cons 91 0)
           (list 10 13.067336 1.0206)
           (cons 40 0)
           (cons 41 0)
           (cons 42 0)
           (cons 91 0)
           (list 10 12.262664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.3762 -0.7445528)
           (cons 40 0)
           (cons 41 0)
           (cons 42 0)
           (cons 91 0)
           (list 10 13.3762 -0.5702072)
           (cons 40 0)
           (cons 41 0)
           (cons 42 0)
           (cons 91 0)
           (list 10 13.532664 -0.51768)
           (cons 40 0)
           (cons 41 0)
           (cons 42 0)
           (cons 91 0)
           (list 10 14.337336 -0.51768)
           (cons 40 0)
           (cons 41 0)
           (cons 42 0)
           (cons 91 0)
           (list 10 14.4938 -0.5702072)
           (cons 40 0)
           (cons 41 0)
           (cons 42 0)
           (cons 91 0)
           (list 10 14.4938 -0.7445528)
           (cons 40 0)
           (cons 41 0)
           (cons 42 0)
           (cons 91 0)
           (list 10 14.337336 -0.79708)
           (cons 40 0)
           (cons 41 0)
           (cons 42 0)
           (cons 91 0)
           (list 10 13.532664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.3762 -1.2474728)
           (cons 40 0)
           (cons 41 0)
           (cons 42 0)
           (cons 91 0)
           (list 10 13.3762 -1.0731272)
           (cons 40 0)
           (cons 41 0)
           (cons 42 0)
           (cons 91 0)
           (list 10 13.532664 -1.0206)
           (cons 40 0)
           (cons 41 0)
           (cons 42 0)
           (cons 91 0)
           (list 10 14.337336 -1.0206)
           (cons 40 0)
           (cons 41 0)
           (cons 42 0)
           (cons 91 0)
           (list 10 14.4938 -1.0731272)
           (cons 40 0)
           (cons 41 0)
           (cons 42 0)
           (cons 91 0)
           (list 10 14.4938 -1.2474728)
           (cons 40 0)
           (cons 41 0)
           (cons 42 0)
           (cons 91 0)
           (list 10 14.337336 -1.3)
           (cons 40 0)
           (cons 41 0)
           (cons 42 0)
           (cons 91 0)
           (list 10 13.532664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.3762 0.5702072)
           (cons 40 0)
           (cons 41 0)
           (cons 42 0)
           (cons 91 0)
           (list 10 13.3762 0.7445528)
           (cons 40 0)
           (cons 41 0)
           (cons 42 0)
           (cons 91 0)
           (list 10 13.532664 0.79708)
           (cons 40 0)
           (cons 41 0)
           (cons 42 0)
           (cons 91 0)
           (list 10 14.337336 0.79708)
           (cons 40 0)
           (cons 41 0)
           (cons 42 0)
           (cons 91 0)
           (list 10 14.4938 0.7445528)
           (cons 40 0)
           (cons 41 0)
           (cons 42 0)
           (cons 91 0)
           (list 10 14.4938 0.5702072)
           (cons 40 0)
           (cons 41 0)
           (cons 42 0)
           (cons 91 0)
           (list 10 14.337336 0.51768)
           (cons 40 0)
           (cons 41 0)
           (cons 42 0)
           (cons 91 0)
           (list 10 13.532664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.3762 1.0731272)
           (cons 40 0)
           (cons 41 0)
           (cons 42 0)
           (cons 91 0)
           (list 10 13.3762 1.2474728)
           (cons 40 0)
           (cons 41 0)
           (cons 42 0)
           (cons 91 0)
           (list 10 13.532664 1.3)
           (cons 40 0)
           (cons 41 0)
           (cons 42 0)
           (cons 91 0)
           (list 10 14.337336 1.3)
           (cons 40 0)
           (cons 41 0)
           (cons 42 0)
           (cons 91 0)
           (list 10 14.4938 1.2474728)
           (cons 40 0)
           (cons 41 0)
           (cons 42 0)
           (cons 91 0)
           (list 10 14.4938 1.0731272)
           (cons 40 0)
           (cons 41 0)
           (cons 42 0)
           (cons 91 0)
           (list 10 14.337336 1.0206)
           (cons 40 0)
           (cons 41 0)
           (cons 42 0)
           (cons 91 0)
           (list 10 13.532664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 1.3 0 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 15 1.3 0)
           (cons 50 0)
          )
         )
         (entmake
          (list
           (cons 0 "POINT")
           (cons 100 "AcDbEntity")
           (cons 67 0)
           (cons 8 "0")
           (cons 100 "AcDbPoint")
           (list 10 15 -1.3 0)
           (cons 50 0)
          )
         )
         (entmake
          (list
           (cons 0 "POINT")
           (cons 100 "AcDbEntity")
           (cons 67 0)
           (cons 8 "0")
           (cons 100 "AcDbPoint")
           (list 10 13.3 1.3 0)
           (cons 50 0)
          )
         )
         (entmake
          (list
           (cons 0 "POINT")
           (cons 100 "AcDbEntity")
           (cons 67 0)
           (cons 8 "0")
           (cons 100 "AcDbPoint")
           (list 10 13.3 -1.3 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 15 -1.3)
           (cons 40 0)
           (cons 41 0)
           (cons 42 0)
           (cons 91 0)
           (list 10 15 1.3)
           (cons 40 0)
           (cons 41 0)
           (cons 42 0)
           (cons 91 0)
           (list 10 0 1.3)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.6 0.56666667 0)
           (cons 40 0.2)
           (cons 1 "1.30")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 0.23333333 0)
           (cons 40 0.2)
           (cons 1 "1.30")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.1 0)
           (cons 40 0.2)
           (cons 1 "13.30")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.43333333 0)
           (cons 40 0.2)
           (cons 1 "0.00")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "TAC-1999-WB-19-TRUCK"))
        (progn
         (entmake)
         (entmake
          (list
           (cons 0 "BLOCK")
           (cons 2 "TAC-1999-WB-19-TRUCK")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.635 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.635 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 7 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 7.26263966 -0.26263966 0)
           (list 11 7.26263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.8062 -0.7445528)
           (cons 40 0)
           (cons 41 0)
           (cons 42 0)
           (cons 91 0)
           (list 10 5.8062 -0.5702072)
           (cons 40 0)
           (cons 41 0)
           (cons 42 0)
           (cons 91 0)
           (list 10 5.962664 -0.51768)
           (cons 40 0)
           (cons 41 0)
           (cons 42 0)
           (cons 91 0)
           (list 10 6.767336 -0.51768)
           (cons 40 0)
           (cons 41 0)
           (cons 42 0)
           (cons 91 0)
           (list 10 6.9238 -0.5702072)
           (cons 40 0)
           (cons 41 0)
           (cons 42 0)
           (cons 91 0)
           (list 10 6.9238 -0.7445528)
           (cons 40 0)
           (cons 41 0)
           (cons 42 0)
           (cons 91 0)
           (list 10 6.767336 -0.79708)
           (cons 40 0)
           (cons 41 0)
           (cons 42 0)
           (cons 91 0)
           (list 10 5.962664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.8062 -1.2474728)
           (cons 40 0)
           (cons 41 0)
           (cons 42 0)
           (cons 91 0)
           (list 10 5.8062 -1.0731272)
           (cons 40 0)
           (cons 41 0)
           (cons 42 0)
           (cons 91 0)
           (list 10 5.962664 -1.0206)
           (cons 40 0)
           (cons 41 0)
           (cons 42 0)
           (cons 91 0)
           (list 10 6.767336 -1.0206)
           (cons 40 0)
           (cons 41 0)
           (cons 42 0)
           (cons 91 0)
           (list 10 6.9238 -1.0731272)
           (cons 40 0)
           (cons 41 0)
           (cons 42 0)
           (cons 91 0)
           (list 10 6.9238 -1.2474728)
           (cons 40 0)
           (cons 41 0)
           (cons 42 0)
           (cons 91 0)
           (list 10 6.767336 -1.3)
           (cons 40 0)
           (cons 41 0)
           (cons 42 0)
           (cons 91 0)
           (list 10 5.962664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.8062 0.5702072)
           (cons 40 0)
           (cons 41 0)
           (cons 42 0)
           (cons 91 0)
           (list 10 5.8062 0.7445528)
           (cons 40 0)
           (cons 41 0)
           (cons 42 0)
           (cons 91 0)
           (list 10 5.962664 0.79708)
           (cons 40 0)
           (cons 41 0)
           (cons 42 0)
           (cons 91 0)
           (list 10 6.767336 0.79708)
           (cons 40 0)
           (cons 41 0)
           (cons 42 0)
           (cons 91 0)
           (list 10 6.9238 0.7445528)
           (cons 40 0)
           (cons 41 0)
           (cons 42 0)
           (cons 91 0)
           (list 10 6.9238 0.5702072)
           (cons 40 0)
           (cons 41 0)
           (cons 42 0)
           (cons 91 0)
           (list 10 6.767336 0.51768)
           (cons 40 0)
           (cons 41 0)
           (cons 42 0)
           (cons 91 0)
           (list 10 5.962664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.8062 1.0731272)
           (cons 40 0)
           (cons 41 0)
           (cons 42 0)
           (cons 91 0)
           (list 10 5.8062 1.2474728)
           (cons 40 0)
           (cons 41 0)
           (cons 42 0)
           (cons 91 0)
           (list 10 5.962664 1.3)
           (cons 40 0)
           (cons 41 0)
           (cons 42 0)
           (cons 91 0)
           (list 10 6.767336 1.3)
           (cons 40 0)
           (cons 41 0)
           (cons 42 0)
           (cons 91 0)
           (list 10 6.9238 1.2474728)
           (cons 40 0)
           (cons 41 0)
           (cons 42 0)
           (cons 91 0)
           (list 10 6.9238 1.0731272)
           (cons 40 0)
           (cons 41 0)
           (cons 42 0)
           (cons 91 0)
           (list 10 6.767336 1.0206)
           (cons 40 0)
           (cons 41 0)
           (cons 42 0)
           (cons 91 0)
           (list 10 5.962664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.0762 -0.7445528)
           (cons 40 0)
           (cons 41 0)
           (cons 42 0)
           (cons 91 0)
           (list 10 7.0762 -0.5702072)
           (cons 40 0)
           (cons 41 0)
           (cons 42 0)
           (cons 91 0)
           (list 10 7.232664 -0.51768)
           (cons 40 0)
           (cons 41 0)
           (cons 42 0)
           (cons 91 0)
           (list 10 8.037336 -0.51768)
           (cons 40 0)
           (cons 41 0)
           (cons 42 0)
           (cons 91 0)
           (list 10 8.1938 -0.5702072)
           (cons 40 0)
           (cons 41 0)
           (cons 42 0)
           (cons 91 0)
           (list 10 8.1938 -0.7445528)
           (cons 40 0)
           (cons 41 0)
           (cons 42 0)
           (cons 91 0)
           (list 10 8.037336 -0.79708)
           (cons 40 0)
           (cons 41 0)
           (cons 42 0)
           (cons 91 0)
           (list 10 7.232664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.0762 -1.2474728)
           (cons 40 0)
           (cons 41 0)
           (cons 42 0)
           (cons 91 0)
           (list 10 7.0762 -1.0731272)
           (cons 40 0)
           (cons 41 0)
           (cons 42 0)
           (cons 91 0)
           (list 10 7.232664 -1.0206)
           (cons 40 0)
           (cons 41 0)
           (cons 42 0)
           (cons 91 0)
           (list 10 8.037336 -1.0206)
           (cons 40 0)
           (cons 41 0)
           (cons 42 0)
           (cons 91 0)
           (list 10 8.1938 -1.0731272)
           (cons 40 0)
           (cons 41 0)
           (cons 42 0)
           (cons 91 0)
           (list 10 8.1938 -1.2474728)
           (cons 40 0)
           (cons 41 0)
           (cons 42 0)
           (cons 91 0)
           (list 10 8.037336 -1.3)
           (cons 40 0)
           (cons 41 0)
           (cons 42 0)
           (cons 91 0)
           (list 10 7.232664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.0762 0.5702072)
           (cons 40 0)
           (cons 41 0)
           (cons 42 0)
           (cons 91 0)
           (list 10 7.0762 0.7445528)
           (cons 40 0)
           (cons 41 0)
           (cons 42 0)
           (cons 91 0)
           (list 10 7.232664 0.79708)
           (cons 40 0)
           (cons 41 0)
           (cons 42 0)
           (cons 91 0)
           (list 10 8.037336 0.79708)
           (cons 40 0)
           (cons 41 0)
           (cons 42 0)
           (cons 91 0)
           (list 10 8.1938 0.7445528)
           (cons 40 0)
           (cons 41 0)
           (cons 42 0)
           (cons 91 0)
           (list 10 8.1938 0.5702072)
           (cons 40 0)
           (cons 41 0)
           (cons 42 0)
           (cons 91 0)
           (list 10 8.037336 0.51768)
           (cons 40 0)
           (cons 41 0)
           (cons 42 0)
           (cons 91 0)
           (list 10 7.232664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.0762 1.0731272)
           (cons 40 0)
           (cons 41 0)
           (cons 42 0)
           (cons 91 0)
           (list 10 7.0762 1.2474728)
           (cons 40 0)
           (cons 41 0)
           (cons 42 0)
           (cons 91 0)
           (list 10 7.232664 1.3)
           (cons 40 0)
           (cons 41 0)
           (cons 42 0)
           (cons 91 0)
           (list 10 8.037336 1.3)
           (cons 40 0)
           (cons 41 0)
           (cons 42 0)
           (cons 91 0)
           (list 10 8.1938 1.2474728)
           (cons 40 0)
           (cons 41 0)
           (cons 42 0)
           (cons 91 0)
           (list 10 8.1938 1.0731272)
           (cons 40 0)
           (cons 41 0)
           (cons 42 0)
           (cons 91 0)
           (list 10 8.037336 1.0206)
           (cons 40 0)
           (cons 41 0)
           (cons 42 0)
           (cons 91 0)
           (list 10 7.232664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 7 0 0)
           (cons 50 0)
          )
         )
         (entmake
          (list
           (cons 0 "POINT")
           (cons 100 "AcDbEntity")
           (cons 67 0)
           (cons 8 "0")
           (cons 100 "AcDbPoint")
           (list 10 0.8 -1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0.8 1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 7 1.3 0)
           (cons 50 0)
          )
         )
         (entmake
          (list
           (cons 0 "POINT")
           (cons 100 "AcDbEntity")
           (cons 67 0)
           (cons 8 "0")
           (cons 100 "AcDbPoint")
           (list 10 7 -1.3 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 7.635 -1.3)
           (cons 40 0)
           (cons 41 0)
           (cons 42 0)
           (cons 91 0)
           (list 10 7.635 1.3)
           (cons 40 0)
           (cons 41 0)
           (cons 42 0)
           (cons 91 0)
           (list 10 0 1.3)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0.8 0 0)
           (cons 50 0)
          )
         )
         (entmake
          (list
           (cons 0 "ATTDEF")
           (cons 100 "AcDbEntity")
           (cons 67 0)
           (cons 8 "0")
           (cons 100 "AcDbText")
           (list 10 0.1 0.56666667 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 0.23333333 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.1 0)
           (cons 40 0.2)
           (cons 1 "7.00")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.43333333 0)
           (cons 40 0.2)
           (cons 1 "7.00")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.76666667 0)
           (cons 40 0.2)
           (cons 1 "29.0")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelRightM1")
           (list 10 0.8 1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM1")
           (list 10 0.8 -1.0206 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "TAC-1999-P"))
        (progn
         (entmake)
         (entmake
          (list
           (cons 0 "BLOCK")
           (cons 2 "TAC-1999-P")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.6 -1 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.6 1 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.9571 -0.9677674)
           (cons 40 0)
           (cons 41 0)
           (cons 42 0)
           (cons 91 0)
           (list 10 3.9571 -0.8607826)
           (cons 40 0)
           (cons 41 0)
           (cons 42 0)
           (cons 91 0)
           (list 10 4.053112 -0.82855)
           (cons 40 0)
           (cons 41 0)
           (cons 42 0)
           (cons 91 0)
           (list 10 4.546888 -0.82855)
           (cons 40 0)
           (cons 41 0)
           (cons 42 0)
           (cons 91 0)
           (list 10 4.6429 -0.8607826)
           (cons 40 0)
           (cons 41 0)
           (cons 42 0)
           (cons 91 0)
           (list 10 4.6429 -0.9677674)
           (cons 40 0)
           (cons 41 0)
           (cons 42 0)
           (cons 91 0)
           (list 10 4.546888 -1)
           (cons 40 0)
           (cons 41 0)
           (cons 42 0)
           (cons 91 0)
           (list 10 4.053112 -1)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.9571 0.8607826)
           (cons 40 0)
           (cons 41 0)
           (cons 42 0)
           (cons 91 0)
           (list 10 3.9571 0.9677674)
           (cons 40 0)
           (cons 41 0)
           (cons 42 0)
           (cons 91 0)
           (list 10 4.053112 1)
           (cons 40 0)
           (cons 41 0)
           (cons 42 0)
           (cons 91 0)
           (list 10 4.546888 1)
           (cons 40 0)
           (cons 41 0)
           (cons 42 0)
           (cons 91 0)
           (list 10 4.6429 0.9677674)
           (cons 40 0)
           (cons 41 0)
           (cons 42 0)
           (cons 91 0)
           (list 10 4.6429 0.8607826)
           (cons 40 0)
           (cons 41 0)
           (cons 42 0)
           (cons 91 0)
           (list 10 4.546888 0.82855)
           (cons 40 0)
           (cons 41 0)
           (cons 42 0)
           (cons 91 0)
           (list 10 4.053112 0.82855)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 1 0)
           (cons 50 0)
          )
         )
         (entmake
          (list
           (cons 0 "POINT")
           (cons 100 "AcDbEntity")
           (cons 67 0)
           (cons 8 "0")
           (cons 100 "AcDbPoint")
           (list 10 1.1 1 0)
           (cons 50 0)
          )
         )
         (entmake
          (list
           (cons 0 "POINT")
           (cons 100 "AcDbEntity")
           (cons 67 0)
           (cons 8 "0")
           (cons 100 "AcDbPoint")
           (list 10 4.3 1 0)
           (cons 50 0)
          )
         )
         (entmake
          (list
           (cons 0 "POINT")
           (cons 100 "AcDbEntity")
           (cons 67 0)
           (cons 8 "0")
           (cons 100 "AcDbPoint")
           (list 10 5.6 1 0)
           (cons 50 0)
          )
         )
         (entmake
          (list
           (cons 0 "POINT")
           (cons 100 "AcDbEntity")
           (cons 67 0)
           (cons 8 "0")
           (cons 100 "AcDbPoint")
           (list 10 5.6 -1 0)
           (cons 50 0)
          )
         )
         (entmake
          (list
           (cons 0 "POINT")
           (cons 100 "AcDbEntity")
           (cons 67 0)
           (cons 8 "0")
           (cons 100 "AcDbPoint")
           (list 10 4.3 -1 0)
           (cons 50 0)
          )
         )
         (entmake
          (list
           (cons 0 "POINT")
           (cons 100 "AcDbEntity")
           (cons 67 0)
           (cons 8 "0")
           (cons 100 "AcDbPoint")
           (list 10 1.1 -1 0)
           (cons 50 0)
          )
         )
         (entmake
          (list
           (cons 0 "POINT")
           (cons 100 "AcDbEntity")
           (cons 67 0)
           (cons 8 "0")
           (cons 100 "AcDbPoint")
           (list 10 0 -1 0)
           (cons 50 0)
          )
         )
         (entmake
          (list
           (cons 0 "POINT")
           (cons 100 "AcDbEntity")
           (cons 67 0)
           (cons 8 "0")
           (cons 100 "AcDbPoint")
           (list 10 1.1 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1)
           (cons 40 0)
           (cons 41 0)
           (cons 42 0)
           (cons 91 0)
           (list 10 5.6 -1)
           (cons 40 0)
           (cons 41 0)
           (cons 42 0)
           (cons 91 0)
           (list 10 5.6 1)
           (cons 40 0)
           (cons 41 0)
           (cons 42 0)
           (cons 91 0)
           (list 10 0 1)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.4 0.56666667 0)
           (cons 40 0.2)
           (cons 1 "1.10")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.4 0.23333333 0)
           (cons 40 0.2)
           (cons 1 "1.10")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.4 -0.1 0)
           (cons 40 0.2)
           (cons 1 "4.30")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.4 -0.43333333 0)
           (cons 40 0.2)
           (cons 1 "0.00")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.4 -0.76666667 0)
           (cons 40 0.2)
           (cons 1 "36.2")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelLeftM3")
           (list 10 1.1 -0.82855 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM3")
           (list 10 1.1 0.82855 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "TAC-1999-MSU"))
        (progn
         (entmake)
         (entmake
          (list
           (cons 0 "BLOCK")
           (cons 2 "TAC-1999-MSU")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 10 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 10 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.792 -0.795048)
           (cons 40 0)
           (cons 41 0)
           (cons 42 0)
           (cons 91 0)
           (list 10 6.792 -0.636552)
           (cons 40 0)
           (cons 41 0)
           (cons 42 0)
           (cons 91 0)
           (list 10 6.93424 -0.5888)
           (cons 40 0)
           (cons 41 0)
           (cons 42 0)
           (cons 91 0)
           (list 10 7.66576 -0.5888)
           (cons 40 0)
           (cons 41 0)
           (cons 42 0)
           (cons 91 0)
           (list 10 7.808 -0.636552)
           (cons 40 0)
           (cons 41 0)
           (cons 42 0)
           (cons 91 0)
           (list 10 7.808 -0.795048)
           (cons 40 0)
           (cons 41 0)
           (cons 42 0)
           (cons 91 0)
           (list 10 7.66576 -0.8428)
           (cons 40 0)
           (cons 41 0)
           (cons 42 0)
           (cons 91 0)
           (list 10 6.93424 -0.8428)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.792 -1.252248)
           (cons 40 0)
           (cons 41 0)
           (cons 42 0)
           (cons 91 0)
           (list 10 6.792 -1.093752)
           (cons 40 0)
           (cons 41 0)
           (cons 42 0)
           (cons 91 0)
           (list 10 6.93424 -1.046)
           (cons 40 0)
           (cons 41 0)
           (cons 42 0)
           (cons 91 0)
           (list 10 7.66576 -1.046)
           (cons 40 0)
           (cons 41 0)
           (cons 42 0)
           (cons 91 0)
           (list 10 7.808 -1.093752)
           (cons 40 0)
           (cons 41 0)
           (cons 42 0)
           (cons 91 0)
           (list 10 7.808 -1.252248)
           (cons 40 0)
           (cons 41 0)
           (cons 42 0)
           (cons 91 0)
           (list 10 7.66576 -1.3)
           (cons 40 0)
           (cons 41 0)
           (cons 42 0)
           (cons 91 0)
           (list 10 6.93424 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.792 0.636552)
           (cons 40 0)
           (cons 41 0)
           (cons 42 0)
           (cons 91 0)
           (list 10 6.792 0.795048)
           (cons 40 0)
           (cons 41 0)
           (cons 42 0)
           (cons 91 0)
           (list 10 6.93424 0.8428)
           (cons 40 0)
           (cons 41 0)
           (cons 42 0)
           (cons 91 0)
           (list 10 7.66576 0.8428)
           (cons 40 0)
           (cons 41 0)
           (cons 42 0)
           (cons 91 0)
           (list 10 7.808 0.795048)
           (cons 40 0)
           (cons 41 0)
           (cons 42 0)
           (cons 91 0)
           (list 10 7.808 0.636552)
           (cons 40 0)
           (cons 41 0)
           (cons 42 0)
           (cons 91 0)
           (list 10 7.66576 0.5888)
           (cons 40 0)
           (cons 41 0)
           (cons 42 0)
           (cons 91 0)
           (list 10 6.93424 0.5888)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.792 1.093752)
           (cons 40 0)
           (cons 41 0)
           (cons 42 0)
           (cons 91 0)
           (list 10 6.792 1.252248)
           (cons 40 0)
           (cons 41 0)
           (cons 42 0)
           (cons 91 0)
           (list 10 6.93424 1.3)
           (cons 40 0)
           (cons 41 0)
           (cons 42 0)
           (cons 91 0)
           (list 10 7.66576 1.3)
           (cons 40 0)
           (cons 41 0)
           (cons 42 0)
           (cons 91 0)
           (list 10 7.808 1.252248)
           (cons 40 0)
           (cons 41 0)
           (cons 42 0)
           (cons 91 0)
           (list 10 7.808 1.093752)
           (cons 40 0)
           (cons 41 0)
           (cons 42 0)
           (cons 91 0)
           (list 10 7.66576 1.046)
           (cons 40 0)
           (cons 41 0)
           (cons 42 0)
           (cons 91 0)
           (list 10 6.93424 1.046)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0.8 -1.3 0)
           (cons 50 0)
          )
         )
         (entmake
          (list
           (cons 0 "POINT")
           (cons 100 "AcDbEntity")
           (cons 67 0)
           (cons 8 "0")
           (cons 100 "AcDbPoint")
           (list 10 7.3 -1.3 0)
           (cons 50 0)
          )
         )
         (entmake
          (list
           (cons 0 "POINT")
           (cons 100 "AcDbEntity")
           (cons 67 0)
           (cons 8 "0")
           (cons 100 "AcDbPoint")
           (list 10 10 -1.3 0)
           (cons 50 0)
          )
         )
         (entmake
          (list
           (cons 0 "POINT")
           (cons 100 "AcDbEntity")
           (cons 67 0)
           (cons 8 "0")
           (cons 100 "AcDbPoint")
           (list 10 10 1.3 0)
           (cons 50 0)
          )
         )
         (entmake
          (list
           (cons 0 "POINT")
           (cons 100 "AcDbEntity")
           (cons 67 0)
           (cons 8 "0")
           (cons 100 "AcDbPoint")
           (list 10 7.3 1.3 0)
           (cons 50 0)
          )
         )
         (entmake
          (list
           (cons 0 "POINT")
           (cons 100 "AcDbEntity")
           (cons 67 0)
           (cons 8 "0")
           (cons 100 "AcDbPoint")
           (list 10 0.8 1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0.8 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 10 -1.3)
           (cons 40 0)
           (cons 41 0)
           (cons 42 0)
           (cons 91 0)
           (list 10 10 1.3)
           (cons 40 0)
           (cons 41 0)
           (cons 42 0)
           (cons 91 0)
           (list 10 0 1.3)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.1 0.56666667 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 0.23333333 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.1 0)
           (cons 40 0.2)
           (cons 1 "7.30")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.43333333 0)
           (cons 40 0.2)
           (cons 1 "0.00")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.76666667 0)
           (cons 40 0.2)
           (cons 1 "40.1")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelRightM2")
           (list 10 0.8 1.046 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM2")
           (list 10 0.8 -1.046 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "TAC-1999-LSU"))
        (progn
         (entmake)
         (entmake
          (list
           (cons 0 "BLOCK")
           (cons 2 "TAC-1999-LSU")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.4 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.4 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.692 -1.252248)
           (cons 40 0)
           (cons 41 0)
           (cons 42 0)
           (cons 91 0)
           (list 10 3.692 -1.093752)
           (cons 40 0)
           (cons 41 0)
           (cons 42 0)
           (cons 91 0)
           (list 10 3.83424 -1.046)
           (cons 40 0)
           (cons 41 0)
           (cons 42 0)
           (cons 91 0)
           (list 10 4.56576 -1.046)
           (cons 40 0)
           (cons 41 0)
           (cons 42 0)
           (cons 91 0)
           (list 10 4.708 -1.093752)
           (cons 40 0)
           (cons 41 0)
           (cons 42 0)
           (cons 91 0)
           (list 10 4.708 -1.252248)
           (cons 40 0)
           (cons 41 0)
           (cons 42 0)
           (cons 91 0)
           (list 10 4.56576 -1.3)
           (cons 40 0)
           (cons 41 0)
           (cons 42 0)
           (cons 91 0)
           (list 10 3.83424 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.692 1.093752)
           (cons 40 0)
           (cons 41 0)
           (cons 42 0)
           (cons 91 0)
           (list 10 3.692 1.252248)
           (cons 40 0)
           (cons 41 0)
           (cons 42 0)
           (cons 91 0)
           (list 10 3.83424 1.3)
           (cons 40 0)
           (cons 41 0)
           (cons 42 0)
           (cons 91 0)
           (list 10 4.56576 1.3)
           (cons 40 0)
           (cons 41 0)
           (cons 42 0)
           (cons 91 0)
           (list 10 4.708 1.252248)
           (cons 40 0)
           (cons 41 0)
           (cons 42 0)
           (cons 91 0)
           (list 10 4.708 1.093752)
           (cons 40 0)
           (cons 41 0)
           (cons 42 0)
           (cons 91 0)
           (list 10 4.56576 1.046)
           (cons 40 0)
           (cons 41 0)
           (cons 42 0)
           (cons 91 0)
           (list 10 3.83424 1.046)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0.8 -1.3 0)
           (cons 50 0)
          )
         )
         (entmake
          (list
           (cons 0 "POINT")
           (cons 100 "AcDbEntity")
           (cons 67 0)
           (cons 8 "0")
           (cons 100 "AcDbPoint")
           (list 10 4.2 -1.3 0)
           (cons 50 0)
          )
         )
         (entmake
          (list
           (cons 0 "POINT")
           (cons 100 "AcDbEntity")
           (cons 67 0)
           (cons 8 "0")
           (cons 100 "AcDbPoint")
           (list 10 6.4 -1.3 0)
           (cons 50 0)
          )
         )
         (entmake
          (list
           (cons 0 "POINT")
           (cons 100 "AcDbEntity")
           (cons 67 0)
           (cons 8 "0")
           (cons 100 "AcDbPoint")
           (list 10 6.4 1.3 0)
           (cons 50 0)
          )
         )
         (entmake
          (list
           (cons 0 "POINT")
           (cons 100 "AcDbEntity")
           (cons 67 0)
           (cons 8 "0")
           (cons 100 "AcDbPoint")
           (list 10 4.2 1.3 0)
           (cons 50 0)
          )
         )
         (entmake
          (list
           (cons 0 "POINT")
           (cons 100 "AcDbEntity")
           (cons 67 0)
           (cons 8 "0")
           (cons 100 "AcDbPoint")
           (list 10 0.8 1.3 0)
           (cons 50 0)
          )
         )
         (entmake
          (list
           (cons 0 "POINT")
           (cons 100 "AcDbEntity")
           (cons 67 0)
           (cons 8 "0")
           (cons 100 "AcDbPoint")
           (list 10 0.8 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 6.4 -1.3)
           (cons 40 0)
           (cons 41 0)
           (cons 42 0)
           (cons 91 0)
           (list 10 6.4 1.3)
           (cons 40 0)
           (cons 41 0)
           (cons 42 0)
           (cons 91 0)
           (list 10 0 1.3)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.1 0.56666667 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 0.23333333 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.1 0)
           (cons 40 0.2)
           (cons 1 "4.20")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.43333333 0)
           (cons 40 0.2)
           (cons 1 "0.00")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.76666667 0)
           (cons 40 0.2)
           (cons 1 "40.8")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelLeftM2")
           (list 10 0.8 -1.046 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM2")
           (list 10 0.8 1.046 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "TAC-1999-I-BUS"))
        (progn
         (entmake)
         (entmake
          (list
           (cons 0 "BLOCK")
           (cons 2 "TAC-1999-I-BUS")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 14 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 14 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.492 -1.152248)
           (cons 40 0)
           (cons 41 0)
           (cons 42 0)
           (cons 91 0)
           (list 10 9.492 -0.993752)
           (cons 40 0)
           (cons 41 0)
           (cons 42 0)
           (cons 91 0)
           (list 10 9.63424 -0.946)
           (cons 40 0)
           (cons 41 0)
           (cons 42 0)
           (cons 91 0)
           (list 10 10.36576 -0.946)
           (cons 40 0)
           (cons 41 0)
           (cons 42 0)
           (cons 91 0)
           (list 10 10.508 -0.993752)
           (cons 40 0)
           (cons 41 0)
           (cons 42 0)
           (cons 91 0)
           (list 10 10.508 -1.152248)
           (cons 40 0)
           (cons 41 0)
           (cons 42 0)
           (cons 91 0)
           (list 10 10.36576 -1.2)
           (cons 40 0)
           (cons 41 0)
           (cons 42 0)
           (cons 91 0)
           (list 10 9.63424 -1.2)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.492 0.993752)
           (cons 40 0)
           (cons 41 0)
           (cons 42 0)
           (cons 91 0)
           (list 10 9.492 1.152248)
           (cons 40 0)
           (cons 41 0)
           (cons 42 0)
           (cons 91 0)
           (list 10 9.63424 1.2)
           (cons 40 0)
           (cons 41 0)
           (cons 42 0)
           (cons 91 0)
           (list 10 10.36576 1.2)
           (cons 40 0)
           (cons 41 0)
           (cons 42 0)
           (cons 91 0)
           (list 10 10.508 1.152248)
           (cons 40 0)
           (cons 41 0)
           (cons 42 0)
           (cons 91 0)
           (list 10 10.508 0.993752)
           (cons 40 0)
           (cons 41 0)
           (cons 42 0)
           (cons 91 0)
           (list 10 10.36576 0.946)
           (cons 40 0)
           (cons 41 0)
           (cons 42 0)
           (cons 91 0)
           (list 10 9.63424 0.946)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -1.2 0)
           (cons 50 0)
          )
         )
         (entmake
          (list
           (cons 0 "POINT")
           (cons 100 "AcDbEntity")
           (cons 67 0)
           (cons 8 "0")
           (cons 100 "AcDbPoint")
           (list 10 0 1.2 0)
           (cons 50 0)
          )
         )
         (entmake
          (list
           (cons 0 "POINT")
           (cons 100 "AcDbEntity")
           (cons 67 0)
           (cons 8 "0")
           (cons 100 "AcDbPoint")
           (list 10 14 1.2 0)
           (cons 50 0)
          )
         )
         (entmake
          (list
           (cons 0 "POINT")
           (cons 100 "AcDbEntity")
           (cons 67 0)
           (cons 8 "0")
           (cons 100 "AcDbPoint")
           (list 10 14 -1.2 0)
           (cons 50 0)
          )
         )
         (entmake
          (list
           (cons 0 "POINT")
           (cons 100 "AcDbEntity")
           (cons 67 0)
           (cons 8 "0")
           (cons 100 "AcDbPoint")
           (list 10 1.8 -1.2 0)
           (cons 50 0)
          )
         )
         (entmake
          (list
           (cons 0 "POINT")
           (cons 100 "AcDbEntity")
           (cons 67 0)
           (cons 8 "0")
           (cons 100 "AcDbPoint")
           (list 10 1.8 1.2 0)
           (cons 50 0)
          )
         )
         (entmake
          (list
           (cons 0 "POINT")
           (cons 100 "AcDbEntity")
           (cons 67 0)
           (cons 8 "0")
           (cons 100 "AcDbPoint")
           (list 10 10 1.2 0)
           (cons 50 0)
          )
         )
         (entmake
          (list
           (cons 0 "POINT")
           (cons 100 "AcDbEntity")
           (cons 67 0)
           (cons 8 "0")
           (cons 100 "AcDbPoint")
           (list 10 10 -1.2 0)
           (cons 50 0)
          )
         )
         (entmake
          (list
           (cons 0 "POINT")
           (cons 100 "AcDbEntity")
           (cons 67 0)
           (cons 8 "0")
           (cons 100 "AcDbPoint")
           (list 10 1.8 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.2)
           (cons 40 0)
           (cons 41 0)
           (cons 42 0)
           (cons 91 0)
           (list 10 14 -1.2)
           (cons 40 0)
           (cons 41 0)
           (cons 42 0)
           (cons 91 0)
           (list 10 14 1.2)
           (cons 40 0)
           (cons 41 0)
           (cons 42 0)
           (cons 91 0)
           (list 10 0 1.2)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 1.1 0.56666667 0)
           (cons 40 0.2)
           (cons 1 "1.80")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.1 0.23333333 0)
           (cons 40 0.2)
           (cons 1 "1.80")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.1 -0.1 0)
           (cons 40 0.2)
           (cons 1 "10.00")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.1 -0.43333333 0)
           (cons 40 0.2)
           (cons 1 "0.00")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.1 -0.76666667 0)
           (cons 40 0.2)
           (cons 1 "39.1")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelRightM2")
           (list 10 1.8 0.946 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM2")
           (list 10 1.8 -0.946 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "TAC-1999-HSU"))
        (progn
         (entmake)
         (entmake
          (list
           (cons 0 "BLOCK")
           (cons 2 "TAC-1999-HSU")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 11.5 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 11.5 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.057 -0.795048)
           (cons 40 0)
           (cons 41 0)
           (cons 42 0)
           (cons 91 0)
           (list 10 8.057 -0.636552)
           (cons 40 0)
           (cons 41 0)
           (cons 42 0)
           (cons 91 0)
           (list 10 8.19924 -0.5888)
           (cons 40 0)
           (cons 41 0)
           (cons 42 0)
           (cons 91 0)
           (list 10 8.93076 -0.5888)
           (cons 40 0)
           (cons 41 0)
           (cons 42 0)
           (cons 91 0)
           (list 10 9.073 -0.636552)
           (cons 40 0)
           (cons 41 0)
           (cons 42 0)
           (cons 91 0)
           (list 10 9.073 -0.795048)
           (cons 40 0)
           (cons 41 0)
           (cons 42 0)
           (cons 91 0)
           (list 10 8.93076 -0.8428)
           (cons 40 0)
           (cons 41 0)
           (cons 42 0)
           (cons 91 0)
           (list 10 8.19924 -0.8428)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.057 -1.252248)
           (cons 40 0)
           (cons 41 0)
           (cons 42 0)
           (cons 91 0)
           (list 10 8.057 -1.093752)
           (cons 40 0)
           (cons 41 0)
           (cons 42 0)
           (cons 91 0)
           (list 10 8.19924 -1.046)
           (cons 40 0)
           (cons 41 0)
           (cons 42 0)
           (cons 91 0)
           (list 10 8.93076 -1.046)
           (cons 40 0)
           (cons 41 0)
           (cons 42 0)
           (cons 91 0)
           (list 10 9.073 -1.093752)
           (cons 40 0)
           (cons 41 0)
           (cons 42 0)
           (cons 91 0)
           (list 10 9.073 -1.252248)
           (cons 40 0)
           (cons 41 0)
           (cons 42 0)
           (cons 91 0)
           (list 10 8.93076 -1.3)
           (cons 40 0)
           (cons 41 0)
           (cons 42 0)
           (cons 91 0)
           (list 10 8.19924 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.057 0.636552)
           (cons 40 0)
           (cons 41 0)
           (cons 42 0)
           (cons 91 0)
           (list 10 8.057 0.795048)
           (cons 40 0)
           (cons 41 0)
           (cons 42 0)
           (cons 91 0)
           (list 10 8.19924 0.8428)
           (cons 40 0)
           (cons 41 0)
           (cons 42 0)
           (cons 91 0)
           (list 10 8.93076 0.8428)
           (cons 40 0)
           (cons 41 0)
           (cons 42 0)
           (cons 91 0)
           (list 10 9.073 0.795048)
           (cons 40 0)
           (cons 41 0)
           (cons 42 0)
           (cons 91 0)
           (list 10 9.073 0.636552)
           (cons 40 0)
           (cons 41 0)
           (cons 42 0)
           (cons 91 0)
           (list 10 8.93076 0.5888)
           (cons 40 0)
           (cons 41 0)
           (cons 42 0)
           (cons 91 0)
           (list 10 8.19924 0.5888)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.057 1.093752)
           (cons 40 0)
           (cons 41 0)
           (cons 42 0)
           (cons 91 0)
           (list 10 8.057 1.252248)
           (cons 40 0)
           (cons 41 0)
           (cons 42 0)
           (cons 91 0)
           (list 10 8.19924 1.3)
           (cons 40 0)
           (cons 41 0)
           (cons 42 0)
           (cons 91 0)
           (list 10 8.93076 1.3)
           (cons 40 0)
           (cons 41 0)
           (cons 42 0)
           (cons 91 0)
           (list 10 9.073 1.252248)
           (cons 40 0)
           (cons 41 0)
           (cons 42 0)
           (cons 91 0)
           (list 10 9.073 1.093752)
           (cons 40 0)
           (cons 41 0)
           (cons 42 0)
           (cons 91 0)
           (list 10 8.93076 1.046)
           (cons 40 0)
           (cons 41 0)
           (cons 42 0)
           (cons 91 0)
           (list 10 8.19924 1.046)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.327 -0.795048)
           (cons 40 0)
           (cons 41 0)
           (cons 42 0)
           (cons 91 0)
           (list 10 9.327 -0.636552)
           (cons 40 0)
           (cons 41 0)
           (cons 42 0)
           (cons 91 0)
           (list 10 9.46924 -0.5888)
           (cons 40 0)
           (cons 41 0)
           (cons 42 0)
           (cons 91 0)
           (list 10 10.20076 -0.5888)
           (cons 40 0)
           (cons 41 0)
           (cons 42 0)
           (cons 91 0)
           (list 10 10.343 -0.636552)
           (cons 40 0)
           (cons 41 0)
           (cons 42 0)
           (cons 91 0)
           (list 10 10.343 -0.795048)
           (cons 40 0)
           (cons 41 0)
           (cons 42 0)
           (cons 91 0)
           (list 10 10.20076 -0.8428)
           (cons 40 0)
           (cons 41 0)
           (cons 42 0)
           (cons 91 0)
           (list 10 9.46924 -0.8428)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.327 -1.252248)
           (cons 40 0)
           (cons 41 0)
           (cons 42 0)
           (cons 91 0)
           (list 10 9.327 -1.093752)
           (cons 40 0)
           (cons 41 0)
           (cons 42 0)
           (cons 91 0)
           (list 10 9.46924 -1.046)
           (cons 40 0)
           (cons 41 0)
           (cons 42 0)
           (cons 91 0)
           (list 10 10.20076 -1.046)
           (cons 40 0)
           (cons 41 0)
           (cons 42 0)
           (cons 91 0)
           (list 10 10.343 -1.093752)
           (cons 40 0)
           (cons 41 0)
           (cons 42 0)
           (cons 91 0)
           (list 10 10.343 -1.252248)
           (cons 40 0)
           (cons 41 0)
           (cons 42 0)
           (cons 91 0)
           (list 10 10.20076 -1.3)
           (cons 40 0)
           (cons 41 0)
           (cons 42 0)
           (cons 91 0)
           (list 10 9.46924 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.327 0.636552)
           (cons 40 0)
           (cons 41 0)
           (cons 42 0)
           (cons 91 0)
           (list 10 9.327 0.795048)
           (cons 40 0)
           (cons 41 0)
           (cons 42 0)
           (cons 91 0)
           (list 10 9.46924 0.8428)
           (cons 40 0)
           (cons 41 0)
           (cons 42 0)
           (cons 91 0)
           (list 10 10.20076 0.8428)
           (cons 40 0)
           (cons 41 0)
           (cons 42 0)
           (cons 91 0)
           (list 10 10.343 0.795048)
           (cons 40 0)
           (cons 41 0)
           (cons 42 0)
           (cons 91 0)
           (list 10 10.343 0.636552)
           (cons 40 0)
           (cons 41 0)
           (cons 42 0)
           (cons 91 0)
           (list 10 10.20076 0.5888)
           (cons 40 0)
           (cons 41 0)
           (cons 42 0)
           (cons 91 0)
           (list 10 9.46924 0.5888)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.327 1.093752)
           (cons 40 0)
           (cons 41 0)
           (cons 42 0)
           (cons 91 0)
           (list 10 9.327 1.252248)
           (cons 40 0)
           (cons 41 0)
           (cons 42 0)
           (cons 91 0)
           (list 10 9.46924 1.3)
           (cons 40 0)
           (cons 41 0)
           (cons 42 0)
           (cons 91 0)
           (list 10 10.20076 1.3)
           (cons 40 0)
           (cons 41 0)
           (cons 42 0)
           (cons 91 0)
           (list 10 10.343 1.252248)
           (cons 40 0)
           (cons 41 0)
           (cons 42 0)
           (cons 91 0)
           (list 10 10.343 1.093752)
           (cons 40 0)
           (cons 41 0)
           (cons 42 0)
           (cons 91 0)
           (list 10 10.20076 1.046)
           (cons 40 0)
           (cons 41 0)
           (cons 42 0)
           (cons 91 0)
           (list 10 9.46924 1.046)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 11.5 1.3 0)
           (cons 50 0)
          )
         )
         (entmake
          (list
           (cons 0 "POINT")
           (cons 100 "AcDbEntity")
           (cons 67 0)
           (cons 8 "0")
           (cons 100 "AcDbPoint")
           (list 10 11.5 -1.3 0)
           (cons 50 0)
          )
         )
         (entmake
          (list
           (cons 0 "POINT")
           (cons 100 "AcDbEntity")
           (cons 67 0)
           (cons 8 "0")
           (cons 100 "AcDbPoint")
           (list 10 0.8 -1.3 0)
           (cons 50 0)
          )
         )
         (entmake
          (list
           (cons 0 "POINT")
           (cons 100 "AcDbEntity")
           (cons 67 0)
           (cons 8 "0")
           (cons 100 "AcDbPoint")
           (list 10 0.8 1.3 0)
           (cons 50 0)
          )
         )
         (entmake
          (list
           (cons 0 "POINT")
           (cons 100 "AcDbEntity")
           (cons 67 0)
           (cons 8 "0")
           (cons 100 "AcDbPoint")
           (list 10 0.8 0 0)
           (cons 50 0)
          )
         )
         (entmake
          (list
           (cons 0 "POINT")
           (cons 100 "AcDbEntity")
           (cons 67 0)
           (cons 8 "0")
           (cons 100 "AcDbPoint")
           (list 10 9.2 1.3 0)
           (cons 50 0)
          )
         )
         (entmake
          (list
           (cons 0 "POINT")
           (cons 100 "AcDbEntity")
           (cons 67 0)
           (cons 8 "0")
           (cons 100 "AcDbPoint")
           (list 10 9.2 -1.3 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 11.5 -1.3)
           (cons 40 0)
           (cons 41 0)
           (cons 42 0)
           (cons 91 0)
           (list 10 11.5 1.3)
           (cons 40 0)
           (cons 41 0)
           (cons 42 0)
           (cons 91 0)
           (list 10 0 1.3)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.1 0.56666667 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 0.23333333 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.1 0)
           (cons 40 0.2)
           (cons 1 "9.20")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.43333333 0)
           (cons 40 0.2)
           (cons 1 "0.00")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.76666667 0)
           (cons 40 0.2)
           (cons 1 "39.7")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelLeftM2")
           (list 10 0.8 -1.046 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM2")
           (list 10 0.8 1.046 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "TAC-1999-BTD-TRAILER2"))
        (progn
         (entmake)
         (entmake
          (list
           (cons 0 "BLOCK")
           (cons 2 "TAC-1999-BTD-TRAILER2")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.6 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.6 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 1.3 0 0)
           (cons 40 0.104)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1062 -0.7445528)
           (cons 40 0)
           (cons 41 0)
           (cons 42 0)
           (cons 91 0)
           (list 10 7.1062 -0.5702072)
           (cons 40 0)
           (cons 41 0)
           (cons 42 0)
           (cons 91 0)
           (list 10 7.262664 -0.51768)
           (cons 40 0)
           (cons 41 0)
           (cons 42 0)
           (cons 91 0)
           (list 10 8.067336 -0.51768)
           (cons 40 0)
           (cons 41 0)
           (cons 42 0)
           (cons 91 0)
           (list 10 8.2238 -0.5702072)
           (cons 40 0)
           (cons 41 0)
           (cons 42 0)
           (cons 91 0)
           (list 10 8.2238 -0.7445528)
           (cons 40 0)
           (cons 41 0)
           (cons 42 0)
           (cons 91 0)
           (list 10 8.067336 -0.79708)
           (cons 40 0)
           (cons 41 0)
           (cons 42 0)
           (cons 91 0)
           (list 10 7.262664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1062 -1.2474728)
           (cons 40 0)
           (cons 41 0)
           (cons 42 0)
           (cons 91 0)
           (list 10 7.1062 -1.0731272)
           (cons 40 0)
           (cons 41 0)
           (cons 42 0)
           (cons 91 0)
           (list 10 7.262664 -1.0206)
           (cons 40 0)
           (cons 41 0)
           (cons 42 0)
           (cons 91 0)
           (list 10 8.067336 -1.0206)
           (cons 40 0)
           (cons 41 0)
           (cons 42 0)
           (cons 91 0)
           (list 10 8.2238 -1.0731272)
           (cons 40 0)
           (cons 41 0)
           (cons 42 0)
           (cons 91 0)
           (list 10 8.2238 -1.2474728)
           (cons 40 0)
           (cons 41 0)
           (cons 42 0)
           (cons 91 0)
           (list 10 8.067336 -1.3)
           (cons 40 0)
           (cons 41 0)
           (cons 42 0)
           (cons 91 0)
           (list 10 7.262664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1062 0.5702072)
           (cons 40 0)
           (cons 41 0)
           (cons 42 0)
           (cons 91 0)
           (list 10 7.1062 0.7445528)
           (cons 40 0)
           (cons 41 0)
           (cons 42 0)
           (cons 91 0)
           (list 10 7.262664 0.79708)
           (cons 40 0)
           (cons 41 0)
           (cons 42 0)
           (cons 91 0)
           (list 10 8.067336 0.79708)
           (cons 40 0)
           (cons 41 0)
           (cons 42 0)
           (cons 91 0)
           (list 10 8.2238 0.7445528)
           (cons 40 0)
           (cons 41 0)
           (cons 42 0)
           (cons 91 0)
           (list 10 8.2238 0.5702072)
           (cons 40 0)
           (cons 41 0)
           (cons 42 0)
           (cons 91 0)
           (list 10 8.067336 0.51768)
           (cons 40 0)
           (cons 41 0)
           (cons 42 0)
           (cons 91 0)
           (list 10 7.262664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1062 1.0731272)
           (cons 40 0)
           (cons 41 0)
           (cons 42 0)
           (cons 91 0)
           (list 10 7.1062 1.2474728)
           (cons 40 0)
           (cons 41 0)
           (cons 42 0)
           (cons 91 0)
           (list 10 7.262664 1.3)
           (cons 40 0)
           (cons 41 0)
           (cons 42 0)
           (cons 91 0)
           (list 10 8.067336 1.3)
           (cons 40 0)
           (cons 41 0)
           (cons 42 0)
           (cons 91 0)
           (list 10 8.2238 1.2474728)
           (cons 40 0)
           (cons 41 0)
           (cons 42 0)
           (cons 91 0)
           (list 10 8.2238 1.0731272)
           (cons 40 0)
           (cons 41 0)
           (cons 42 0)
           (cons 91 0)
           (list 10 8.067336 1.0206)
           (cons 40 0)
           (cons 41 0)
           (cons 42 0)
           (cons 91 0)
           (list 10 7.262664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.3762 -0.7445528)
           (cons 40 0)
           (cons 41 0)
           (cons 42 0)
           (cons 91 0)
           (list 10 8.3762 -0.5702072)
           (cons 40 0)
           (cons 41 0)
           (cons 42 0)
           (cons 91 0)
           (list 10 8.532664 -0.51768)
           (cons 40 0)
           (cons 41 0)
           (cons 42 0)
           (cons 91 0)
           (list 10 9.337336 -0.51768)
           (cons 40 0)
           (cons 41 0)
           (cons 42 0)
           (cons 91 0)
           (list 10 9.4938 -0.5702072)
           (cons 40 0)
           (cons 41 0)
           (cons 42 0)
           (cons 91 0)
           (list 10 9.4938 -0.7445528)
           (cons 40 0)
           (cons 41 0)
           (cons 42 0)
           (cons 91 0)
           (list 10 9.337336 -0.79708)
           (cons 40 0)
           (cons 41 0)
           (cons 42 0)
           (cons 91 0)
           (list 10 8.532664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.3762 -1.2474728)
           (cons 40 0)
           (cons 41 0)
           (cons 42 0)
           (cons 91 0)
           (list 10 8.3762 -1.0731272)
           (cons 40 0)
           (cons 41 0)
           (cons 42 0)
           (cons 91 0)
           (list 10 8.532664 -1.0206)
           (cons 40 0)
           (cons 41 0)
           (cons 42 0)
           (cons 91 0)
           (list 10 9.337336 -1.0206)
           (cons 40 0)
           (cons 41 0)
           (cons 42 0)
           (cons 91 0)
           (list 10 9.4938 -1.0731272)
           (cons 40 0)
           (cons 41 0)
           (cons 42 0)
           (cons 91 0)
           (list 10 9.4938 -1.2474728)
           (cons 40 0)
           (cons 41 0)
           (cons 42 0)
           (cons 91 0)
           (list 10 9.337336 -1.3)
           (cons 40 0)
           (cons 41 0)
           (cons 42 0)
           (cons 91 0)
           (list 10 8.532664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.3762 0.5702072)
           (cons 40 0)
           (cons 41 0)
           (cons 42 0)
           (cons 91 0)
           (list 10 8.3762 0.7445528)
           (cons 40 0)
           (cons 41 0)
           (cons 42 0)
           (cons 91 0)
           (list 10 8.532664 0.79708)
           (cons 40 0)
           (cons 41 0)
           (cons 42 0)
           (cons 91 0)
           (list 10 9.337336 0.79708)
           (cons 40 0)
           (cons 41 0)
           (cons 42 0)
           (cons 91 0)
           (list 10 9.4938 0.7445528)
           (cons 40 0)
           (cons 41 0)
           (cons 42 0)
           (cons 91 0)
           (list 10 9.4938 0.5702072)
           (cons 40 0)
           (cons 41 0)
           (cons 42 0)
           (cons 91 0)
           (list 10 9.337336 0.51768)
           (cons 40 0)
           (cons 41 0)
           (cons 42 0)
           (cons 91 0)
           (list 10 8.532664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.3762 1.0731272)
           (cons 40 0)
           (cons 41 0)
           (cons 42 0)
           (cons 91 0)
           (list 10 8.3762 1.2474728)
           (cons 40 0)
           (cons 41 0)
           (cons 42 0)
           (cons 91 0)
           (list 10 8.532664 1.3)
           (cons 40 0)
           (cons 41 0)
           (cons 42 0)
           (cons 91 0)
           (list 10 9.337336 1.3)
           (cons 40 0)
           (cons 41 0)
           (cons 42 0)
           (cons 91 0)
           (list 10 9.4938 1.2474728)
           (cons 40 0)
           (cons 41 0)
           (cons 42 0)
           (cons 91 0)
           (list 10 9.4938 1.0731272)
           (cons 40 0)
           (cons 41 0)
           (cons 42 0)
           (cons 91 0)
           (list 10 9.337336 1.0206)
           (cons 40 0)
           (cons 41 0)
           (cons 42 0)
           (cons 91 0)
           (list 10 8.532664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 1.3 0 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 8.3 1.3 0)
           (cons 50 0)
          )
         )
         (entmake
          (list
           (cons 0 "POINT")
           (cons 100 "AcDbEntity")
           (cons 67 0)
           (cons 8 "0")
           (cons 100 "AcDbPoint")
           (list 10 8.3 -1.3 0)
           (cons 50 0)
          )
         )
         (entmake
          (list
           (cons 0 "POINT")
           (cons 100 "AcDbEntity")
           (cons 67 0)
           (cons 8 "0")
           (cons 100 "AcDbPoint")
           (list 10 9.6 1.3 0)
           (cons 50 0)
          )
         )
         (entmake
          (list
           (cons 0 "POINT")
           (cons 100 "AcDbEntity")
           (cons 67 0)
           (cons 8 "0")
           (cons 100 "AcDbPoint")
           (list 10 9.6 -1.3 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 9.6 -1.3)
           (cons 40 0)
           (cons 41 0)
           (cons 42 0)
           (cons 91 0)
           (list 10 9.6 1.3)
           (cons 40 0)
           (cons 41 0)
           (cons 42 0)
           (cons 91 0)
           (list 10 0 1.3)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.6 0.56666667 0)
           (cons 40 0.2)
           (cons 1 "1.30")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 0.23333333 0)
           (cons 40 0.2)
           (cons 1 "1.30")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.1 0)
           (cons 40 0.2)
           (cons 1 "8.30")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.43333333 0)
           (cons 40 0.2)
           (cons 1 "0.00")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "TAC-1999-BTD-TRAILER1"))
        (progn
         (entmake)
         (entmake
          (list
           (cons 0 "BLOCK")
           (cons 2 "TAC-1999-BTD-TRAILER1")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.5 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.5 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 11.57 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 11.57 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.5 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.5 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 1.3 0 0)
           (cons 40 0.104)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 11.1 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 11.36263966 -0.26263966 0)
           (list 11 11.36263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.4712 -0.7445528)
           (cons 40 0)
           (cons 41 0)
           (cons 42 0)
           (cons 91 0)
           (list 10 8.4712 -0.5702072)
           (cons 40 0)
           (cons 41 0)
           (cons 42 0)
           (cons 91 0)
           (list 10 8.627664 -0.51768)
           (cons 40 0)
           (cons 41 0)
           (cons 42 0)
           (cons 91 0)
           (list 10 9.432336 -0.51768)
           (cons 40 0)
           (cons 41 0)
           (cons 42 0)
           (cons 91 0)
           (list 10 9.5888 -0.5702072)
           (cons 40 0)
           (cons 41 0)
           (cons 42 0)
           (cons 91 0)
           (list 10 9.5888 -0.7445528)
           (cons 40 0)
           (cons 41 0)
           (cons 42 0)
           (cons 91 0)
           (list 10 9.432336 -0.79708)
           (cons 40 0)
           (cons 41 0)
           (cons 42 0)
           (cons 91 0)
           (list 10 8.627664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.4712 -1.2474728)
           (cons 40 0)
           (cons 41 0)
           (cons 42 0)
           (cons 91 0)
           (list 10 8.4712 -1.0731272)
           (cons 40 0)
           (cons 41 0)
           (cons 42 0)
           (cons 91 0)
           (list 10 8.627664 -1.0206)
           (cons 40 0)
           (cons 41 0)
           (cons 42 0)
           (cons 91 0)
           (list 10 9.432336 -1.0206)
           (cons 40 0)
           (cons 41 0)
           (cons 42 0)
           (cons 91 0)
           (list 10 9.5888 -1.0731272)
           (cons 40 0)
           (cons 41 0)
           (cons 42 0)
           (cons 91 0)
           (list 10 9.5888 -1.2474728)
           (cons 40 0)
           (cons 41 0)
           (cons 42 0)
           (cons 91 0)
           (list 10 9.432336 -1.3)
           (cons 40 0)
           (cons 41 0)
           (cons 42 0)
           (cons 91 0)
           (list 10 8.627664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.4712 0.5702072)
           (cons 40 0)
           (cons 41 0)
           (cons 42 0)
           (cons 91 0)
           (list 10 8.4712 0.7445528)
           (cons 40 0)
           (cons 41 0)
           (cons 42 0)
           (cons 91 0)
           (list 10 8.627664 0.79708)
           (cons 40 0)
           (cons 41 0)
           (cons 42 0)
           (cons 91 0)
           (list 10 9.432336 0.79708)
           (cons 40 0)
           (cons 41 0)
           (cons 42 0)
           (cons 91 0)
           (list 10 9.5888 0.7445528)
           (cons 40 0)
           (cons 41 0)
           (cons 42 0)
           (cons 91 0)
           (list 10 9.5888 0.5702072)
           (cons 40 0)
           (cons 41 0)
           (cons 42 0)
           (cons 91 0)
           (list 10 9.432336 0.51768)
           (cons 40 0)
           (cons 41 0)
           (cons 42 0)
           (cons 91 0)
           (list 10 8.627664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.4712 1.0731272)
           (cons 40 0)
           (cons 41 0)
           (cons 42 0)
           (cons 91 0)
           (list 10 8.4712 1.2474728)
           (cons 40 0)
           (cons 41 0)
           (cons 42 0)
           (cons 91 0)
           (list 10 8.627664 1.3)
           (cons 40 0)
           (cons 41 0)
           (cons 42 0)
           (cons 91 0)
           (list 10 9.432336 1.3)
           (cons 40 0)
           (cons 41 0)
           (cons 42 0)
           (cons 91 0)
           (list 10 9.5888 1.2474728)
           (cons 40 0)
           (cons 41 0)
           (cons 42 0)
           (cons 91 0)
           (list 10 9.5888 1.0731272)
           (cons 40 0)
           (cons 41 0)
           (cons 42 0)
           (cons 91 0)
           (list 10 9.432336 1.0206)
           (cons 40 0)
           (cons 41 0)
           (cons 42 0)
           (cons 91 0)
           (list 10 8.627664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.7412 -0.7445528)
           (cons 40 0)
           (cons 41 0)
           (cons 42 0)
           (cons 91 0)
           (list 10 9.7412 -0.5702072)
           (cons 40 0)
           (cons 41 0)
           (cons 42 0)
           (cons 91 0)
           (list 10 9.897664 -0.51768)
           (cons 40 0)
           (cons 41 0)
           (cons 42 0)
           (cons 91 0)
           (list 10 10.702336 -0.51768)
           (cons 40 0)
           (cons 41 0)
           (cons 42 0)
           (cons 91 0)
           (list 10 10.8588 -0.5702072)
           (cons 40 0)
           (cons 41 0)
           (cons 42 0)
           (cons 91 0)
           (list 10 10.8588 -0.7445528)
           (cons 40 0)
           (cons 41 0)
           (cons 42 0)
           (cons 91 0)
           (list 10 10.702336 -0.79708)
           (cons 40 0)
           (cons 41 0)
           (cons 42 0)
           (cons 91 0)
           (list 10 9.897664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.7412 -1.2474728)
           (cons 40 0)
           (cons 41 0)
           (cons 42 0)
           (cons 91 0)
           (list 10 9.7412 -1.0731272)
           (cons 40 0)
           (cons 41 0)
           (cons 42 0)
           (cons 91 0)
           (list 10 9.897664 -1.0206)
           (cons 40 0)
           (cons 41 0)
           (cons 42 0)
           (cons 91 0)
           (list 10 10.702336 -1.0206)
           (cons 40 0)
           (cons 41 0)
           (cons 42 0)
           (cons 91 0)
           (list 10 10.8588 -1.0731272)
           (cons 40 0)
           (cons 41 0)
           (cons 42 0)
           (cons 91 0)
           (list 10 10.8588 -1.2474728)
           (cons 40 0)
           (cons 41 0)
           (cons 42 0)
           (cons 91 0)
           (list 10 10.702336 -1.3)
           (cons 40 0)
           (cons 41 0)
           (cons 42 0)
           (cons 91 0)
           (list 10 9.897664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.7412 0.5702072)
           (cons 40 0)
           (cons 41 0)
           (cons 42 0)
           (cons 91 0)
           (list 10 9.7412 0.7445528)
           (cons 40 0)
           (cons 41 0)
           (cons 42 0)
           (cons 91 0)
           (list 10 9.897664 0.79708)
           (cons 40 0)
           (cons 41 0)
           (cons 42 0)
           (cons 91 0)
           (list 10 10.702336 0.79708)
           (cons 40 0)
           (cons 41 0)
           (cons 42 0)
           (cons 91 0)
           (list 10 10.8588 0.7445528)
           (cons 40 0)
           (cons 41 0)
           (cons 42 0)
           (cons 91 0)
           (list 10 10.8588 0.5702072)
           (cons 40 0)
           (cons 41 0)
           (cons 42 0)
           (cons 91 0)
           (list 10 10.702336 0.51768)
           (cons 40 0)
           (cons 41 0)
           (cons 42 0)
           (cons 91 0)
           (list 10 9.897664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.7412 1.0731272)
           (cons 40 0)
           (cons 41 0)
           (cons 42 0)
           (cons 91 0)
           (list 10 9.7412 1.2474728)
           (cons 40 0)
           (cons 41 0)
           (cons 42 0)
           (cons 91 0)
           (list 10 9.897664 1.3)
           (cons 40 0)
           (cons 41 0)
           (cons 42 0)
           (cons 91 0)
           (list 10 10.702336 1.3)
           (cons 40 0)
           (cons 41 0)
           (cons 42 0)
           (cons 91 0)
           (list 10 10.8588 1.2474728)
           (cons 40 0)
           (cons 41 0)
           (cons 42 0)
           (cons 91 0)
           (list 10 10.8588 1.0731272)
           (cons 40 0)
           (cons 41 0)
           (cons 42 0)
           (cons 91 0)
           (list 10 10.702336 1.0206)
           (cons 40 0)
           (cons 41 0)
           (cons 42 0)
           (cons 91 0)
           (list 10 9.897664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.0112 -0.7445528)
           (cons 40 0)
           (cons 41 0)
           (cons 42 0)
           (cons 91 0)
           (list 10 11.0112 -0.5702072)
           (cons 40 0)
           (cons 41 0)
           (cons 42 0)
           (cons 91 0)
           (list 10 11.167664 -0.51768)
           (cons 40 0)
           (cons 41 0)
           (cons 42 0)
           (cons 91 0)
           (list 10 11.972336 -0.51768)
           (cons 40 0)
           (cons 41 0)
           (cons 42 0)
           (cons 91 0)
           (list 10 12.1288 -0.5702072)
           (cons 40 0)
           (cons 41 0)
           (cons 42 0)
           (cons 91 0)
           (list 10 12.1288 -0.7445528)
           (cons 40 0)
           (cons 41 0)
           (cons 42 0)
           (cons 91 0)
           (list 10 11.972336 -0.79708)
           (cons 40 0)
           (cons 41 0)
           (cons 42 0)
           (cons 91 0)
           (list 10 11.167664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.0112 -1.2474728)
           (cons 40 0)
           (cons 41 0)
           (cons 42 0)
           (cons 91 0)
           (list 10 11.0112 -1.0731272)
           (cons 40 0)
           (cons 41 0)
           (cons 42 0)
           (cons 91 0)
           (list 10 11.167664 -1.0206)
           (cons 40 0)
           (cons 41 0)
           (cons 42 0)
           (cons 91 0)
           (list 10 11.972336 -1.0206)
           (cons 40 0)
           (cons 41 0)
           (cons 42 0)
           (cons 91 0)
           (list 10 12.1288 -1.0731272)
           (cons 40 0)
           (cons 41 0)
           (cons 42 0)
           (cons 91 0)
           (list 10 12.1288 -1.2474728)
           (cons 40 0)
           (cons 41 0)
           (cons 42 0)
           (cons 91 0)
           (list 10 11.972336 -1.3)
           (cons 40 0)
           (cons 41 0)
           (cons 42 0)
           (cons 91 0)
           (list 10 11.167664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.0112 0.5702072)
           (cons 40 0)
           (cons 41 0)
           (cons 42 0)
           (cons 91 0)
           (list 10 11.0112 0.7445528)
           (cons 40 0)
           (cons 41 0)
           (cons 42 0)
           (cons 91 0)
           (list 10 11.167664 0.79708)
           (cons 40 0)
           (cons 41 0)
           (cons 42 0)
           (cons 91 0)
           (list 10 11.972336 0.79708)
           (cons 40 0)
           (cons 41 0)
           (cons 42 0)
           (cons 91 0)
           (list 10 12.1288 0.7445528)
           (cons 40 0)
           (cons 41 0)
           (cons 42 0)
           (cons 91 0)
           (list 10 12.1288 0.5702072)
           (cons 40 0)
           (cons 41 0)
           (cons 42 0)
           (cons 91 0)
           (list 10 11.972336 0.51768)
           (cons 40 0)
           (cons 41 0)
           (cons 42 0)
           (cons 91 0)
           (list 10 11.167664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.0112 1.0731272)
           (cons 40 0)
           (cons 41 0)
           (cons 42 0)
           (cons 91 0)
           (list 10 11.0112 1.2474728)
           (cons 40 0)
           (cons 41 0)
           (cons 42 0)
           (cons 91 0)
           (list 10 11.167664 1.3)
           (cons 40 0)
           (cons 41 0)
           (cons 42 0)
           (cons 91 0)
           (list 10 11.972336 1.3)
           (cons 40 0)
           (cons 41 0)
           (cons 42 0)
           (cons 91 0)
           (list 10 12.1288 1.2474728)
           (cons 40 0)
           (cons 41 0)
           (cons 42 0)
           (cons 91 0)
           (list 10 12.1288 1.0731272)
           (cons 40 0)
           (cons 41 0)
           (cons 42 0)
           (cons 91 0)
           (list 10 11.972336 1.0206)
           (cons 40 0)
           (cons 41 0)
           (cons 42 0)
           (cons 91 0)
           (list 10 11.167664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 1.3 0 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 10.3 1.3 0)
           (cons 50 0)
          )
         )
         (entmake
          (list
           (cons 0 "POINT")
           (cons 100 "AcDbEntity")
           (cons 67 0)
           (cons 8 "0")
           (cons 100 "AcDbPoint")
           (list 10 10.3 -1.3 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 11.57 -1.3)
           (cons 40 0)
           (cons 41 0)
           (cons 42 0)
           (cons 91 0)
           (list 10 11.57 1.3)
           (cons 40 0)
           (cons 41 0)
           (cons 42 0)
           (cons 91 0)
           (list 10 0 1.3)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 11.1 0 0)
           (cons 50 0)
          )
         )
         (entmake
          (list
           (cons 0 "ATTDEF")
           (cons 100 "AcDbEntity")
           (cons 67 0)
           (cons 8 "0")
           (cons 100 "AcDbText")
           (list 10 0.6 0.56666667 0)
           (cons 40 0.2)
           (cons 1 "1.30")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 0.23333333 0)
           (cons 40 0.2)
           (cons 1 "1.30")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.1 0)
           (cons 40 0.2)
           (cons 1 "10.30")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.43333333 0)
           (cons 40 0.2)
           (cons 1 "11.10")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "TAC-1999-BTD-TRUCK"))
        (progn
         (entmake)
         (entmake
          (list
           (cons 0 "BLOCK")
           (cons 2 "TAC-1999-BTD-TRUCK")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.535 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.535 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 6.9 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 7.16263966 -0.26263966 0)
           (list 11 7.16263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.7062 -0.7445528)
           (cons 40 0)
           (cons 41 0)
           (cons 42 0)
           (cons 91 0)
           (list 10 5.7062 -0.5702072)
           (cons 40 0)
           (cons 41 0)
           (cons 42 0)
           (cons 91 0)
           (list 10 5.862664 -0.51768)
           (cons 40 0)
           (cons 41 0)
           (cons 42 0)
           (cons 91 0)
           (list 10 6.667336 -0.51768)
           (cons 40 0)
           (cons 41 0)
           (cons 42 0)
           (cons 91 0)
           (list 10 6.8238 -0.5702072)
           (cons 40 0)
           (cons 41 0)
           (cons 42 0)
           (cons 91 0)
           (list 10 6.8238 -0.7445528)
           (cons 40 0)
           (cons 41 0)
           (cons 42 0)
           (cons 91 0)
           (list 10 6.667336 -0.79708)
           (cons 40 0)
           (cons 41 0)
           (cons 42 0)
           (cons 91 0)
           (list 10 5.862664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.7062 -1.2474728)
           (cons 40 0)
           (cons 41 0)
           (cons 42 0)
           (cons 91 0)
           (list 10 5.7062 -1.0731272)
           (cons 40 0)
           (cons 41 0)
           (cons 42 0)
           (cons 91 0)
           (list 10 5.862664 -1.0206)
           (cons 40 0)
           (cons 41 0)
           (cons 42 0)
           (cons 91 0)
           (list 10 6.667336 -1.0206)
           (cons 40 0)
           (cons 41 0)
           (cons 42 0)
           (cons 91 0)
           (list 10 6.8238 -1.0731272)
           (cons 40 0)
           (cons 41 0)
           (cons 42 0)
           (cons 91 0)
           (list 10 6.8238 -1.2474728)
           (cons 40 0)
           (cons 41 0)
           (cons 42 0)
           (cons 91 0)
           (list 10 6.667336 -1.3)
           (cons 40 0)
           (cons 41 0)
           (cons 42 0)
           (cons 91 0)
           (list 10 5.862664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.7062 0.5702072)
           (cons 40 0)
           (cons 41 0)
           (cons 42 0)
           (cons 91 0)
           (list 10 5.7062 0.7445528)
           (cons 40 0)
           (cons 41 0)
           (cons 42 0)
           (cons 91 0)
           (list 10 5.862664 0.79708)
           (cons 40 0)
           (cons 41 0)
           (cons 42 0)
           (cons 91 0)
           (list 10 6.667336 0.79708)
           (cons 40 0)
           (cons 41 0)
           (cons 42 0)
           (cons 91 0)
           (list 10 6.8238 0.7445528)
           (cons 40 0)
           (cons 41 0)
           (cons 42 0)
           (cons 91 0)
           (list 10 6.8238 0.5702072)
           (cons 40 0)
           (cons 41 0)
           (cons 42 0)
           (cons 91 0)
           (list 10 6.667336 0.51768)
           (cons 40 0)
           (cons 41 0)
           (cons 42 0)
           (cons 91 0)
           (list 10 5.862664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.7062 1.0731272)
           (cons 40 0)
           (cons 41 0)
           (cons 42 0)
           (cons 91 0)
           (list 10 5.7062 1.2474728)
           (cons 40 0)
           (cons 41 0)
           (cons 42 0)
           (cons 91 0)
           (list 10 5.862664 1.3)
           (cons 40 0)
           (cons 41 0)
           (cons 42 0)
           (cons 91 0)
           (list 10 6.667336 1.3)
           (cons 40 0)
           (cons 41 0)
           (cons 42 0)
           (cons 91 0)
           (list 10 6.8238 1.2474728)
           (cons 40 0)
           (cons 41 0)
           (cons 42 0)
           (cons 91 0)
           (list 10 6.8238 1.0731272)
           (cons 40 0)
           (cons 41 0)
           (cons 42 0)
           (cons 91 0)
           (list 10 6.667336 1.0206)
           (cons 40 0)
           (cons 41 0)
           (cons 42 0)
           (cons 91 0)
           (list 10 5.862664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.9762 -0.7445528)
           (cons 40 0)
           (cons 41 0)
           (cons 42 0)
           (cons 91 0)
           (list 10 6.9762 -0.5702072)
           (cons 40 0)
           (cons 41 0)
           (cons 42 0)
           (cons 91 0)
           (list 10 7.132664 -0.51768)
           (cons 40 0)
           (cons 41 0)
           (cons 42 0)
           (cons 91 0)
           (list 10 7.937336 -0.51768)
           (cons 40 0)
           (cons 41 0)
           (cons 42 0)
           (cons 91 0)
           (list 10 8.0938 -0.5702072)
           (cons 40 0)
           (cons 41 0)
           (cons 42 0)
           (cons 91 0)
           (list 10 8.0938 -0.7445528)
           (cons 40 0)
           (cons 41 0)
           (cons 42 0)
           (cons 91 0)
           (list 10 7.937336 -0.79708)
           (cons 40 0)
           (cons 41 0)
           (cons 42 0)
           (cons 91 0)
           (list 10 7.132664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.9762 -1.2474728)
           (cons 40 0)
           (cons 41 0)
           (cons 42 0)
           (cons 91 0)
           (list 10 6.9762 -1.0731272)
           (cons 40 0)
           (cons 41 0)
           (cons 42 0)
           (cons 91 0)
           (list 10 7.132664 -1.0206)
           (cons 40 0)
           (cons 41 0)
           (cons 42 0)
           (cons 91 0)
           (list 10 7.937336 -1.0206)
           (cons 40 0)
           (cons 41 0)
           (cons 42 0)
           (cons 91 0)
           (list 10 8.0938 -1.0731272)
           (cons 40 0)
           (cons 41 0)
           (cons 42 0)
           (cons 91 0)
           (list 10 8.0938 -1.2474728)
           (cons 40 0)
           (cons 41 0)
           (cons 42 0)
           (cons 91 0)
           (list 10 7.937336 -1.3)
           (cons 40 0)
           (cons 41 0)
           (cons 42 0)
           (cons 91 0)
           (list 10 7.132664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.9762 0.5702072)
           (cons 40 0)
           (cons 41 0)
           (cons 42 0)
           (cons 91 0)
           (list 10 6.9762 0.7445528)
           (cons 40 0)
           (cons 41 0)
           (cons 42 0)
           (cons 91 0)
           (list 10 7.132664 0.79708)
           (cons 40 0)
           (cons 41 0)
           (cons 42 0)
           (cons 91 0)
           (list 10 7.937336 0.79708)
           (cons 40 0)
           (cons 41 0)
           (cons 42 0)
           (cons 91 0)
           (list 10 8.0938 0.7445528)
           (cons 40 0)
           (cons 41 0)
           (cons 42 0)
           (cons 91 0)
           (list 10 8.0938 0.5702072)
           (cons 40 0)
           (cons 41 0)
           (cons 42 0)
           (cons 91 0)
           (list 10 7.937336 0.51768)
           (cons 40 0)
           (cons 41 0)
           (cons 42 0)
           (cons 91 0)
           (list 10 7.132664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.9762 1.0731272)
           (cons 40 0)
           (cons 41 0)
           (cons 42 0)
           (cons 91 0)
           (list 10 6.9762 1.2474728)
           (cons 40 0)
           (cons 41 0)
           (cons 42 0)
           (cons 91 0)
           (list 10 7.132664 1.3)
           (cons 40 0)
           (cons 41 0)
           (cons 42 0)
           (cons 91 0)
           (list 10 7.937336 1.3)
           (cons 40 0)
           (cons 41 0)
           (cons 42 0)
           (cons 91 0)
           (list 10 8.0938 1.2474728)
           (cons 40 0)
           (cons 41 0)
           (cons 42 0)
           (cons 91 0)
           (list 10 8.0938 1.0731272)
           (cons 40 0)
           (cons 41 0)
           (cons 42 0)
           (cons 91 0)
           (list 10 7.937336 1.0206)
           (cons 40 0)
           (cons 41 0)
           (cons 42 0)
           (cons 91 0)
           (list 10 7.132664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0.8 0 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0.8 1.3 0)
           (cons 50 0)
          )
         )
         (entmake
          (list
           (cons 0 "POINT")
           (cons 100 "AcDbEntity")
           (cons 67 0)
           (cons 8 "0")
           (cons 100 "AcDbPoint")
           (list 10 0.8 -1.3 0)
           (cons 50 0)
          )
         )
         (entmake
          (list
           (cons 0 "POINT")
           (cons 100 "AcDbEntity")
           (cons 67 0)
           (cons 8 "0")
           (cons 100 "AcDbPoint")
           (list 10 6.9 -1.3 0)
           (cons 50 0)
          )
         )
         (entmake
          (list
           (cons 0 "POINT")
           (cons 100 "AcDbEntity")
           (cons 67 0)
           (cons 8 "0")
           (cons 100 "AcDbPoint")
           (list 10 6.9 1.3 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 7.535 -1.3)
           (cons 40 0)
           (cons 41 0)
           (cons 42 0)
           (cons 91 0)
           (list 10 7.535 1.3)
           (cons 40 0)
           (cons 41 0)
           (cons 42 0)
           (cons 91 0)
           (list 10 0 1.3)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 6.9 0 0)
           (cons 50 0)
          )
         )
         (entmake
          (list
           (cons 0 "ATTDEF")
           (cons 100 "AcDbEntity")
           (cons 67 0)
           (cons 8 "0")
           (cons 100 "AcDbText")
           (list 10 0.1 0.56666667 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 0.23333333 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.1 0)
           (cons 40 0.2)
           (cons 1 "6.90")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.43333333 0)
           (cons 40 0.2)
           (cons 1 "6.90")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.76666667 0)
           (cons 40 0.2)
           (cons 1 "29.50")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelLeftM1")
           (list 10 0.8 -1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM1")
           (list 10 0.8 1.0206 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "TAC-1999-B-12"))
        (progn
         (entmake)
         (entmake
          (list
           (cons 0 "BLOCK")
           (cons 2 "TAC-1999-B-12")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.2)
           (cons 40 0)
           (cons 41 0)
           (cons 42 0)
           (cons 91 0)
           (list 10 12.2 -1.2)
           (cons 40 0)
           (cons 41 0)
           (cons 42 0)
           (cons 91 0)
           (list 10 12.2 1.2)
           (cons 40 0)
           (cons 41 0)
           (cons 42 0)
           (cons 91 0)
           (list 10 0 1.2)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 12.2 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 12.2 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.892 -1.152248)
           (cons 40 0)
           (cons 41 0)
           (cons 42 0)
           (cons 91 0)
           (list 10 8.892 -0.993752)
           (cons 40 0)
           (cons 41 0)
           (cons 42 0)
           (cons 91 0)
           (list 10 9.03424 -0.946)
           (cons 40 0)
           (cons 41 0)
           (cons 42 0)
           (cons 91 0)
           (list 10 9.76576 -0.946)
           (cons 40 0)
           (cons 41 0)
           (cons 42 0)
           (cons 91 0)
           (list 10 9.908 -0.993752)
           (cons 40 0)
           (cons 41 0)
           (cons 42 0)
           (cons 91 0)
           (list 10 9.908 -1.152248)
           (cons 40 0)
           (cons 41 0)
           (cons 42 0)
           (cons 91 0)
           (list 10 9.76576 -1.2)
           (cons 40 0)
           (cons 41 0)
           (cons 42 0)
           (cons 91 0)
           (list 10 9.03424 -1.2)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.892 0.993752)
           (cons 40 0)
           (cons 41 0)
           (cons 42 0)
           (cons 91 0)
           (list 10 8.892 1.152248)
           (cons 40 0)
           (cons 41 0)
           (cons 42 0)
           (cons 91 0)
           (list 10 9.03424 1.2)
           (cons 40 0)
           (cons 41 0)
           (cons 42 0)
           (cons 91 0)
           (list 10 9.76576 1.2)
           (cons 40 0)
           (cons 41 0)
           (cons 42 0)
           (cons 91 0)
           (list 10 9.908 1.152248)
           (cons 40 0)
           (cons 41 0)
           (cons 42 0)
           (cons 91 0)
           (list 10 9.908 0.993752)
           (cons 40 0)
           (cons 41 0)
           (cons 42 0)
           (cons 91 0)
           (list 10 9.76576 0.946)
           (cons 40 0)
           (cons 41 0)
           (cons 42 0)
           (cons 91 0)
           (list 10 9.03424 0.946)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -1.2 0)
           (cons 50 0)
          )
         )
         (entmake
          (list
           (cons 0 "POINT")
           (cons 100 "AcDbEntity")
           (cons 67 0)
           (cons 8 "0")
           (cons 100 "AcDbPoint")
           (list 10 0 1.2 0)
           (cons 50 0)
          )
         )
         (entmake
          (list
           (cons 0 "POINT")
           (cons 100 "AcDbEntity")
           (cons 67 0)
           (cons 8 "0")
           (cons 100 "AcDbPoint")
           (list 10 12.2 1.2 0)
           (cons 50 0)
          )
         )
         (entmake
          (list
           (cons 0 "POINT")
           (cons 100 "AcDbEntity")
           (cons 67 0)
           (cons 8 "0")
           (cons 100 "AcDbPoint")
           (list 10 12.2 -1.2 0)
           (cons 50 0)
          )
         )
         (entmake
          (list
           (cons 0 "POINT")
           (cons 100 "AcDbEntity")
           (cons 67 0)
           (cons 8 "0")
           (cons 100 "AcDbPoint")
           (list 10 2.2 0 0)
           (cons 50 0)
          )
         )
         (entmake
          (list
           (cons 0 "POINT")
           (cons 100 "AcDbEntity")
           (cons 67 0)
           (cons 8 "0")
           (cons 100 "AcDbPoint")
           (list 10 2.2 1.2 0)
           (cons 50 0)
          )
         )
         (entmake
          (list
           (cons 0 "POINT")
           (cons 100 "AcDbEntity")
           (cons 67 0)
           (cons 8 "0")
           (cons 100 "AcDbPoint")
           (list 10 9.4 1.2 0)
           (cons 50 0)
          )
         )
         (entmake
          (list
           (cons 0 "POINT")
           (cons 100 "AcDbEntity")
           (cons 67 0)
           (cons 8 "0")
           (cons 100 "AcDbPoint")
           (list 10 9.4 -1.2 0)
           (cons 50 0)
          )
         )
         (entmake
          (list
           (cons 0 "POINT")
           (cons 100 "AcDbEntity")
           (cons 67 0)
           (cons 8 "0")
           (cons 100 "AcDbPoint")
           (list 10 2.2 -1.2 0)
           (cons 50 0)
          )
         )
         (entmake
          (list
           (cons 0 "ATTDEF")
           (cons 100 "AcDbEntity")
           (cons 67 0)
           (cons 8 "0")
           (cons 100 "AcDbText")
           (list 10 1.5 0.56666667 0)
           (cons 40 0.2)
           (cons 1 "2.200")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.5 0.23333333 0)
           (cons 40 0.2)
           (cons 1 "2.200")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.5 -0.1 0)
           (cons 40 0.2)
           (cons 1 "9.400")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.5 -0.43333333 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.5 -0.76666667 0)
           (cons 40 0.2)
           (cons 1 "37.1")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelLeftM2")
           (list 10 2.2 -0.946 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM2")
           (list 10 2.2 0.946 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "TAC-1999-ATD-TRAILER2"))
        (progn
         (entmake)
         (entmake
          (list
           (cons 0 "BLOCK")
           (cons 2 "TAC-1999-ATD-TRAILER2")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 9.4 -1.3)
           (cons 40 0)
           (cons 41 0)
           (cons 42 0)
           (cons 91 0)
           (list 10 9.4 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.4 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.4 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 1 0 0)
           (cons 40 0.17333333)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.7062 -0.7445528)
           (cons 40 0)
           (cons 41 0)
           (cons 42 0)
           (cons 91 0)
           (list 10 6.7062 -0.5702072)
           (cons 40 0)
           (cons 41 0)
           (cons 42 0)
           (cons 91 0)
           (list 10 6.862664 -0.51768)
           (cons 40 0)
           (cons 41 0)
           (cons 42 0)
           (cons 91 0)
           (list 10 7.667336 -0.51768)
           (cons 40 0)
           (cons 41 0)
           (cons 42 0)
           (cons 91 0)
           (list 10 7.8238 -0.5702072)
           (cons 40 0)
           (cons 41 0)
           (cons 42 0)
           (cons 91 0)
           (list 10 7.8238 -0.7445528)
           (cons 40 0)
           (cons 41 0)
           (cons 42 0)
           (cons 91 0)
           (list 10 7.667336 -0.79708)
           (cons 40 0)
           (cons 41 0)
           (cons 42 0)
           (cons 91 0)
           (list 10 6.862664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.7062 -1.2474728)
           (cons 40 0)
           (cons 41 0)
           (cons 42 0)
           (cons 91 0)
           (list 10 6.7062 -1.0731272)
           (cons 40 0)
           (cons 41 0)
           (cons 42 0)
           (cons 91 0)
           (list 10 6.862664 -1.0206)
           (cons 40 0)
           (cons 41 0)
           (cons 42 0)
           (cons 91 0)
           (list 10 7.667336 -1.0206)
           (cons 40 0)
           (cons 41 0)
           (cons 42 0)
           (cons 91 0)
           (list 10 7.8238 -1.0731272)
           (cons 40 0)
           (cons 41 0)
           (cons 42 0)
           (cons 91 0)
           (list 10 7.8238 -1.2474728)
           (cons 40 0)
           (cons 41 0)
           (cons 42 0)
           (cons 91 0)
           (list 10 7.667336 -1.3)
           (cons 40 0)
           (cons 41 0)
           (cons 42 0)
           (cons 91 0)
           (list 10 6.862664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.7062 0.5702072)
           (cons 40 0)
           (cons 41 0)
           (cons 42 0)
           (cons 91 0)
           (list 10 6.7062 0.7445528)
           (cons 40 0)
           (cons 41 0)
           (cons 42 0)
           (cons 91 0)
           (list 10 6.862664 0.79708)
           (cons 40 0)
           (cons 41 0)
           (cons 42 0)
           (cons 91 0)
           (list 10 7.667336 0.79708)
           (cons 40 0)
           (cons 41 0)
           (cons 42 0)
           (cons 91 0)
           (list 10 7.8238 0.7445528)
           (cons 40 0)
           (cons 41 0)
           (cons 42 0)
           (cons 91 0)
           (list 10 7.8238 0.5702072)
           (cons 40 0)
           (cons 41 0)
           (cons 42 0)
           (cons 91 0)
           (list 10 7.667336 0.51768)
           (cons 40 0)
           (cons 41 0)
           (cons 42 0)
           (cons 91 0)
           (list 10 6.862664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.7062 1.0731272)
           (cons 40 0)
           (cons 41 0)
           (cons 42 0)
           (cons 91 0)
           (list 10 6.7062 1.2474728)
           (cons 40 0)
           (cons 41 0)
           (cons 42 0)
           (cons 91 0)
           (list 10 6.862664 1.3)
           (cons 40 0)
           (cons 41 0)
           (cons 42 0)
           (cons 91 0)
           (list 10 7.667336 1.3)
           (cons 40 0)
           (cons 41 0)
           (cons 42 0)
           (cons 91 0)
           (list 10 7.8238 1.2474728)
           (cons 40 0)
           (cons 41 0)
           (cons 42 0)
           (cons 91 0)
           (list 10 7.8238 1.0731272)
           (cons 40 0)
           (cons 41 0)
           (cons 42 0)
           (cons 91 0)
           (list 10 7.667336 1.0206)
           (cons 40 0)
           (cons 41 0)
           (cons 42 0)
           (cons 91 0)
           (list 10 6.862664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.9762 -0.7445528)
           (cons 40 0)
           (cons 41 0)
           (cons 42 0)
           (cons 91 0)
           (list 10 7.9762 -0.5702072)
           (cons 40 0)
           (cons 41 0)
           (cons 42 0)
           (cons 91 0)
           (list 10 8.132664 -0.51768)
           (cons 40 0)
           (cons 41 0)
           (cons 42 0)
           (cons 91 0)
           (list 10 8.937336 -0.51768)
           (cons 40 0)
           (cons 41 0)
           (cons 42 0)
           (cons 91 0)
           (list 10 9.0938 -0.5702072)
           (cons 40 0)
           (cons 41 0)
           (cons 42 0)
           (cons 91 0)
           (list 10 9.0938 -0.7445528)
           (cons 40 0)
           (cons 41 0)
           (cons 42 0)
           (cons 91 0)
           (list 10 8.937336 -0.79708)
           (cons 40 0)
           (cons 41 0)
           (cons 42 0)
           (cons 91 0)
           (list 10 8.132664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.9762 -1.2474728)
           (cons 40 0)
           (cons 41 0)
           (cons 42 0)
           (cons 91 0)
           (list 10 7.9762 -1.0731272)
           (cons 40 0)
           (cons 41 0)
           (cons 42 0)
           (cons 91 0)
           (list 10 8.132664 -1.0206)
           (cons 40 0)
           (cons 41 0)
           (cons 42 0)
           (cons 91 0)
           (list 10 8.937336 -1.0206)
           (cons 40 0)
           (cons 41 0)
           (cons 42 0)
           (cons 91 0)
           (list 10 9.0938 -1.0731272)
           (cons 40 0)
           (cons 41 0)
           (cons 42 0)
           (cons 91 0)
           (list 10 9.0938 -1.2474728)
           (cons 40 0)
           (cons 41 0)
           (cons 42 0)
           (cons 91 0)
           (list 10 8.937336 -1.3)
           (cons 40 0)
           (cons 41 0)
           (cons 42 0)
           (cons 91 0)
           (list 10 8.132664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.9762 0.5702072)
           (cons 40 0)
           (cons 41 0)
           (cons 42 0)
           (cons 91 0)
           (list 10 7.9762 0.7445528)
           (cons 40 0)
           (cons 41 0)
           (cons 42 0)
           (cons 91 0)
           (list 10 8.132664 0.79708)
           (cons 40 0)
           (cons 41 0)
           (cons 42 0)
           (cons 91 0)
           (list 10 8.937336 0.79708)
           (cons 40 0)
           (cons 41 0)
           (cons 42 0)
           (cons 91 0)
           (list 10 9.0938 0.7445528)
           (cons 40 0)
           (cons 41 0)
           (cons 42 0)
           (cons 91 0)
           (list 10 9.0938 0.5702072)
           (cons 40 0)
           (cons 41 0)
           (cons 42 0)
           (cons 91 0)
           (list 10 8.937336 0.51768)
           (cons 40 0)
           (cons 41 0)
           (cons 42 0)
           (cons 91 0)
           (list 10 8.132664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.9762 1.0731272)
           (cons 40 0)
           (cons 41 0)
           (cons 42 0)
           (cons 91 0)
           (list 10 7.9762 1.2474728)
           (cons 40 0)
           (cons 41 0)
           (cons 42 0)
           (cons 91 0)
           (list 10 8.132664 1.3)
           (cons 40 0)
           (cons 41 0)
           (cons 42 0)
           (cons 91 0)
           (list 10 8.937336 1.3)
           (cons 40 0)
           (cons 41 0)
           (cons 42 0)
           (cons 91 0)
           (list 10 9.0938 1.2474728)
           (cons 40 0)
           (cons 41 0)
           (cons 42 0)
           (cons 91 0)
           (list 10 9.0938 1.0731272)
           (cons 40 0)
           (cons 41 0)
           (cons 42 0)
           (cons 91 0)
           (list 10 8.937336 1.0206)
           (cons 40 0)
           (cons 41 0)
           (cons 42 0)
           (cons 91 0)
           (list 10 8.132664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 9.4 -1.3 0)
           (cons 50 0)
          )
         )
         (entmake
          (list
           (cons 0 "POINT")
           (cons 100 "AcDbEntity")
           (cons 67 0)
           (cons 8 "0")
           (cons 100 "AcDbPoint")
           (list 10 9.4 1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 1 0 0)
           (cons 50 0)
          )
         )
         (entmake
          (list
           (cons 0 "POINT")
           (cons 100 "AcDbEntity")
           (cons 67 0)
           (cons 8 "0")
           (cons 100 "AcDbPoint")
           (list 10 7.9 0 0)
           (cons 50 0)
          )
         )
         (entmake
          (list
           (cons 0 "POINT")
           (cons 100 "AcDbEntity")
           (cons 67 0)
           (cons 8 "0")
           (cons 100 "AcDbPoint")
           (list 10 7.9 1.3 0)
           (cons 50 0)
          )
         )
         (entmake
          (list
           (cons 0 "POINT")
           (cons 100 "AcDbEntity")
           (cons 67 0)
           (cons 8 "0")
           (cons 100 "AcDbPoint")
           (list 10 7.9 -1.3 0)
           (cons 50 0)
          )
         )
         (entmake
          (list
           (cons 0 "ATTDEF")
           (cons 100 "AcDbEntity")
           (cons 67 0)
           (cons 8 "0")
           (cons 100 "AcDbText")
           (list 10 0.3 0.56666667 0)
           (cons 40 0.2)
           (cons 1 "1.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 0.23333333 0)
           (cons 40 0.2)
           (cons 1 "1.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.1 0)
           (cons 40 0.2)
           (cons 1 "7.900")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.43333333 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "TAC-1999-ATD-PUP"))
        (progn
         (entmake)
         (entmake
          (list
           (cons 0 "BLOCK")
           (cons 2 "TAC-1999-ATD-PUP")
           (cons 70 2)
           (cons 4 "")
           (list 10 0 0 0)
          )
         )
         (entmake
          (list
           (cons 0 "POLYLINE")
           (cons 100 "AcDbEntity")
           (cons 67 0)
           (cons 8 "Defpoints")
           (cons 100 "AcDb2dPolyline")
           (cons 66 1)
           (list 10 0 0 0)
           (cons 70 129)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "Defpoints")
           (cons 100 "AcDbVertex")
           (cons 100 "AcDb2dVertex")
           (list 10 0 0 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 2.1 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 2.1 1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "Defpoints")
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 2.1 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.17333333)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 -0.7445528)
           (cons 40 0)
           (cons 41 0)
           (cons 42 0)
           (cons 91 0)
           (list 10 1.5412 -0.5702072)
           (cons 40 0)
           (cons 41 0)
           (cons 42 0)
           (cons 91 0)
           (list 10 1.697664 -0.51768)
           (cons 40 0)
           (cons 41 0)
           (cons 42 0)
           (cons 91 0)
           (list 10 2.502336 -0.51768)
           (cons 40 0)
           (cons 41 0)
           (cons 42 0)
           (cons 91 0)
           (list 10 2.6588 -0.5702072)
           (cons 40 0)
           (cons 41 0)
           (cons 42 0)
           (cons 91 0)
           (list 10 2.6588 -0.7445528)
           (cons 40 0)
           (cons 41 0)
           (cons 42 0)
           (cons 91 0)
           (list 10 2.502336 -0.79708)
           (cons 40 0)
           (cons 41 0)
           (cons 42 0)
           (cons 91 0)
           (list 10 1.697664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 -1.2474728)
           (cons 40 0)
           (cons 41 0)
           (cons 42 0)
           (cons 91 0)
           (list 10 1.5412 -1.0731272)
           (cons 40 0)
           (cons 41 0)
           (cons 42 0)
           (cons 91 0)
           (list 10 1.697664 -1.0206)
           (cons 40 0)
           (cons 41 0)
           (cons 42 0)
           (cons 91 0)
           (list 10 2.502336 -1.0206)
           (cons 40 0)
           (cons 41 0)
           (cons 42 0)
           (cons 91 0)
           (list 10 2.6588 -1.0731272)
           (cons 40 0)
           (cons 41 0)
           (cons 42 0)
           (cons 91 0)
           (list 10 2.6588 -1.2474728)
           (cons 40 0)
           (cons 41 0)
           (cons 42 0)
           (cons 91 0)
           (list 10 2.502336 -1.3)
           (cons 40 0)
           (cons 41 0)
           (cons 42 0)
           (cons 91 0)
           (list 10 1.697664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 0.5702072)
           (cons 40 0)
           (cons 41 0)
           (cons 42 0)
           (cons 91 0)
           (list 10 1.5412 0.7445528)
           (cons 40 0)
           (cons 41 0)
           (cons 42 0)
           (cons 91 0)
           (list 10 1.697664 0.79708)
           (cons 40 0)
           (cons 41 0)
           (cons 42 0)
           (cons 91 0)
           (list 10 2.502336 0.79708)
           (cons 40 0)
           (cons 41 0)
           (cons 42 0)
           (cons 91 0)
           (list 10 2.6588 0.7445528)
           (cons 40 0)
           (cons 41 0)
           (cons 42 0)
           (cons 91 0)
           (list 10 2.6588 0.5702072)
           (cons 40 0)
           (cons 41 0)
           (cons 42 0)
           (cons 91 0)
           (list 10 2.502336 0.51768)
           (cons 40 0)
           (cons 41 0)
           (cons 42 0)
           (cons 91 0)
           (list 10 1.697664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 1.0731272)
           (cons 40 0)
           (cons 41 0)
           (cons 42 0)
           (cons 91 0)
           (list 10 1.5412 1.2474728)
           (cons 40 0)
           (cons 41 0)
           (cons 42 0)
           (cons 91 0)
           (list 10 1.697664 1.3)
           (cons 40 0)
           (cons 41 0)
           (cons 42 0)
           (cons 91 0)
           (list 10 2.502336 1.3)
           (cons 40 0)
           (cons 41 0)
           (cons 42 0)
           (cons 91 0)
           (list 10 2.6588 1.2474728)
           (cons 40 0)
           (cons 41 0)
           (cons 42 0)
           (cons 91 0)
           (list 10 2.6588 1.0731272)
           (cons 40 0)
           (cons 41 0)
           (cons 42 0)
           (cons 91 0)
           (list 10 2.502336 1.0206)
           (cons 40 0)
           (cons 41 0)
           (cons 42 0)
           (cons 91 0)
           (list 10 1.697664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 2.1 0 0)
           (cons 50 0)
          )
         )
         (entmake
          (list
           (cons 0 "POINT")
           (cons 100 "AcDbEntity")
           (cons 67 0)
           (cons 8 "0")
           (cons 100 "AcDbPoint")
           (list 10 2.1 1.3 0)
           (cons 50 0)
          )
         )
         (entmake
          (list
           (cons 0 "POINT")
           (cons 100 "AcDbEntity")
           (cons 67 0)
           (cons 8 "0")
           (cons 100 "AcDbPoint")
           (list 10 2.1 -1.3 0)
           (cons 50 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "2.100")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "2.100")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "TAC-1999-ATD-TRAILER1"))
        (progn
         (entmake)
         (entmake
          (list
           (cons 0 "BLOCK")
           (cons 2 "TAC-1999-ATD-TRAILER1")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 9.1 -1.3)
           (cons 40 0)
           (cons 41 0)
           (cons 42 0)
           (cons 91 0)
           (list 10 9.1 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.1 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.1 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 1 0 0)
           (cons 40 0.104)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.7062 -0.7445528)
           (cons 40 0)
           (cons 41 0)
           (cons 42 0)
           (cons 91 0)
           (list 10 6.7062 -0.5702072)
           (cons 40 0)
           (cons 41 0)
           (cons 42 0)
           (cons 91 0)
           (list 10 6.862664 -0.51768)
           (cons 40 0)
           (cons 41 0)
           (cons 42 0)
           (cons 91 0)
           (list 10 7.667336 -0.51768)
           (cons 40 0)
           (cons 41 0)
           (cons 42 0)
           (cons 91 0)
           (list 10 7.8238 -0.5702072)
           (cons 40 0)
           (cons 41 0)
           (cons 42 0)
           (cons 91 0)
           (list 10 7.8238 -0.7445528)
           (cons 40 0)
           (cons 41 0)
           (cons 42 0)
           (cons 91 0)
           (list 10 7.667336 -0.79708)
           (cons 40 0)
           (cons 41 0)
           (cons 42 0)
           (cons 91 0)
           (list 10 6.862664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.7062 -1.2474728)
           (cons 40 0)
           (cons 41 0)
           (cons 42 0)
           (cons 91 0)
           (list 10 6.7062 -1.0731272)
           (cons 40 0)
           (cons 41 0)
           (cons 42 0)
           (cons 91 0)
           (list 10 6.862664 -1.0206)
           (cons 40 0)
           (cons 41 0)
           (cons 42 0)
           (cons 91 0)
           (list 10 7.667336 -1.0206)
           (cons 40 0)
           (cons 41 0)
           (cons 42 0)
           (cons 91 0)
           (list 10 7.8238 -1.0731272)
           (cons 40 0)
           (cons 41 0)
           (cons 42 0)
           (cons 91 0)
           (list 10 7.8238 -1.2474728)
           (cons 40 0)
           (cons 41 0)
           (cons 42 0)
           (cons 91 0)
           (list 10 7.667336 -1.3)
           (cons 40 0)
           (cons 41 0)
           (cons 42 0)
           (cons 91 0)
           (list 10 6.862664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.7062 0.5702072)
           (cons 40 0)
           (cons 41 0)
           (cons 42 0)
           (cons 91 0)
           (list 10 6.7062 0.7445528)
           (cons 40 0)
           (cons 41 0)
           (cons 42 0)
           (cons 91 0)
           (list 10 6.862664 0.79708)
           (cons 40 0)
           (cons 41 0)
           (cons 42 0)
           (cons 91 0)
           (list 10 7.667336 0.79708)
           (cons 40 0)
           (cons 41 0)
           (cons 42 0)
           (cons 91 0)
           (list 10 7.8238 0.7445528)
           (cons 40 0)
           (cons 41 0)
           (cons 42 0)
           (cons 91 0)
           (list 10 7.8238 0.5702072)
           (cons 40 0)
           (cons 41 0)
           (cons 42 0)
           (cons 91 0)
           (list 10 7.667336 0.51768)
           (cons 40 0)
           (cons 41 0)
           (cons 42 0)
           (cons 91 0)
           (list 10 6.862664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.7062 1.0731272)
           (cons 40 0)
           (cons 41 0)
           (cons 42 0)
           (cons 91 0)
           (list 10 6.7062 1.2474728)
           (cons 40 0)
           (cons 41 0)
           (cons 42 0)
           (cons 91 0)
           (list 10 6.862664 1.3)
           (cons 40 0)
           (cons 41 0)
           (cons 42 0)
           (cons 91 0)
           (list 10 7.667336 1.3)
           (cons 40 0)
           (cons 41 0)
           (cons 42 0)
           (cons 91 0)
           (list 10 7.8238 1.2474728)
           (cons 40 0)
           (cons 41 0)
           (cons 42 0)
           (cons 91 0)
           (list 10 7.8238 1.0731272)
           (cons 40 0)
           (cons 41 0)
           (cons 42 0)
           (cons 91 0)
           (list 10 7.667336 1.0206)
           (cons 40 0)
           (cons 41 0)
           (cons 42 0)
           (cons 91 0)
           (list 10 6.862664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.9762 -0.7445528)
           (cons 40 0)
           (cons 41 0)
           (cons 42 0)
           (cons 91 0)
           (list 10 7.9762 -0.5702072)
           (cons 40 0)
           (cons 41 0)
           (cons 42 0)
           (cons 91 0)
           (list 10 8.132664 -0.51768)
           (cons 40 0)
           (cons 41 0)
           (cons 42 0)
           (cons 91 0)
           (list 10 8.937336 -0.51768)
           (cons 40 0)
           (cons 41 0)
           (cons 42 0)
           (cons 91 0)
           (list 10 9.0938 -0.5702072)
           (cons 40 0)
           (cons 41 0)
           (cons 42 0)
           (cons 91 0)
           (list 10 9.0938 -0.7445528)
           (cons 40 0)
           (cons 41 0)
           (cons 42 0)
           (cons 91 0)
           (list 10 8.937336 -0.79708)
           (cons 40 0)
           (cons 41 0)
           (cons 42 0)
           (cons 91 0)
           (list 10 8.132664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.9762 -1.2474728)
           (cons 40 0)
           (cons 41 0)
           (cons 42 0)
           (cons 91 0)
           (list 10 7.9762 -1.0731272)
           (cons 40 0)
           (cons 41 0)
           (cons 42 0)
           (cons 91 0)
           (list 10 8.132664 -1.0206)
           (cons 40 0)
           (cons 41 0)
           (cons 42 0)
           (cons 91 0)
           (list 10 8.937336 -1.0206)
           (cons 40 0)
           (cons 41 0)
           (cons 42 0)
           (cons 91 0)
           (list 10 9.0938 -1.0731272)
           (cons 40 0)
           (cons 41 0)
           (cons 42 0)
           (cons 91 0)
           (list 10 9.0938 -1.2474728)
           (cons 40 0)
           (cons 41 0)
           (cons 42 0)
           (cons 91 0)
           (list 10 8.937336 -1.3)
           (cons 40 0)
           (cons 41 0)
           (cons 42 0)
           (cons 91 0)
           (list 10 8.132664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.9762 0.5702072)
           (cons 40 0)
           (cons 41 0)
           (cons 42 0)
           (cons 91 0)
           (list 10 7.9762 0.7445528)
           (cons 40 0)
           (cons 41 0)
           (cons 42 0)
           (cons 91 0)
           (list 10 8.132664 0.79708)
           (cons 40 0)
           (cons 41 0)
           (cons 42 0)
           (cons 91 0)
           (list 10 8.937336 0.79708)
           (cons 40 0)
           (cons 41 0)
           (cons 42 0)
           (cons 91 0)
           (list 10 9.0938 0.7445528)
           (cons 40 0)
           (cons 41 0)
           (cons 42 0)
           (cons 91 0)
           (list 10 9.0938 0.5702072)
           (cons 40 0)
           (cons 41 0)
           (cons 42 0)
           (cons 91 0)
           (list 10 8.937336 0.51768)
           (cons 40 0)
           (cons 41 0)
           (cons 42 0)
           (cons 91 0)
           (list 10 8.132664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.9762 1.0731272)
           (cons 40 0)
           (cons 41 0)
           (cons 42 0)
           (cons 91 0)
           (list 10 7.9762 1.2474728)
           (cons 40 0)
           (cons 41 0)
           (cons 42 0)
           (cons 91 0)
           (list 10 8.132664 1.3)
           (cons 40 0)
           (cons 41 0)
           (cons 42 0)
           (cons 91 0)
           (list 10 8.937336 1.3)
           (cons 40 0)
           (cons 41 0)
           (cons 42 0)
           (cons 91 0)
           (list 10 9.0938 1.2474728)
           (cons 40 0)
           (cons 41 0)
           (cons 42 0)
           (cons 91 0)
           (list 10 9.0938 1.0731272)
           (cons 40 0)
           (cons 41 0)
           (cons 42 0)
           (cons 91 0)
           (list 10 8.937336 1.0206)
           (cons 40 0)
           (cons 41 0)
           (cons 42 0)
           (cons 91 0)
           (list 10 8.132664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 1 0 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 9.1 1.3 0)
           (cons 50 0)
          )
         )
         (entmake
          (list
           (cons 0 "POINT")
           (cons 100 "AcDbEntity")
           (cons 67 0)
           (cons 8 "0")
           (cons 100 "AcDbPoint")
           (list 10 9.1 -1.3 0)
           (cons 50 0)
          )
         )
         (entmake
          (list
           (cons 0 "POINT")
           (cons 100 "AcDbEntity")
           (cons 67 0)
           (cons 8 "0")
           (cons 100 "AcDbPoint")
           (list 10 7.9 -1.3 0)
           (cons 50 0)
          )
         )
         (entmake
          (list
           (cons 0 "POINT")
           (cons 100 "AcDbEntity")
           (cons 67 0)
           (cons 8 "0")
           (cons 100 "AcDbPoint")
           (list 10 7.9 1.3 0)
           (cons 50 0)
          )
         )
         (entmake
          (list
           (cons 0 "ATTDEF")
           (cons 100 "AcDbEntity")
           (cons 67 0)
           (cons 8 "0")
           (cons 100 "AcDbText")
           (list 10 0.3 0.56666667 0)
           (cons 40 0.2)
           (cons 1 "1.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 0.23333333 0)
           (cons 40 0.2)
           (cons 1 "1.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.1 0)
           (cons 40 0.2)
           (cons 1 "7.900")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.43333333 0)
           (cons 40 0.2)
           (cons 1 "9.100")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "POINT")
           (cons 100 "AcDbEntity")
           (cons 67 0)
           (cons 8 "0")
           (cons 100 "AcDbPoint")
           (list 10 9.1 0 0)
           (cons 50 0)
          )
         )
         (entmake (list (cons 0 "ENDBLK")))
        )
       )
       ((= (strcase BLKNAME) (strcase "TAC-1999-ATD-TRUCK"))
        (progn
         (entmake)
         (entmake
          (list
           (cons 0 "BLOCK")
           (cons 2 "TAC-1999-ATD-TRUCK")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 6.535 -1.3)
           (cons 40 0)
           (cons 41 0)
           (cons 42 0)
           (cons 91 0)
           (list 10 6.535 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.535 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.535 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 5.9 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 6.16263966 -0.26263966 0)
           (list 11 6.16263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.7062 -0.7445528)
           (cons 40 0)
           (cons 41 0)
           (cons 42 0)
           (cons 91 0)
           (list 10 4.7062 -0.5702072)
           (cons 40 0)
           (cons 41 0)
           (cons 42 0)
           (cons 91 0)
           (list 10 4.862664 -0.51768)
           (cons 40 0)
           (cons 41 0)
           (cons 42 0)
           (cons 91 0)
           (list 10 5.667336 -0.51768)
           (cons 40 0)
           (cons 41 0)
           (cons 42 0)
           (cons 91 0)
           (list 10 5.8238 -0.5702072)
           (cons 40 0)
           (cons 41 0)
           (cons 42 0)
           (cons 91 0)
           (list 10 5.8238 -0.7445528)
           (cons 40 0)
           (cons 41 0)
           (cons 42 0)
           (cons 91 0)
           (list 10 5.667336 -0.79708)
           (cons 40 0)
           (cons 41 0)
           (cons 42 0)
           (cons 91 0)
           (list 10 4.862664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.7062 -1.2474728)
           (cons 40 0)
           (cons 41 0)
           (cons 42 0)
           (cons 91 0)
           (list 10 4.7062 -1.0731272)
           (cons 40 0)
           (cons 41 0)
           (cons 42 0)
           (cons 91 0)
           (list 10 4.862664 -1.0206)
           (cons 40 0)
           (cons 41 0)
           (cons 42 0)
           (cons 91 0)
           (list 10 5.667336 -1.0206)
           (cons 40 0)
           (cons 41 0)
           (cons 42 0)
           (cons 91 0)
           (list 10 5.8238 -1.0731272)
           (cons 40 0)
           (cons 41 0)
           (cons 42 0)
           (cons 91 0)
           (list 10 5.8238 -1.2474728)
           (cons 40 0)
           (cons 41 0)
           (cons 42 0)
           (cons 91 0)
           (list 10 5.667336 -1.3)
           (cons 40 0)
           (cons 41 0)
           (cons 42 0)
           (cons 91 0)
           (list 10 4.862664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.7062 0.5702072)
           (cons 40 0)
           (cons 41 0)
           (cons 42 0)
           (cons 91 0)
           (list 10 4.7062 0.7445528)
           (cons 40 0)
           (cons 41 0)
           (cons 42 0)
           (cons 91 0)
           (list 10 4.862664 0.79708)
           (cons 40 0)
           (cons 41 0)
           (cons 42 0)
           (cons 91 0)
           (list 10 5.667336 0.79708)
           (cons 40 0)
           (cons 41 0)
           (cons 42 0)
           (cons 91 0)
           (list 10 5.8238 0.7445528)
           (cons 40 0)
           (cons 41 0)
           (cons 42 0)
           (cons 91 0)
           (list 10 5.8238 0.5702072)
           (cons 40 0)
           (cons 41 0)
           (cons 42 0)
           (cons 91 0)
           (list 10 5.667336 0.51768)
           (cons 40 0)
           (cons 41 0)
           (cons 42 0)
           (cons 91 0)
           (list 10 4.862664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.7062 1.0731272)
           (cons 40 0)
           (cons 41 0)
           (cons 42 0)
           (cons 91 0)
           (list 10 4.7062 1.2474728)
           (cons 40 0)
           (cons 41 0)
           (cons 42 0)
           (cons 91 0)
           (list 10 4.862664 1.3)
           (cons 40 0)
           (cons 41 0)
           (cons 42 0)
           (cons 91 0)
           (list 10 5.667336 1.3)
           (cons 40 0)
           (cons 41 0)
           (cons 42 0)
           (cons 91 0)
           (list 10 5.8238 1.2474728)
           (cons 40 0)
           (cons 41 0)
           (cons 42 0)
           (cons 91 0)
           (list 10 5.8238 1.0731272)
           (cons 40 0)
           (cons 41 0)
           (cons 42 0)
           (cons 91 0)
           (list 10 5.667336 1.0206)
           (cons 40 0)
           (cons 41 0)
           (cons 42 0)
           (cons 91 0)
           (list 10 4.862664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9762 -0.7445528)
           (cons 40 0)
           (cons 41 0)
           (cons 42 0)
           (cons 91 0)
           (list 10 5.9762 -0.5702072)
           (cons 40 0)
           (cons 41 0)
           (cons 42 0)
           (cons 91 0)
           (list 10 6.132664 -0.51768)
           (cons 40 0)
           (cons 41 0)
           (cons 42 0)
           (cons 91 0)
           (list 10 6.937336 -0.51768)
           (cons 40 0)
           (cons 41 0)
           (cons 42 0)
           (cons 91 0)
           (list 10 7.0938 -0.5702072)
           (cons 40 0)
           (cons 41 0)
           (cons 42 0)
           (cons 91 0)
           (list 10 7.0938 -0.7445528)
           (cons 40 0)
           (cons 41 0)
           (cons 42 0)
           (cons 91 0)
           (list 10 6.937336 -0.79708)
           (cons 40 0)
           (cons 41 0)
           (cons 42 0)
           (cons 91 0)
           (list 10 6.132664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9762 -1.2474728)
           (cons 40 0)
           (cons 41 0)
           (cons 42 0)
           (cons 91 0)
           (list 10 5.9762 -1.0731272)
           (cons 40 0)
           (cons 41 0)
           (cons 42 0)
           (cons 91 0)
           (list 10 6.132664 -1.0206)
           (cons 40 0)
           (cons 41 0)
           (cons 42 0)
           (cons 91 0)
           (list 10 6.937336 -1.0206)
           (cons 40 0)
           (cons 41 0)
           (cons 42 0)
           (cons 91 0)
           (list 10 7.0938 -1.0731272)
           (cons 40 0)
           (cons 41 0)
           (cons 42 0)
           (cons 91 0)
           (list 10 7.0938 -1.2474728)
           (cons 40 0)
           (cons 41 0)
           (cons 42 0)
           (cons 91 0)
           (list 10 6.937336 -1.3)
           (cons 40 0)
           (cons 41 0)
           (cons 42 0)
           (cons 91 0)
           (list 10 6.132664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9762 0.5702072)
           (cons 40 0)
           (cons 41 0)
           (cons 42 0)
           (cons 91 0)
           (list 10 5.9762 0.7445528)
           (cons 40 0)
           (cons 41 0)
           (cons 42 0)
           (cons 91 0)
           (list 10 6.132664 0.79708)
           (cons 40 0)
           (cons 41 0)
           (cons 42 0)
           (cons 91 0)
           (list 10 6.937336 0.79708)
           (cons 40 0)
           (cons 41 0)
           (cons 42 0)
           (cons 91 0)
           (list 10 7.0938 0.7445528)
           (cons 40 0)
           (cons 41 0)
           (cons 42 0)
           (cons 91 0)
           (list 10 7.0938 0.5702072)
           (cons 40 0)
           (cons 41 0)
           (cons 42 0)
           (cons 91 0)
           (list 10 6.937336 0.51768)
           (cons 40 0)
           (cons 41 0)
           (cons 42 0)
           (cons 91 0)
           (list 10 6.132664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9762 1.0731272)
           (cons 40 0)
           (cons 41 0)
           (cons 42 0)
           (cons 91 0)
           (list 10 5.9762 1.2474728)
           (cons 40 0)
           (cons 41 0)
           (cons 42 0)
           (cons 91 0)
           (list 10 6.132664 1.3)
           (cons 40 0)
           (cons 41 0)
           (cons 42 0)
           (cons 91 0)
           (list 10 6.937336 1.3)
           (cons 40 0)
           (cons 41 0)
           (cons 42 0)
           (cons 91 0)
           (list 10 7.0938 1.2474728)
           (cons 40 0)
           (cons 41 0)
           (cons 42 0)
           (cons 91 0)
           (list 10 7.0938 1.0731272)
           (cons 40 0)
           (cons 41 0)
           (cons 42 0)
           (cons 91 0)
           (list 10 6.937336 1.0206)
           (cons 40 0)
           (cons 41 0)
           (cons 42 0)
           (cons 91 0)
           (list 10 6.132664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0.8 0 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0.8 1.3 0)
           (cons 50 0)
          )
         )
         (entmake
          (list
           (cons 0 "POINT")
           (cons 100 "AcDbEntity")
           (cons 67 0)
           (cons 8 "0")
           (cons 100 "AcDbPoint")
           (list 10 0.8 -1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 5.9 1.3 0)
           (cons 50 0)
          )
         )
         (entmake
          (list
           (cons 0 "POINT")
           (cons 100 "AcDbEntity")
           (cons 67 0)
           (cons 8 "0")
           (cons 100 "AcDbPoint")
           (list 10 5.9 -1.3 0)
           (cons 50 0)
          )
         )
         (entmake
          (list
           (cons 0 "POINT")
           (cons 100 "AcDbEntity")
           (cons 67 0)
           (cons 8 "0")
           (cons 100 "AcDbPoint")
           (list 10 5.9 0 0)
           (cons 50 0)
          )
         )
         (entmake
          (list
           (cons 0 "ATTDEF")
           (cons 100 "AcDbEntity")
           (cons 67 0)
           (cons 8 "0")
           (cons 100 "AcDbText")
           (list 10 0.1 0.56666667 0)
           (cons 40 0.2)
           (cons 1 "0.800")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 0.23333333 0)
           (cons 40 0.2)
           (cons 1 "0.800")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.1 0)
           (cons 40 0.2)
           (cons 1 "5.900")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.43333333 0)
           (cons 40 0.2)
           (cons 1 "5.900")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.76666667 0)
           (cons 40 0.2)
           (cons 1 "27.4")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelRightM1")
           (list 10 0.8 1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM1")
           (list 10 0.8 -1.0206 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "TAC-1999-A-BUS-REAR"))
        (progn
         (entmake)
         (entmake
          (list
           (cons 0 "BLOCK")
           (cons 2 "TAC-1999-A-BUS-REAR")
           (cons 70 2)
           (cons 4 "")
           (list 10 0 0 0)
          )
         )
         (entmake
          (list
           (cons 0 "POLYLINE")
           (cons 100 "AcDbEntity")
           (cons 67 0)
           (cons 8 "Defpoints")
           (cons 100 "AcDb2dPolyline")
           (cons 66 1)
           (list 10 0 0 0)
           (cons 70 129)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "Defpoints")
           (cons 100 "AcDbVertex")
           (cons 100 "AcDb2dVertex")
           (list 10 0 0 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 0.6 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 7.8 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 7.8 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 0.6 1.2 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "Defpoints")
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0.6 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.8 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.8 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0.6 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0.6 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0.6 -1.2 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 0.6 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.16)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.292 -1.152248)
           (cons 40 0)
           (cons 41 0)
           (cons 42 0)
           (cons 91 0)
           (list 10 4.292 -0.993752)
           (cons 40 0)
           (cons 41 0)
           (cons 42 0)
           (cons 91 0)
           (list 10 4.43424 -0.946)
           (cons 40 0)
           (cons 41 0)
           (cons 42 0)
           (cons 91 0)
           (list 10 5.16576 -0.946)
           (cons 40 0)
           (cons 41 0)
           (cons 42 0)
           (cons 91 0)
           (list 10 5.308 -0.993752)
           (cons 40 0)
           (cons 41 0)
           (cons 42 0)
           (cons 91 0)
           (list 10 5.308 -1.152248)
           (cons 40 0)
           (cons 41 0)
           (cons 42 0)
           (cons 91 0)
           (list 10 5.16576 -1.2)
           (cons 40 0)
           (cons 41 0)
           (cons 42 0)
           (cons 91 0)
           (list 10 4.43424 -1.2)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.292 0.993752)
           (cons 40 0)
           (cons 41 0)
           (cons 42 0)
           (cons 91 0)
           (list 10 4.292 1.152248)
           (cons 40 0)
           (cons 41 0)
           (cons 42 0)
           (cons 91 0)
           (list 10 4.43424 1.2)
           (cons 40 0)
           (cons 41 0)
           (cons 42 0)
           (cons 91 0)
           (list 10 5.16576 1.2)
           (cons 40 0)
           (cons 41 0)
           (cons 42 0)
           (cons 91 0)
           (list 10 5.308 1.152248)
           (cons 40 0)
           (cons 41 0)
           (cons 42 0)
           (cons 91 0)
           (list 10 5.308 0.993752)
           (cons 40 0)
           (cons 41 0)
           (cons 42 0)
           (cons 91 0)
           (list 10 5.16576 0.946)
           (cons 40 0)
           (cons 41 0)
           (cons 42 0)
           (cons 91 0)
           (list 10 4.43424 0.946)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "4.800")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "POINT")
           (cons 100 "AcDbEntity")
           (cons 67 0)
           (cons 8 "0")
           (cons 100 "AcDbPoint")
           (list 10 4.8 -1.2 0)
           (cons 50 0)
          )
         )
         (entmake
          (list
           (cons 0 "POINT")
           (cons 100 "AcDbEntity")
           (cons 67 0)
           (cons 8 "0")
           (cons 100 "AcDbPoint")
           (list 10 4.8 1.2 0)
           (cons 50 0)
          )
         )
         (entmake
          (list
           (cons 0 "POINT")
           (cons 100 "AcDbEntity")
           (cons 67 0)
           (cons 8 "0")
           (cons 100 "AcDbPoint")
           (list 10 7.8 1.2 0)
           (cons 50 0)
          )
         )
         (entmake
          (list
           (cons 0 "POINT")
           (cons 100 "AcDbEntity")
           (cons 67 0)
           (cons 8 "0")
           (cons 100 "AcDbPoint")
           (list 10 7.8 -1.2 0)
           (cons 50 0)
          )
         )
         (entmake (list (cons 0 "ENDBLK")))
        )
       )
       ((= (strcase BLKNAME) (strcase "TAC-1999-A-BUS-FRONT"))
        (progn
         (entmake)
         (entmake
          (list
           (cons 0 "BLOCK")
           (cons 2 "TAC-1999-A-BUS-FRONT")
           (cons 70 2)
           (cons 4 "")
           (list 10 0 0 0)
          )
         )
         (entmake
          (list
           (cons 0 "POLYLINE")
           (cons 100 "AcDbEntity")
           (cons 67 0)
           (cons 8 "Defpoints")
           (cons 100 "AcDb2dPolyline")
           (cons 66 1)
           (list 10 0 0 0)
           (cons 70 129)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "Defpoints")
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 9.9 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 10.5 0 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 9.9 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 0 1.2 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "Defpoints")
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.9 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.9 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 9.9 0 0)
           (list 11 10.5 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 10.5 0 0)
           (cons 40 0.1016)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.192 -1.152248)
           (cons 40 0)
           (cons 41 0)
           (cons 42 0)
           (cons 91 0)
           (list 10 8.192 -0.993752)
           (cons 40 0)
           (cons 41 0)
           (cons 42 0)
           (cons 91 0)
           (list 10 8.33424 -0.946)
           (cons 40 0)
           (cons 41 0)
           (cons 42 0)
           (cons 91 0)
           (list 10 9.06576 -0.946)
           (cons 40 0)
           (cons 41 0)
           (cons 42 0)
           (cons 91 0)
           (list 10 9.208 -0.993752)
           (cons 40 0)
           (cons 41 0)
           (cons 42 0)
           (cons 91 0)
           (list 10 9.208 -1.152248)
           (cons 40 0)
           (cons 41 0)
           (cons 42 0)
           (cons 91 0)
           (list 10 9.06576 -1.2)
           (cons 40 0)
           (cons 41 0)
           (cons 42 0)
           (cons 91 0)
           (list 10 8.33424 -1.2)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.192 0.993752)
           (cons 40 0)
           (cons 41 0)
           (cons 42 0)
           (cons 91 0)
           (list 10 8.192 1.152248)
           (cons 40 0)
           (cons 41 0)
           (cons 42 0)
           (cons 91 0)
           (list 10 8.33424 1.2)
           (cons 40 0)
           (cons 41 0)
           (cons 42 0)
           (cons 91 0)
           (list 10 9.06576 1.2)
           (cons 40 0)
           (cons 41 0)
           (cons 42 0)
           (cons 91 0)
           (list 10 9.208 1.152248)
           (cons 40 0)
           (cons 41 0)
           (cons 42 0)
           (cons 91 0)
           (list 10 9.208 0.993752)
           (cons 40 0)
           (cons 41 0)
           (cons 42 0)
           (cons 91 0)
           (list 10 9.06576 0.946)
           (cons 40 0)
           (cons 41 0)
           (cons 42 0)
           (cons 91 0)
           (list 10 8.33424 0.946)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 3.2 0 0)
           (cons 50 0)
          )
         )
         (entmake
          (list
           (cons 0 "ATTDEF")
           (cons 100 "AcDbEntity")
           (cons 67 0)
           (cons 8 "0")
           (cons 100 "AcDbText")
           (list 10 2.5 0.56666667 0)
           (cons 40 0.2)
           (cons 1 "3.200")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 2.5 0.23333333 0)
           (cons 40 0.2)
           (cons 1 "3.200")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 2.5 -0.1 0)
           (cons 40 0.2)
           (cons 1 "8.700")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 2.5 -0.43333333 0)
           (cons 40 0.2)
           (cons 1 "10.500")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 2.5 -0.76666667 0)
           (cons 40 0.2)
           (cons 1 "27.3")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "POINT")
           (cons 100 "AcDbEntity")
           (cons 67 0)
           (cons 8 "0")
           (cons 100 "AcDbPoint")
           (list 10 0 -1.2 0)
           (cons 50 0)
          )
         )
         (entmake
          (list
           (cons 0 "POINT")
           (cons 100 "AcDbEntity")
           (cons 67 0)
           (cons 8 "0")
           (cons 100 "AcDbPoint")
           (list 10 0 1.2 0)
           (cons 50 0)
          )
         )
         (entmake
          (list
           (cons 0 "POINT")
           (cons 100 "AcDbEntity")
           (cons 67 0)
           (cons 8 "0")
           (cons 100 "AcDbPoint")
           (list 10 9.9 1.2 0)
           (cons 50 0)
          )
         )
         (entmake
          (list
           (cons 0 "POINT")
           (cons 100 "AcDbEntity")
           (cons 67 0)
           (cons 8 "0")
           (cons 100 "AcDbPoint")
           (list 10 9.9 -1.2 0)
           (cons 50 0)
          )
         )
         (entmake
          (list
           (cons 0 "POINT")
           (cons 100 "AcDbEntity")
           (cons 67 0)
           (cons 8 "0")
           (cons 100 "AcDbPoint")
           (list 10 3.2 1.2 0)
           (cons 50 0)
          )
         )
         (entmake
          (list
           (cons 0 "POINT")
           (cons 100 "AcDbEntity")
           (cons 67 0)
           (cons 8 "0")
           (cons 100 "AcDbPoint")
           (list 10 3.2 -1.2 0)
           (cons 50 0)
          )
         )
         (entmake
          (list
           (cons 0 "POINT")
           (cons 100 "AcDbEntity")
           (cons 67 0)
           (cons 8 "0")
           (cons 100 "AcDbPoint")
           (list 10 8.7 -1.2 0)
           (cons 50 0)
          )
         )
         (entmake
          (list
           (cons 0 "POINT")
           (cons 100 "AcDbEntity")
           (cons 67 0)
           (cons 8 "0")
           (cons 100 "AcDbPoint")
           (list 10 8.7 1.2 0)
           (cons 50 0)
          )
         )
         (entmake
          (list
           (cons 0 "POINT")
           (cons 100 "AcDbEntity")
           (cons 67 0)
           (cons 8 "0")
           (cons 100 "AcDbPoint")
           (list 10 10.5 0 0)
           (cons 50 0)
          )
         )
         (entmake
          (list
           (cons 0 "INSERT")
           (cons 100 "AcDbEntity")
           (cons 67 0)
           (cons 8 "0")
           (cons 100 "AcDbBlockReference")
           (cons 2 "WheelRightM2")
           (list 10 3.2 0.946 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM2")
           (list 10 3.2 -0.946 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "WheelRightM1"))
        (progn
         (entmake)
         (entmake
          (list
           (cons 0 "BLOCK")
           (cons 2 "WheelRightM1")
           (cons 70 0)
           (cons 4 "")
           (list 10 0 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -0.5588 0.0525272)
           (cons 40 0)
           (cons 41 0)
           (cons 42 0)
           (cons 91 0)
           (list 10 -0.5588 0.2268728)
           (cons 40 0)
           (cons 41 0)
           (cons 42 0)
           (cons 91 0)
           (list 10 -0.402336 0.2794)
           (cons 40 0)
           (cons 41 0)
           (cons 42 0)
           (cons 91 0)
           (list 10 0.402336 0.2794)
           (cons 40 0)
           (cons 41 0)
           (cons 42 0)
           (cons 91 0)
           (list 10 0.5588 0.2268728)
           (cons 40 0)
           (cons 41 0)
           (cons 42 0)
           (cons 91 0)
           (list 10 0.5588 0.0525272)
           (cons 40 0)
           (cons 41 0)
           (cons 42 0)
           (cons 91 0)
           (list 10 0.402336 0)
           (cons 40 0)
           (cons 41 0)
           (cons 42 0)
           (cons 91 0)
           (list 10 -0.402336 0)
           (cons 40 0)
           (cons 41 0)
           (cons 42 0)
           (cons 91 0)
          )
         )
         (entmake (list (cons 0 "ENDBLK")))
        )
       )
       ((= (strcase BLKNAME) (strcase "WheelLeftM1"))
        (progn
         (entmake)
         (entmake
          (list
           (cons 0 "BLOCK")
           (cons 2 "WheelLeftM1")
           (cons 70 0)
           (cons 4 "")
           (list 10 0 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -0.5588 -0.2268728)
           (cons 40 0)
           (cons 41 0)
           (cons 42 0)
           (cons 91 0)
           (list 10 -0.5588 -0.0525272)
           (cons 40 0)
           (cons 41 0)
           (cons 42 0)
           (cons 91 0)
           (list 10 -0.402336 0)
           (cons 40 0)
           (cons 41 0)
           (cons 42 0)
           (cons 91 0)
           (list 10 0.402336 0)
           (cons 40 0)
           (cons 41 0)
           (cons 42 0)
           (cons 91 0)
           (list 10 0.5588 -0.0525272)
           (cons 40 0)
           (cons 41 0)
           (cons 42 0)
           (cons 91 0)
           (list 10 0.5588 -0.2268728)
           (cons 40 0)
           (cons 41 0)
           (cons 42 0)
           (cons 91 0)
           (list 10 0.402336 -0.2794)
           (cons 40 0)
           (cons 41 0)
           (cons 42 0)
           (cons 91 0)
           (list 10 -0.402336 -0.2794)
           (cons 40 0)
           (cons 41 0)
           (cons 42 0)
           (cons 91 0)
          )
         )
         (entmake (list (cons 0 "ENDBLK")))
        )
       )
       ((= (strcase BLKNAME) (strcase "WheelLeft1"))
        (progn
         (entmake)
         (entmake
          (list
           (cons 0 "BLOCK")
           (cons 2 "WheelLeft1")
           (cons 70 0)
           (cons 4 "")
           (list 10 0 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -1.83333333 -0.74433333)
           (cons 40 0)
           (cons 41 0)
           (cons 42 0)
           (cons 91 0)
           (list 10 -1.83333333 -0.17233333)
           (cons 40 0)
           (cons 41 0)
           (cons 42 0)
           (cons 91 0)
           (list 10 -1.32 0)
           (cons 40 0)
           (cons 41 0)
           (cons 42 0)
           (cons 91 0)
           (list 10 1.32 0)
           (cons 40 0)
           (cons 41 0)
           (cons 42 0)
           (cons 91 0)
           (list 10 1.83333333 -0.17233333)
           (cons 40 0)
           (cons 41 0)
           (cons 42 0)
           (cons 91 0)
           (list 10 1.83333333 -0.74433333)
           (cons 40 0)
           (cons 41 0)
           (cons 42 0)
           (cons 91 0)
           (list 10 1.32 -0.91666667)
           (cons 40 0)
           (cons 41 0)
           (cons 42 0)
           (cons 91 0)
           (list 10 -1.32 -0.91666667)
           (cons 40 0)
           (cons 41 0)
           (cons 42 0)
           (cons 91 0)
          )
         )
         (entmake (list (cons 0 "ENDBLK")))
        )
       )
       ((= (strcase BLKNAME) (strcase "WheelRight1"))
        (progn
         (entmake)
         (entmake
          (list
           (cons 0 "BLOCK")
           (cons 2 "WheelRight1")
           (cons 70 0)
           (cons 4 "")
           (list 10 0 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -1.83333333 0.17233333)
           (cons 40 0)
           (cons 41 0)
           (cons 42 0)
           (cons 91 0)
           (list 10 -1.83333333 0.74433333)
           (cons 40 0)
           (cons 41 0)
           (cons 42 0)
           (cons 91 0)
           (list 10 -1.32 0.91666667)
           (cons 40 0)
           (cons 41 0)
           (cons 42 0)
           (cons 91 0)
           (list 10 1.32 0.91666667)
           (cons 40 0)
           (cons 41 0)
           (cons 42 0)
           (cons 91 0)
           (list 10 1.83333333 0.74433333)
           (cons 40 0)
           (cons 41 0)
           (cons 42 0)
           (cons 91 0)
           (list 10 1.83333333 0.17233333)
           (cons 40 0)
           (cons 41 0)
           (cons 42 0)
           (cons 91 0)
           (list 10 1.32 0)
           (cons 40 0)
           (cons 41 0)
           (cons 42 0)
           (cons 91 0)
           (list 10 -1.32 0)
           (cons 40 0)
           (cons 41 0)
           (cons 42 0)
           (cons 91 0)
          )
         )
         (entmake (list (cons 0 "ENDBLK")))
        )
       )
       ((= (strcase BLKNAME) (strcase "WheelLeft2"))
        (progn
         (entmake)
         (entmake
          (list
           (cons 0 "BLOCK")
           (cons 2 "WheelLeft2")
           (cons 70 0)
           (cons 4 "")
           (list 10 0 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -1.66666667 -0.67666667)
           (cons 40 0)
           (cons 41 0)
           (cons 42 0)
           (cons 91 0)
           (list 10 -1.66666667 -0.15666667)
           (cons 40 0)
           (cons 41 0)
           (cons 42 0)
           (cons 91 0)
           (list 10 -1.2 0)
           (cons 40 0)
           (cons 41 0)
           (cons 42 0)
           (cons 91 0)
           (list 10 1.2 0)
           (cons 40 0)
           (cons 41 0)
           (cons 42 0)
           (cons 91 0)
           (list 10 1.66666667 -0.15666667)
           (cons 40 0)
           (cons 41 0)
           (cons 42 0)
           (cons 91 0)
           (list 10 1.66666667 -0.67666667)
           (cons 40 0)
           (cons 41 0)
           (cons 42 0)
           (cons 91 0)
           (list 10 1.2 -0.83333333)
           (cons 40 0)
           (cons 41 0)
           (cons 42 0)
           (cons 91 0)
           (list 10 -1.2 -0.83333333)
           (cons 40 0)
           (cons 41 0)
           (cons 42 0)
           (cons 91 0)
          )
         )
         (entmake (list (cons 0 "ENDBLK")))
        )
       )
       ((= (strcase BLKNAME) (strcase "WheelRight2"))
        (progn
         (entmake)
         (entmake
          (list
           (cons 0 "BLOCK")
           (cons 2 "WheelRight2")
           (cons 70 0)
           (cons 4 "")
           (list 10 0 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -1.66666667 0.15666667)
           (cons 40 0)
           (cons 41 0)
           (cons 42 0)
           (cons 91 0)
           (list 10 -1.66666667 0.67666667)
           (cons 40 0)
           (cons 41 0)
           (cons 42 0)
           (cons 91 0)
           (list 10 -1.2 0.83333333)
           (cons 40 0)
           (cons 41 0)
           (cons 42 0)
           (cons 91 0)
           (list 10 1.2 0.83333333)
           (cons 40 0)
           (cons 41 0)
           (cons 42 0)
           (cons 91 0)
           (list 10 1.66666667 0.67666667)
           (cons 40 0)
           (cons 41 0)
           (cons 42 0)
           (cons 91 0)
           (list 10 1.66666667 0.15666667)
           (cons 40 0)
           (cons 41 0)
           (cons 42 0)
           (cons 91 0)
           (list 10 1.2 0)
           (cons 40 0)
           (cons 41 0)
           (cons 42 0)
           (cons 91 0)
           (list 10 -1.2 0)
           (cons 40 0)
           (cons 41 0)
           (cons 42 0)
           (cons 91 0)
          )
         )
         (entmake (list (cons 0 "ENDBLK")))
        )
       )
       ((= (strcase BLKNAME) (strcase "WheelLeft4"))
        (progn
         (entmake)
         (entmake
          (list
           (cons 0 "BLOCK")
           (cons 2 "WheelLeft4")
           (cons 70 0)
           (cons 4 "")
           (list 10 0 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -1.04166667 -0.42291667)
           (cons 40 0)
           (cons 41 0)
           (cons 42 0)
           (cons 91 0)
           (list 10 -1.04166667 -0.09791667)
           (cons 40 0)
           (cons 41 0)
           (cons 42 0)
           (cons 91 0)
           (list 10 -0.75 0)
           (cons 40 0)
           (cons 41 0)
           (cons 42 0)
           (cons 91 0)
           (list 10 0.75 0)
           (cons 40 0)
           (cons 41 0)
           (cons 42 0)
           (cons 91 0)
           (list 10 1.04166667 -0.09791667)
           (cons 40 0)
           (cons 41 0)
           (cons 42 0)
           (cons 91 0)
           (list 10 1.04166667 -0.42291667)
           (cons 40 0)
           (cons 41 0)
           (cons 42 0)
           (cons 91 0)
           (list 10 0.75 -0.52083333)
           (cons 40 0)
           (cons 41 0)
           (cons 42 0)
           (cons 91 0)
           (list 10 -0.75 -0.52083333)
           (cons 40 0)
           (cons 41 0)
           (cons 42 0)
           (cons 91 0)
          )
         )
         (entmake (list (cons 0 "ENDBLK")))
        )
       )
       ((= (strcase BLKNAME) (strcase "WheelRight4"))
        (progn
         (entmake)
         (entmake
          (list
           (cons 0 "BLOCK")
           (cons 2 "WheelRight4")
           (cons 70 0)
           (cons 4 "")
           (list 10 0 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -1.04166667 0.09791667)
           (cons 40 0)
           (cons 41 0)
           (cons 42 0)
           (cons 91 0)
           (list 10 -1.04166667 0.42291667)
           (cons 40 0)
           (cons 41 0)
           (cons 42 0)
           (cons 91 0)
           (list 10 -0.75 0.52083333)
           (cons 40 0)
           (cons 41 0)
           (cons 42 0)
           (cons 91 0)
           (list 10 0.75 0.52083333)
           (cons 40 0)
           (cons 41 0)
           (cons 42 0)
           (cons 91 0)
           (list 10 1.04166667 0.42291667)
           (cons 40 0)
           (cons 41 0)
           (cons 42 0)
           (cons 91 0)
           (list 10 1.04166667 0.09791667)
           (cons 40 0)
           (cons 41 0)
           (cons 42 0)
           (cons 91 0)
           (list 10 0.75 0)
           (cons 40 0)
           (cons 41 0)
           (cons 42 0)
           (cons 91 0)
           (list 10 -0.75 0)
           (cons 40 0)
           (cons 41 0)
           (cons 42 0)
           (cons 91 0)
          )
         )
         (entmake (list (cons 0 "ENDBLK")))
        )
       )
       ((= (strcase BLKNAME) (strcase "WheelRightM2"))
        (progn
         (entmake)
         (entmake
          (list
           (cons 0 "BLOCK")
           (cons 2 "WheelRightM2")
           (cons 70 0)
           (cons 4 "")
           (list 10 0 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -0.508 0.047752)
           (cons 40 0)
           (cons 41 0)
           (cons 42 0)
           (cons 91 0)
           (list 10 -0.508 0.206248)
           (cons 40 0)
           (cons 41 0)
           (cons 42 0)
           (cons 91 0)
           (list 10 -0.36576 0.254)
           (cons 40 0)
           (cons 41 0)
           (cons 42 0)
           (cons 91 0)
           (list 10 0.36576 0.254)
           (cons 40 0)
           (cons 41 0)
           (cons 42 0)
           (cons 91 0)
           (list 10 0.508 0.206248)
           (cons 40 0)
           (cons 41 0)
           (cons 42 0)
           (cons 91 0)
           (list 10 0.508 0.047752)
           (cons 40 0)
           (cons 41 0)
           (cons 42 0)
           (cons 91 0)
           (list 10 0.36576 0)
           (cons 40 0)
           (cons 41 0)
           (cons 42 0)
           (cons 91 0)
           (list 10 -0.36576 0)
           (cons 40 0)
           (cons 41 0)
           (cons 42 0)
           (cons 91 0)
          )
         )
         (entmake (list (cons 0 "ENDBLK")))
        )
       )
       ((= (strcase BLKNAME) (strcase "WheelLeftM2"))
        (progn
         (entmake)
         (entmake
          (list
           (cons 0 "BLOCK")
           (cons 2 "WheelLeftM2")
           (cons 70 0)
           (cons 4 "")
           (list 10 0 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -0.508 -0.206248)
           (cons 40 0)
           (cons 41 0)
           (cons 42 0)
           (cons 91 0)
           (list 10 -0.508 -0.047752)
           (cons 40 0)
           (cons 41 0)
           (cons 42 0)
           (cons 91 0)
           (list 10 -0.36576 0)
           (cons 40 0)
           (cons 41 0)
           (cons 42 0)
           (cons 91 0)
           (list 10 0.36576 0)
           (cons 40 0)
           (cons 41 0)
           (cons 42 0)
           (cons 91 0)
           (list 10 0.508 -0.047752)
           (cons 40 0)
           (cons 41 0)
           (cons 42 0)
           (cons 91 0)
           (list 10 0.508 -0.206248)
           (cons 40 0)
           (cons 41 0)
           (cons 42 0)
           (cons 91 0)
           (list 10 0.36576 -0.254)
           (cons 40 0)
           (cons 41 0)
           (cons 42 0)
           (cons 91 0)
           (list 10 -0.36576 -0.254)
           (cons 40 0)
           (cons 41 0)
           (cons 42 0)
           (cons 91 0)
          )
         )
         (entmake (list (cons 0 "ENDBLK")))
        )
       )
       ((= (strcase BLKNAME) (strcase "WheelRightM3"))
        (progn
         (entmake)
         (entmake
          (list
           (cons 0 "BLOCK")
           (cons 2 "WheelRightM3")
           (cons 70 0)
           (cons 4 "")
           (list 10 0 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -0.3429 0.0322326)
           (cons 40 0)
           (cons 41 0)
           (cons 42 0)
           (cons 91 0)
           (list 10 -0.3429 0.1392174)
           (cons 40 0)
           (cons 41 0)
           (cons 42 0)
           (cons 91 0)
           (list 10 -0.246888 0.17145)
           (cons 40 0)
           (cons 41 0)
           (cons 42 0)
           (cons 91 0)
           (list 10 0.246888 0.17145)
           (cons 40 0)
           (cons 41 0)
           (cons 42 0)
           (cons 91 0)
           (list 10 0.3429 0.1392174)
           (cons 40 0)
           (cons 41 0)
           (cons 42 0)
           (cons 91 0)
           (list 10 0.3429 0.0322326)
           (cons 40 0)
           (cons 41 0)
           (cons 42 0)
           (cons 91 0)
           (list 10 0.246888 0)
           (cons 40 0)
           (cons 41 0)
           (cons 42 0)
           (cons 91 0)
           (list 10 -0.246888 0)
           (cons 40 0)
           (cons 41 0)
           (cons 42 0)
           (cons 91 0)
          )
         )
         (entmake (list (cons 0 "ENDBLK")))
        )
       )
       ((= (strcase BLKNAME) (strcase "WheelLeftM3"))
        (progn
         (entmake)
         (entmake
          (list
           (cons 0 "BLOCK")
           (cons 2 "WheelLeftM3")
           (cons 70 0)
           (cons 4 "")
           (list 10 0 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -0.3429 -0.1392174)
           (cons 40 0)
           (cons 41 0)
           (cons 42 0)
           (cons 91 0)
           (list 10 -0.3429 -0.0322326)
           (cons 40 0)
           (cons 41 0)
           (cons 42 0)
           (cons 91 0)
           (list 10 -0.246888 0)
           (cons 40 0)
           (cons 41 0)
           (cons 42 0)
           (cons 91 0)
           (list 10 0.246888 0)
           (cons 40 0)
           (cons 41 0)
           (cons 42 0)
           (cons 91 0)
           (list 10 0.3429 -0.0322326)
           (cons 40 0)
           (cons 41 0)
           (cons 42 0)
           (cons 91 0)
           (list 10 0.3429 -0.1392174)
           (cons 40 0)
           (cons 41 0)
           (cons 42 0)
           (cons 91 0)
           (list 10 0.246888 -0.17145)
           (cons 40 0)
           (cons 41 0)
           (cons 42 0)
           (cons 91 0)
           (list 10 -0.246888 -0.17145)
           (cons 40 0)
           (cons 41 0)
           (cons 42 0)
           (cons 91 0)
          )
         )
         (entmake (list (cons 0 "ENDBLK")))
        )
       )
       ((= (strcase BLKNAME) (strcase "Wheel5"))
        (progn
         (entmake)
         (entmake
          (list
           (cons 0 "BLOCK")
           (cons 2 "Wheel5")
           (cons 70 0)
           (cons 4 "")
           (list 10 0 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -0.4572 -2.48804176)
           (cons 40 0)
           (cons 41 0)
           (cons 42 0)
           (cons 91 0)
           (list 10 -0.4572 -2.15203024)
           (cons 40 0)
           (cons 41 0)
           (cons 42 0)
           (cons 91 0)
           (list 10 -0.329184 -2.050796)
           (cons 40 0)
           (cons 41 0)
           (cons 42 0)
           (cons 91 0)
           (list 10 0.329184 -2.050796)
           (cons 40 0)
           (cons 41 0)
           (cons 42 0)
           (cons 91 0)
           (list 10 0.4572 -2.15203024)
           (cons 40 0)
           (cons 41 0)
           (cons 42 0)
           (cons 91 0)
           (list 10 0.4572 -2.48804176)
           (cons 40 0)
           (cons 41 0)
           (cons 42 0)
           (cons 91 0)
           (list 10 0.329184 -2.589276)
           (cons 40 0)
           (cons 41 0)
           (cons 42 0)
           (cons 91 0)
           (list 10 -0.329184 -2.589276)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -0.4572 -1.52030176)
           (cons 40 0)
           (cons 41 0)
           (cons 42 0)
           (cons 91 0)
           (list 10 -0.4572 -1.18429024)
           (cons 40 0)
           (cons 41 0)
           (cons 42 0)
           (cons 91 0)
           (list 10 -0.329184 -1.083056)
           (cons 40 0)
           (cons 41 0)
           (cons 42 0)
           (cons 91 0)
           (list 10 0.329184 -1.083056)
           (cons 40 0)
           (cons 41 0)
           (cons 42 0)
           (cons 91 0)
           (list 10 0.4572 -1.18429024)
           (cons 40 0)
           (cons 41 0)
           (cons 42 0)
           (cons 91 0)
           (list 10 0.4572 -1.52030176)
           (cons 40 0)
           (cons 41 0)
           (cons 42 0)
           (cons 91 0)
           (list 10 0.329184 -1.621536)
           (cons 40 0)
           (cons 41 0)
           (cons 42 0)
           (cons 91 0)
           (list 10 -0.329184 -1.621536)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -0.4572 -0.55256176)
           (cons 40 0)
           (cons 41 0)
           (cons 42 0)
           (cons 91 0)
           (list 10 -0.4572 -0.21655024)
           (cons 40 0)
           (cons 41 0)
           (cons 42 0)
           (cons 91 0)
           (list 10 -0.329184 -0.115316)
           (cons 40 0)
           (cons 41 0)
           (cons 42 0)
           (cons 91 0)
           (list 10 0.329184 -0.115316)
           (cons 40 0)
           (cons 41 0)
           (cons 42 0)
           (cons 91 0)
           (list 10 0.4572 -0.21655024)
           (cons 40 0)
           (cons 41 0)
           (cons 42 0)
           (cons 91 0)
           (list 10 0.4572 -0.55256176)
           (cons 40 0)
           (cons 41 0)
           (cons 42 0)
           (cons 91 0)
           (list 10 0.329184 -0.653796)
           (cons 40 0)
           (cons 41 0)
           (cons 42 0)
           (cons 91 0)
           (list 10 -0.329184 -0.653796)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -0.4572 0.21655024)
           (cons 40 0)
           (cons 41 0)
           (cons 42 0)
           (cons 91 0)
           (list 10 -0.4572 0.55256176)
           (cons 40 0)
           (cons 41 0)
           (cons 42 0)
           (cons 91 0)
           (list 10 -0.329184 0.653796)
           (cons 40 0)
           (cons 41 0)
           (cons 42 0)
           (cons 91 0)
           (list 10 0.329184 0.653796)
           (cons 40 0)
           (cons 41 0)
           (cons 42 0)
           (cons 91 0)
           (list 10 0.4572 0.55256176)
           (cons 40 0)
           (cons 41 0)
           (cons 42 0)
           (cons 91 0)
           (list 10 0.4572 0.21655024)
           (cons 40 0)
           (cons 41 0)
           (cons 42 0)
           (cons 91 0)
           (list 10 0.329184 0.115316)
           (cons 40 0)
           (cons 41 0)
           (cons 42 0)
           (cons 91 0)
           (list 10 -0.329184 0.115316)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -0.4572 1.18429024)
           (cons 40 0)
           (cons 41 0)
           (cons 42 0)
           (cons 91 0)
           (list 10 -0.4572 1.52030176)
           (cons 40 0)
           (cons 41 0)
           (cons 42 0)
           (cons 91 0)
           (list 10 -0.329184 1.621536)
           (cons 40 0)
           (cons 41 0)
           (cons 42 0)
           (cons 91 0)
           (list 10 0.329184 1.621536)
           (cons 40 0)
           (cons 41 0)
           (cons 42 0)
           (cons 91 0)
           (list 10 0.4572 1.52030176)
           (cons 40 0)
           (cons 41 0)
           (cons 42 0)
           (cons 91 0)
           (list 10 0.4572 1.18429024)
           (cons 40 0)
           (cons 41 0)
           (cons 42 0)
           (cons 91 0)
           (list 10 0.329184 1.083056)
           (cons 40 0)
           (cons 41 0)
           (cons 42 0)
           (cons 91 0)
           (list 10 -0.329184 1.083056)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -0.4572 2.15203024)
           (cons 40 0)
           (cons 41 0)
           (cons 42 0)
           (cons 91 0)
           (list 10 -0.4572 2.48804176)
           (cons 40 0)
           (cons 41 0)
           (cons 42 0)
           (cons 91 0)
           (list 10 -0.329184 2.589276)
           (cons 40 0)
           (cons 41 0)
           (cons 42 0)
           (cons 91 0)
           (list 10 0.329184 2.589276)
           (cons 40 0)
           (cons 41 0)
           (cons 42 0)
           (cons 91 0)
           (list 10 0.4572 2.48804176)
           (cons 40 0)
           (cons 41 0)
           (cons 42 0)
           (cons 91 0)
           (list 10 0.4572 2.15203024)
           (cons 40 0)
           (cons 41 0)
           (cons 42 0)
           (cons 91 0)
           (list 10 0.329184 2.050796)
           (cons 40 0)
           (cons 41 0)
           (cons 42 0)
           (cons 91 0)
           (list 10 -0.329184 2.050796)
           (cons 40 0)
           (cons 41 0)
           (cons 42 0)
           (cons 91 0)
          )
         )
         (entmake (list (cons 0 "ENDBLK")))
        )
       )
       ((= (strcase BLKNAME) (strcase "WheelLeftM6"))
        (progn
         (entmake)
         (entmake
          (list
           (cons 0 "BLOCK")
           (cons 2 "WheelLeftM6")
           (cons 70 0)
           (cons 4 "")
           (list 10 0 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -0.508 -0.206248)
           (cons 40 0)
           (cons 41 0)
           (cons 42 0)
           (cons 91 0)
           (list 10 -0.508 -0.047752)
           (cons 40 0)
           (cons 41 0)
           (cons 42 0)
           (cons 91 0)
           (list 10 -0.36576 0)
           (cons 40 0)
           (cons 41 0)
           (cons 42 0)
           (cons 91 0)
           (list 10 0.36576 0)
           (cons 40 0)
           (cons 41 0)
           (cons 42 0)
           (cons 91 0)
           (list 10 0.508 -0.047752)
           (cons 40 0)
           (cons 41 0)
           (cons 42 0)
           (cons 91 0)
           (list 10 0.508 -0.206248)
           (cons 40 0)
           (cons 41 0)
           (cons 42 0)
           (cons 91 0)
           (list 10 0.36576 -0.254)
           (cons 40 0)
           (cons 41 0)
           (cons 42 0)
           (cons 91 0)
           (list 10 -0.36576 -0.254)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -0.508 -0.663448)
           (cons 40 0)
           (cons 41 0)
           (cons 42 0)
           (cons 91 0)
           (list 10 -0.508 -0.504952)
           (cons 40 0)
           (cons 41 0)
           (cons 42 0)
           (cons 91 0)
           (list 10 -0.36576 -0.4572)
           (cons 40 0)
           (cons 41 0)
           (cons 42 0)
           (cons 91 0)
           (list 10 0.36576 -0.4572)
           (cons 40 0)
           (cons 41 0)
           (cons 42 0)
           (cons 91 0)
           (list 10 0.508 -0.504952)
           (cons 40 0)
           (cons 41 0)
           (cons 42 0)
           (cons 91 0)
           (list 10 0.508 -0.663448)
           (cons 40 0)
           (cons 41 0)
           (cons 42 0)
           (cons 91 0)
           (list 10 0.36576 -0.7112)
           (cons 40 0)
           (cons 41 0)
           (cons 42 0)
           (cons 91 0)
           (list 10 -0.36576 -0.7112)
           (cons 40 0)
           (cons 41 0)
           (cons 42 0)
           (cons 91 0)
          )
         )
         (entmake (list (cons 0 "ENDBLK")))
        )
       )
       ((= (strcase BLKNAME) (strcase "WheelRightM6"))
        (progn
         (entmake)
         (entmake
          (list
           (cons 0 "BLOCK")
           (cons 2 "WheelRightM6")
           (cons 70 0)
           (cons 4 "")
           (list 10 0 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -0.508 0.047752)
           (cons 40 0)
           (cons 41 0)
           (cons 42 0)
           (cons 91 0)
           (list 10 -0.508 0.206248)
           (cons 40 0)
           (cons 41 0)
           (cons 42 0)
           (cons 91 0)
           (list 10 -0.36576 0.254)
           (cons 40 0)
           (cons 41 0)
           (cons 42 0)
           (cons 91 0)
           (list 10 0.36576 0.254)
           (cons 40 0)
           (cons 41 0)
           (cons 42 0)
           (cons 91 0)
           (list 10 0.508 0.206248)
           (cons 40 0)
           (cons 41 0)
           (cons 42 0)
           (cons 91 0)
           (list 10 0.508 0.047752)
           (cons 40 0)
           (cons 41 0)
           (cons 42 0)
           (cons 91 0)
           (list 10 0.36576 0)
           (cons 40 0)
           (cons 41 0)
           (cons 42 0)
           (cons 91 0)
           (list 10 -0.36576 0)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -0.508 0.504952)
           (cons 40 0)
           (cons 41 0)
           (cons 42 0)
           (cons 91 0)
           (list 10 -0.508 0.663448)
           (cons 40 0)
           (cons 41 0)
           (cons 42 0)
           (cons 91 0)
           (list 10 -0.36576 0.7112)
           (cons 40 0)
           (cons 41 0)
           (cons 42 0)
           (cons 91 0)
           (list 10 0.36576 0.7112)
           (cons 40 0)
           (cons 41 0)
           (cons 42 0)
           (cons 91 0)
           (list 10 0.508 0.663448)
           (cons 40 0)
           (cons 41 0)
           (cons 42 0)
           (cons 91 0)
           (list 10 0.508 0.504952)
           (cons 40 0)
           (cons 41 0)
           (cons 42 0)
           (cons 91 0)
           (list 10 0.36576 0.4572)
           (cons 40 0)
           (cons 41 0)
           (cons 42 0)
           (cons 91 0)
           (list 10 -0.36576 0.4572)
           (cons 40 0)
           (cons 41 0)
           (cons 42 0)
           (cons 91 0)
          )
         )
         (entmake (list (cons 0 "ENDBLK")))
        )
       )
       (T
        (progn
         (alert (strcat "!!! BLOCK DOES NOT EXIST - " BLKNAME " !!!"))
        )
       )
 )
)
;
;
;     Program written by Robert Livingston, 2015-11-18
;
;     QTMAKESLB creates the QuickTurn Vehicle Library Slide Library file
;
;
(defun QT:MAKESLB (FILE / C FILEBINARY _WriteStream)
;  _WriteStream obtained from Michael Puckett (https://www.linkedin.com/in/puckettm)
;     http://www.theswamp.org/index.php?topic=17465.0
;
 (defun _WriteStream ( path text mode / fso stream file result )

     ;;  Return the file size if the file is successfully written 
     ;;  to, otherwise nil. Will write all ascii chars to file
     ;;  including nulls. If the caller wants to pass a list of
     ;;  byte values to the function just call it like so:
     ;;
     ;;      (_WriteStream 
     ;;          path 
     ;;          (vl-list->string '(87 111 111 116 33)) 
     ;;          mode
     ;;      ) 
     ;;
     ;;  Arguments:
     ;;
     ;;      path  <duh>
     ;;      text  <duh>
     ;;      mode  "a" to create/append, 
     ;;            "w" to create/overwrite (default)
    
     (setq mode (if (member mode '("a" "A")) "a" "w"))
    
     (vl-catch-all-apply
        '(lambda ( / format )
             (setq fso (vlax-create-object "Scripting.FileSystemObject"))
             (cond
                 (   (or (null (findfile path)) (eq "w" mode))
                     (setq stream
                         (vlax-invoke 
                             fso
                            'CreateTextFile 
                             path 
                            -1 ;; 0 (false) = don't overwrite , -1 (true) = overwrite
                             0 ;; 0 (false) = ascii, -1 (true) = unicode 
                         )
                     )
                     (setq file (vlax-invoke fso 'GetFile path))
                 )
                 (   (setq file (vlax-invoke fso 'GetFile path))
                     (setq stream
                         (vlax-invoke 
                             file
                            'OpenAsTextStream 
                             8 ;; 1 = read, 2 = write, 8 = append
                             0 ;; 0 = ascii, -1 = unicode, -2 system default
                         )
                     )       
                 )
             )
             (vlax-invoke stream 'Write text)
             (vlax-invoke stream 'Close)
             (setq result (vlax-get file 'Size))
         )
     )

     (if file (vlax-release-object file))
     (if stream (vlax-release-object stream))
     (if fso (vlax-release-object fso))
    
     result
    
 )
 (_WriteStream FILE (vl-list->string (list 65  117 116 111 67  65  68  32  83  108 105 100 101 32  76  105 98  114 97  114 121 32  49  46  48  13  10  26  0   0   0   0   66  67  95  77  79  84  73  45  84  83  55  0   0   0   0   0   0   0   0   0   0   0   0   0   0   0   0   0   0   0   0   0   
                                           0   8   0   0   65  65  83  72  84  79  45  50  48  49  49  45  87  66  45  49  48  48  84  0   0   0   0   0   0   0   0   0   0   0   0   0   167 34  0   0   65  66  95  73  78  70  45  87  66  45  51  51  0   0   0   0   0   0   0   0   0   0   0   0   
                                           0   0   0   0   0   0   0   0   184 56  0   0   84  65  67  45  49  57  57  57  45  66  84  68  0   0   0   0   0   0   0   0   0   0   0   0   0   0   0   0   0   0   0   0   65  97  0   0   65  65  83  72  84  79  45  50  48  49  49  45  77  72  66  0   
                                           0   0   0   0   0   0   0   0   0   0   0   0   0   0   0   0   172 117 0   0   66  67  95  77  79  84  73  45  76  71  53  0   0   0   0   0   0   0   0   0   0   0   0   0   0   0   0   0   0   0   0   0   143 126 0   0   65  66  95  73  78  70  45  66  
                                           85  83  0   0   0   0   0   0   0   0   0   0   0   0   0   0   0   0   0   0   0   0   0   0   68  146 0   0   65  65  83  72  84  79  45  50  48  49  49  45  87  66  45  52  48  0   0   0   0   0   0   0   0   0   0   0   0   0   0   0   79  155 0   0   
                                           84  65  67  45  49  57  57  57  45  87  66  45  50  48  0   0   0   0   0   0   0   0   0   0   0   0   0   0   0   0   0   0   78  165 0   0   65  65  83  72  84  79  45  50  48  49  49  45  87  66  45  54  50  0   0   0   0   0   0   0   0   0   0   0   
                                           0   0   0   0   137 178 0   0   84  65  67  45  49  57  57  57  45  65  84  68  0   0   0   0   0   0   0   0   0   0   0   0   0   0   0   0   0   0   0   0   144 189 0   0   65  66  95  73  78  70  45  87  66  45  49  55  0   0   0   0   0   0   0   0   
                                           0   0   0   0   0   0   0   0   0   0   0   0   205 212 0   0   65  65  83  72  84  79  45  50  48  49  49  45  83  85  45  51  48  0   0   0   0   0   0   0   0   0   0   0   0   0   0   0   74  229 0   0   84  65  67  45  49  57  57  57  45  77  83  85  
                                           0   0   0   0   0   0   0   0   0   0   0   0   0   0   0   0   0   0   0   0   101 234 0   0   65  66  95  73  78  70  45  87  66  45  50  51  0   0   0   0   0   0   0   0   0   0   0   0   0   0   0   0   0   0   0   0   112 240 0   0   65  65  83  72  
                                           84  79  45  50  48  49  49  45  77  72  84  0   0   0   0   0   0   0   0   0   0   0   0   0   0   0   0   0   59  11  1   0   65  66  95  73  78  70  45  76  79  71  72  65  85  76  0   0   0   0   0   0   0   0   0   0   0   0   0   0   0   0   0   0   
                                           130 20  1   0   84  65  67  45  49  57  57  57  45  73  45  66  85  83  0   0   0   0   0   0   0   0   0   0   0   0   0   0   0   0   0   0   17  52  1   0   66  67  95  77  79  84  73  45  87  66  45  49  53  0   0   0   0   0   0   0   0   0   0   0   
                                           0   0   0   0   0   0   0   0   152 57  1   0   84  65  67  45  49  57  57  57  45  87  66  45  49  57  0   0   0   0   0   0   0   0   0   0   0   0   0   0   0   0   0   0   107 72  1   0   65  65  83  72  84  79  45  50  48  49  49  45  83  85  45  52  
                                           48  0   0   0   0   0   0   0   0   0   0   0   0   0   0   0   190 87  1   0   84  65  67  45  49  57  57  57  45  72  83  85  0   0   0   0   0   0   0   0   0   0   0   0   0   0   0   0   0   0   0   0   225 93  1   0   65  65  83  72  84  79  45  50  
                                           48  49  49  45  87  66  45  54  55  0   0   0   0   0   0   0   0   0   0   0   0   0   0   0   244 100 1   0   65  65  83  72  84  79  45  50  48  49  49  45  66  85  83  45  52  53  0   0   0   0   0   0   0   0   0   0   0   0   0   0   169 111 1   0   
                                           65  65  83  72  84  79  45  50  48  49  49  45  80  66  0   0   0   0   0   0   0   0   0   0   0   0   0   0   0   0   0   0   194 116 1   0   65  65  83  72  84  79  45  50  48  49  49  45  83  45  66  85  83  45  52  48  0   0   0   0   0   0   0   0   
                                           0   0   0   0   229 127 1   0   65  66  95  73  78  70  45  53  65  88  76  69  0   0   0   0   0   0   0   0   0   0   0   0   0   0   0   0   0   0   0   0   124 132 1   0   65  66  95  73  78  70  45  87  66  45  50  49  0   0   0   0   0   0   0   0   
                                           0   0   0   0   0   0   0   0   0   0   0   0   191 146 1   0   65  65  83  72  84  79  45  50  48  49  49  45  80  0   0   0   0   0   0   0   0   0   0   0   0   0   0   0   0   0   0   0   92  165 1   0   65  66  95  73  78  70  45  65  66  85  83  0   
                                           0   0   0   0   0   0   0   0   0   0   0   0   0   0   0   0   0   0   0   0   71  170 1   0   84  65  67  45  49  57  57  57  45  80  0   0   0   0   0   0   0   0   0   0   0   0   0   0   0   0   0   0   0   0   0   0   144 183 1   0   65  66  95  73  
                                           78  70  45  73  45  66  85  83  0   0   0   0   0   0   0   0   0   0   0   0   0   0   0   0   0   0   0   0   23  189 1   0   65  65  83  72  84  79  45  50  48  49  49  45  77  72  0   0   0   0   0   0   0   0   0   0   0   0   0   0   0   0   0   0   
                                           174 199 1   0   65  65  83  72  84  79  45  50  48  49  49  45  66  85  83  45  52  48  0   0   0   0   0   0   0   0   0   0   0   0   0   0   153 204 1   0   84  65  67  45  49  57  57  57  45  76  83  85  0   0   0   0   0   0   0   0   0   0   0   0   
                                           0   0   0   0   0   0   0   0   186 210 1   0   65  66  95  73  78  70  45  87  66  45  51  54  0   0   0   0   0   0   0   0   0   0   0   0   0   0   0   0   0   0   0   0   65  216 1   0   65  65  83  72  84  79  45  50  48  49  49  45  87  66  45  57  
                                           50  68  0   0   0   0   0   0   0   0   0   0   0   0   0   0   200 240 1   0   65  66  95  73  78  70  45  83  85  57  0   0   0   0   0   0   0   0   0   0   0   0   0   0   0   0   0   0   0   0   0   0   1   3   2   0   65  65  83  72  84  79  45  50  
                                           48  49  49  45  80  84  0   0   0   0   0   0   0   0   0   0   0   0   0   0   0   0   0   0   94  10  2   0   65  66  95  73  78  70  45  87  66  45  49  50  0   0   0   0   0   0   0   0   0   0   0   0   0   0   0   0   0   0   0   0   5   21  2   0   
                                           65  65  83  72  84  79  45  50  48  49  49  45  87  66  45  54  55  68  0   0   0   0   0   0   0   0   0   0   0   0   0   0   34  41  2   0   65  65  83  72  84  79  45  50  48  49  49  45  65  45  66  85  83  0   0   0   0   0   0   0   0   0   0   0   
                                           0   0   0   0   255 56  2   0   65  66  95  73  78  70  45  80  0   0   0   0   0   0   0   0   0   0   0   0   0   0   0   0   0   0   0   0   0   0   0   0   42  65  2   0   65  66  95  73  78  70  45  80  84  0   0   0   0   0   0   0   0   0   0   0   
                                           0   0   0   0   0   0   0   0   0   0   0   0   245 71  2   0   65  65  83  72  84  79  45  50  48  49  49  45  83  45  66  85  83  45  51  54  0   0   0   0   0   0   0   0   0   0   0   0   54  85  2   0   65  65  83  72  84  79  45  50  48  49  49  45  
                                           87  66  45  50  48  68  0   0   0   0   0   0   0   0   0   0   0   0   0   0   79  90  2   0   83  80  69  67  73  65  76  45  49  57  72  69  65  86  89  72  65  85  76  0   0   0   0   0   0   0   0   0   0   0   0   0   38  111 2   0   65  66  95  73  
                                           78  70  45  87  66  45  50  56  0   0   0   0   0   0   0   0   0   0   0   0   0   0   0   0   0   0   0   0   199 147 2   0   84  65  67  45  49  57  57  57  45  65  45  66  85  83  0   0   0   0   0   0   0   0   0   0   0   0   0   0   0   0   0   0   
                                           206 173 2   0   65  65  83  72  84  79  45  50  48  49  49  45  87  66  45  49  48  57  68  0   0   0   0   0   0   0   0   0   0   0   0   0   175 183 2   0   65  66  95  73  78  70  45  87  66  45  49  53  0   0   0   0   0   0   0   0   0   0   0   0   
                                           0   0   0   0   0   0   0   0   74  204 2   0   84  65  67  45  49  57  57  57  45  66  45  49  50  0   0   0   0   0   0   0   0   0   0   0   0   0   0   0   0   0   0   0   199 220 2   0   66  67  95  77  79  84  73  45  76  71  51  0   0   0   0   0   
                                           0   0   0   0   0   0   0   0   0   0   0   0   0   0   0   0   78  226 2   0   65  66  95  73  78  70  45  72  69  65  86  89  72  65  85  76  0   0   0   0   0   0   0   0   0   0   0   0   0   0   0   0   3   246 2   0   65  65  83  72  84  79  45  50  
                                           48  49  49  45  67  73  84  89  45  66  85  83  0   0   0   0   0   0   0   0   0   0   0   0   84  19  3   0   0   0   0   0   0   0   0   0   0   0   0   0   0   0   0   0   0   0   0   0   0   0   0   0   0   0   0   0   0   0   0   0   0   0   0   0   
                                           65  117 116 111 67  65  68  32  83  108 105 100 101 13  10  26  0   86  2   73  6   31  3   200 70  51  1   2   0   52  18  7   255 7   255 106 0   223 1   106 0   224 1   106 0   224 1   106 0   225 1   106 0   225 1   105 0   226 1   105 0   226 1   105 
                                           0   227 1   105 0   227 1   104 0   228 1   104 0   228 1   103 0   229 1   103 0   229 1   102 0   230 1   102 0   230 1   101 0   230 1   101 0   230 1   100 0   230 1   100 0   230 1   98  0   230 1   98  0   230 1   97  0   230 1   97  0   230 1   96  
                                           0   230 1   96  0   230 1   95  0   230 1   95  0   230 1   94  0   229 1   94  0   229 1   93  0   229 1   93  0   229 1   93  0   228 1   93  0   228 1   92  0   227 1   92  0   227 1   91  0   226 1   91  0   226 1   91  0   225 1   91  0   225 1   91  
                                           0   224 1   91  0   224 1   91  0   223 1   91  0   223 1   91  0   222 1   91  0   222 1   91  0   221 1   91  0   221 1   91  0   220 1   91  0   220 1   92  0   219 1   92  0   219 1   93  0   218 1   93  0   218 1   93  0   217 1   93  0   217 1   94  
                                           0   216 1   94  0   216 1   95  0   216 1   95  0   216 1   96  0   215 1   96  0   215 1   97  0   215 1   97  0   215 1   98  0   215 1   98  0   215 1   100 0   215 1   100 0   215 1   101 0   215 1   101 0   215 1   102 0   216 1   102 0   216 1   103 
                                           0   216 1   103 0   216 1   103 0   217 1   103 0   217 1   104 0   218 1   104 0   218 1   105 0   219 1   105 0   219 1   105 0   220 1   105 0   220 1   106 0   221 1   106 0   221 1   106 0   222 1   106 0   222 1   106 0   223 1   7   255 83  0   223 
                                           1   114 0   223 1   7   255 98  0   207 1   98  0   238 1   7   255 106 0   63  1   106 0   64  1   106 0   64  1   106 0   65  1   106 0   65  1   105 0   66  1   105 0   66  1   105 0   67  1   105 0   67  1   104 0   68  1   104 0   68  1   103 0   69  
                                           1   103 0   69  1   103 0   70  1   103 0   70  1   102 0   70  1   102 0   70  1   101 0   71  1   101 0   71  1   100 0   71  1   100 0   71  1   98  0   71  1   98  0   71  1   97  0   71  1   97  0   71  1   96  0   71  1   96  0   71  1   95  0   70  
                                           1   95  0   70  1   94  0   70  1   94  0   70  1   93  0   69  1   93  0   69  1   93  0   68  1   93  0   68  1   92  0   67  1   92  0   67  1   91  0   66  1   91  0   66  1   91  0   65  1   91  0   65  1   91  0   64  1   91  0   64  1   91  0   63  
                                           1   91  0   63  1   91  0   62  1   91  0   62  1   91  0   61  1   91  0   61  1   91  0   60  1   91  0   60  1   92  0   59  1   92  0   59  1   93  0   58  1   93  0   58  1   93  0   57  1   93  0   57  1   94  0   57  1   94  0   57  1   95  0   56  
                                           1   95  0   56  1   96  0   56  1   96  0   56  1   97  0   56  1   97  0   56  1   98  0   56  1   98  0   56  1   100 0   56  1   100 0   56  1   101 0   56  1   101 0   56  1   102 0   56  1   102 0   56  1   103 0   57  1   103 0   57  1   104 0   58  
                                           1   104 0   58  1   105 0   59  1   105 0   59  1   105 0   60  1   105 0   60  1   106 0   61  1   106 0   61  1   106 0   62  1   106 0   62  1   106 0   63  1   7   255 83  0   63  1   114 0   63  1   7   255 98  0   48  1   98  0   79  1   7   255 79  
                                           2   63  1   79  2   64  1   79  2   64  1   78  2   65  1   78  2   65  1   78  2   66  1   78  2   66  1   78  2   67  1   78  2   67  1   77  2   68  1   77  2   68  1   76  2   69  1   76  2   69  1   75  2   70  1   75  2   70  1   74  2   70  1   74  
                                           2   70  1   73  2   71  1   73  2   71  1   72  2   71  1   72  2   71  1   71  2   71  1   71  2   71  1   70  2   71  1   70  2   71  1   69  2   71  1   69  2   71  1   68  2   70  1   68  2   70  1   67  2   70  1   67  2   70  1   66  2   69  1   66  
                                           2   69  1   65  2   68  1   65  2   68  1   65  2   67  1   65  2   67  1   64  2   66  1   64  2   66  1   64  2   65  1   64  2   65  1   64  2   64  1   64  2   64  1   63  2   63  1   63  2   63  1   64  2   62  1   64  2   62  1   64  2   61  1   64  
                                           2   61  1   64  2   60  1   64  2   60  1   65  2   59  1   65  2   59  1   65  2   58  1   65  2   58  1   66  2   57  1   66  2   57  1   67  2   57  1   67  2   57  1   68  2   56  1   68  2   56  1   69  2   56  1   69  2   56  1   70  2   56  1   70  
                                           2   56  1   71  2   56  1   71  2   56  1   72  2   56  1   72  2   56  1   73  2   56  1   73  2   56  1   74  2   56  1   74  2   56  1   75  2   57  1   75  2   57  1   76  2   57  1   76  2   57  1   77  2   58  1   77  2   58  1   78  2   59  1   78  
                                           2   59  1   78  2   60  1   78  2   60  1   78  2   61  1   78  2   61  1   79  2   62  1   79  2   62  1   79  2   63  1   7   255 56  2   63  1   86  2   63  1   7   255 71  2   48  1   71  2   79  1   7   255 79  2   223 1   79  2   224 1   79  2   224 
                                           1   78  2   225 1   78  2   225 1   78  2   226 1   78  2   226 1   78  2   227 1   78  2   227 1   77  2   228 1   77  2   228 1   76  2   229 1   76  2   229 1   75  2   229 1   75  2   229 1   74  2   230 1   74  2   230 1   73  2   230 1   73  2   230 
                                           1   72  2   230 1   72  2   230 1   71  2   230 1   71  2   230 1   70  2   230 1   70  2   230 1   69  2   230 1   69  2   230 1   68  2   230 1   68  2   230 1   67  2   229 1   67  2   229 1   66  2   229 1   66  2   229 1   65  2   228 1   65  2   228 
                                           1   65  2   227 1   65  2   227 1   64  2   226 1   64  2   226 1   64  2   225 1   64  2   225 1   64  2   224 1   64  2   224 1   63  2   223 1   63  2   223 1   64  2   222 1   64  2   222 1   64  2   221 1   64  2   221 1   64  2   220 1   64  2   220 
                                           1   65  2   219 1   65  2   219 1   65  2   218 1   65  2   218 1   66  2   217 1   66  2   217 1   67  2   216 1   67  2   216 1   68  2   216 1   68  2   216 1   69  2   215 1   69  2   215 1   70  2   215 1   70  2   215 1   71  2   215 1   71  2   215 
                                           1   72  2   215 1   72  2   215 1   73  2   215 1   73  2   215 1   74  2   216 1   74  2   216 1   75  2   216 1   75  2   216 1   76  2   217 1   76  2   217 1   77  2   218 1   77  2   218 1   78  2   219 1   78  2   219 1   78  2   220 1   78  2   220 
                                           1   78  2   221 1   78  2   221 1   79  2   222 1   79  2   222 1   79  2   223 1   7   255 56  2   223 1   86  2   223 1   7   255 71  2   207 1   71  2   238 1   7   255 174 0   63  1   174 0   64  1   174 0   64  1   173 0   65  1   173 0   65  1   173 
                                           0   66  1   173 0   66  1   172 0   67  1   172 0   67  1   172 0   68  1   172 0   68  1   171 0   69  1   171 0   69  1   170 0   70  1   170 0   70  1   169 0   70  1   169 0   70  1   168 0   71  1   168 0   71  1   167 0   71  1   167 0   71  1   166 
                                           0   71  1   166 0   71  1   165 0   71  1   165 0   71  1   164 0   71  1   164 0   71  1   163 0   70  1   163 0   70  1   162 0   70  1   162 0   70  1   161 0   69  1   161 0   69  1   160 0   68  1   160 0   68  1   159 0   67  1   159 0   67  1   159 
                                           0   66  1   159 0   66  1   159 0   65  1   159 0   65  1   158 0   64  1   158 0   64  1   158 0   63  1   158 0   63  1   158 0   62  1   158 0   62  1   159 0   61  1   159 0   61  1   159 0   60  1   159 0   60  1   159 0   59  1   159 0   59  1   160 
                                           0   58  1   160 0   58  1   161 0   57  1   161 0   57  1   162 0   57  1   162 0   57  1   163 0   56  1   163 0   56  1   164 0   56  1   164 0   56  1   165 0   56  1   165 0   56  1   166 0   56  1   166 0   56  1   167 0   56  1   167 0   56  1   168 
                                           0   56  1   168 0   56  1   169 0   56  1   169 0   56  1   170 0   57  1   170 0   57  1   171 0   57  1   171 0   57  1   172 0   58  1   172 0   58  1   172 0   59  1   172 0   59  1   173 0   60  1   173 0   60  1   173 0   61  1   173 0   61  1   174 
                                           0   62  1   174 0   62  1   174 0   63  1   7   255 151 0   63  1   181 0   63  1   7   255 166 0   48  1   166 0   79  1   7   255 174 0   223 1   174 0   224 1   174 0   224 1   173 0   225 1   173 0   225 1   173 0   226 1   173 0   226 1   172 0   227 
                                           1   172 0   227 1   172 0   228 1   172 0   228 1   171 0   229 1   171 0   229 1   170 0   229 1   170 0   229 1   169 0   230 1   169 0   230 1   168 0   230 1   168 0   230 1   167 0   230 1   167 0   230 1   166 0   230 1   166 0   230 1   165 0   230 
                                           1   165 0   230 1   164 0   230 1   164 0   230 1   163 0   230 1   163 0   230 1   162 0   229 1   162 0   229 1   161 0   229 1   161 0   229 1   160 0   228 1   160 0   228 1   159 0   227 1   159 0   227 1   159 0   226 1   159 0   226 1   159 0   225 
                                           )) "w")
 (_WriteStream FILE (vl-list->string (list 1   159 0   225 1   158 0   224 1   158 0   224 1   158 0   223 1   158 0   223 1   158 0   222 1   158 0   222 1   159 0   221 1   159 0   221 1   159 0   220 1   159 0   220 1   159 0   219 1   159 0   219 1   160 0   218 1   160 0   218 1   161 0   217 
                                           1   161 0   217 1   162 0   216 1   162 0   216 1   163 0   216 1   163 0   216 1   164 0   215 1   164 0   215 1   165 0   215 1   165 0   215 1   166 0   215 1   166 0   215 1   167 0   215 1   167 0   215 1   168 0   215 1   168 0   215 1   169 0   216 
                                           1   169 0   216 1   170 0   216 1   170 0   216 1   171 0   217 1   171 0   217 1   172 0   218 1   172 0   218 1   172 0   219 1   172 0   219 1   173 0   220 1   173 0   220 1   173 0   221 1   173 0   221 1   174 0   222 1   174 0   222 1   174 0   223 
                                           1   7   255 151 0   223 1   181 0   223 1   7   255 166 0   207 1   166 0   238 1   7   255 174 0   143 1   174 0   144 1   174 0   144 1   173 0   145 1   173 0   145 1   173 0   146 1   173 0   146 1   172 0   147 1   172 0   147 1   172 0   148 1   172 
                                           0   148 1   171 0   149 1   171 0   149 1   170 0   149 1   170 0   149 1   169 0   150 1   169 0   150 1   168 0   150 1   168 0   150 1   167 0   151 1   167 0   151 1   166 0   151 1   166 0   151 1   165 0   151 1   165 0   151 1   164 0   150 1   164 
                                           0   150 1   163 0   150 1   163 0   150 1   162 0   149 1   162 0   149 1   161 0   149 1   161 0   149 1   160 0   148 1   160 0   148 1   159 0   147 1   159 0   147 1   159 0   146 1   159 0   146 1   159 0   145 1   159 0   145 1   158 0   144 1   158 
                                           0   144 1   158 0   143 1   158 0   143 1   158 0   142 1   158 0   142 1   159 0   141 1   159 0   141 1   159 0   140 1   159 0   140 1   159 0   139 1   159 0   139 1   160 0   138 1   160 0   138 1   161 0   137 1   161 0   137 1   162 0   137 1   162 
                                           0   137 1   163 0   136 1   163 0   136 1   164 0   136 1   164 0   136 1   165 0   135 1   165 0   135 1   166 0   135 1   166 0   135 1   167 0   135 1   167 0   135 1   168 0   136 1   168 0   136 1   169 0   136 1   169 0   136 1   170 0   137 1   170 
                                           0   137 1   171 0   137 1   171 0   137 1   172 0   138 1   172 0   138 1   172 0   139 1   172 0   139 1   173 0   140 1   173 0   140 1   173 0   141 1   173 0   141 1   174 0   142 1   174 0   142 1   174 0   143 1   7   255 151 0   143 1   181 0   143 
                                           1   7   255 166 0   128 1   166 0   158 1   7   255 132 0   67  1   132 0   77  1   132 0   77  1   141 0   80  1   141 0   80  1   191 0   80  1   191 0   80  1   200 0   77  1   200 0   77  1   200 0   67  1   200 0   67  1   191 0   63  1   191 0   63  
                                           1   141 0   63  1   141 0   63  1   132 0   67  1   7   255 132 0   209 1   132 0   219 1   132 0   219 1   141 0   223 1   141 0   223 1   191 0   223 1   191 0   223 1   200 0   219 1   200 0   219 1   200 0   209 1   200 0   209 1   191 0   206 1   191 
                                           0   206 1   141 0   206 1   141 0   206 1   132 0   209 1   7   255 37  2   209 1   37  2   219 1   37  2   219 1   46  2   223 1   46  2   223 1   96  2   223 1   96  2   223 1   105 2   219 1   105 2   219 1   105 2   209 1   105 2   209 1   96  2   206 
                                           1   96  2   206 1   46  2   206 1   46  2   206 1   37  2   209 1   7   255 37  2   178 1   37  2   189 1   37  2   189 1   46  2   192 1   46  2   192 1   96  2   192 1   96  2   192 1   105 2   189 1   105 2   189 1   105 2   178 1   105 2   178 1   96  
                                           2   175 1   96  2   175 1   46  2   175 1   46  2   175 1   37  2   178 1   7   255 37  2   97  1   37  2   108 1   37  2   108 1   46  2   111 1   46  2   111 1   96  2   111 1   96  2   111 1   105 2   108 1   105 2   108 1   105 2   97  1   105 2   97  
                                           1   96  2   94  1   96  2   94  1   46  2   94  1   46  2   94  1   37  2   97  1   7   255 37  2   67  1   37  2   77  1   37  2   77  1   46  2   80  1   46  2   80  1   96  2   80  1   96  2   80  1   105 2   77  1   105 2   77  1   105 2   67  1   105 
                                           2   67  1   96  2   63  1   96  2   63  1   46  2   63  1   46  2   63  1   37  2   67  1   7   255 98  0   63  1   244 0   63  1   244 0   63  1   244 0   111 1   244 0   111 1   225 2   111 1   225 2   111 1   225 2   175 1   225 2   175 1   244 0   175 
                                           1   244 0   175 1   244 0   223 1   7   255 244 0   223 1   98  0   223 1   7   255 98  0   223 1   98  0   63  1   7   255 98  0   63  1   98  0   63  1   7   255 98  0   63  1   98  0   63  1   7   255 98  0   63  1   98  0   63  1   7   255 42  2   143 
                                           1   42  2   144 1   42  2   144 1   42  2   145 1   42  2   145 1   41  2   146 1   41  2   146 1   41  2   147 1   41  2   147 1   40  2   148 1   40  2   148 1   39  2   149 1   39  2   149 1   38  2   149 1   38  2   149 1   37  2   150 1   37  2   150 
                                           1   36  2   150 1   36  2   150 1   35  2   151 1   35  2   151 1   34  2   151 1   34  2   151 1   33  2   151 1   33  2   151 1   32  2   150 1   32  2   150 1   31  2   150 1   31  2   150 1   30  2   149 1   30  2   149 1   29  2   149 1   29  2   149 
                                           1   29  2   148 1   29  2   148 1   28  2   147 1   28  2   147 1   27  2   146 1   27  2   146 1   27  2   145 1   27  2   145 1   27  2   144 1   27  2   144 1   27  2   143 1   27  2   143 1   27  2   142 1   27  2   142 1   27  2   141 1   27  2   141 
                                           1   27  2   140 1   27  2   140 1   28  2   139 1   28  2   139 1   29  2   138 1   29  2   138 1   29  2   137 1   29  2   137 1   30  2   137 1   30  2   137 1   31  2   136 1   31  2   136 1   32  2   136 1   32  2   136 1   33  2   135 1   33  2   135 
                                           1   34  2   135 1   34  2   135 1   35  2   135 1   35  2   135 1   36  2   136 1   36  2   136 1   37  2   136 1   37  2   136 1   38  2   137 1   38  2   137 1   39  2   137 1   39  2   137 1   40  2   138 1   40  2   138 1   41  2   139 1   41  2   139 
                                           1   41  2   140 1   41  2   140 1   42  2   141 1   42  2   141 1   42  2   142 1   42  2   142 1   42  2   143 1   7   255 19  2   143 1   50  2   143 1   7   255 34  2   128 1   34  2   158 1   7   255 45  2   143 1   45  2   144 1   45  2   144 1   45  
                                           2   146 1   45  2   146 1   44  2   147 1   44  2   147 1   44  2   148 1   44  2   148 1   43  2   149 1   43  2   149 1   42  2   151 1   42  2   151 1   41  2   151 1   41  2   151 1   40  2   152 1   40  2   152 1   38  2   153 1   38  2   153 1   37  
                                           2   153 1   37  2   153 1   36  2   154 1   36  2   154 1   34  2   154 1   34  2   154 1   33  2   154 1   33  2   154 1   32  2   153 1   32  2   153 1   30  2   153 1   30  2   153 1   29  2   152 1   29  2   152 1   28  2   151 1   28  2   151 1   27  
                                           2   151 1   27  2   151 1   26  2   149 1   26  2   149 1   25  2   148 1   25  2   148 1   24  2   147 1   24  2   147 1   24  2   146 1   24  2   146 1   24  2   144 1   24  2   144 1   24  2   143 1   24  2   143 1   24  2   142 1   24  2   142 1   24  
                                           2   140 1   24  2   140 1   24  2   139 1   24  2   139 1   25  2   138 1   25  2   138 1   26  2   137 1   26  2   137 1   27  2   135 1   27  2   135 1   28  2   135 1   28  2   135 1   29  2   134 1   29  2   134 1   30  2   133 1   30  2   133 1   32  
                                           2   133 1   32  2   133 1   33  2   132 1   33  2   132 1   34  2   132 1   34  2   132 1   36  2   132 1   36  2   132 1   37  2   133 1   37  2   133 1   38  2   133 1   38  2   133 1   40  2   134 1   40  2   134 1   41  2   135 1   41  2   135 1   42  
                                           2   135 1   42  2   135 1   43  2   137 1   43  2   137 1   44  2   138 1   44  2   138 1   44  2   139 1   44  2   139 1   45  2   140 1   45  2   140 1   45  2   142 1   45  2   142 1   45  2   143 1   7   255 195 1   63  1   230 5   63  1   230 5   63  
                                           1   230 5   223 1   230 5   223 1   195 1   223 1   195 1   223 1   195 1   63  1   7   255 195 1   63  1   195 1   63  1   7   255 195 1   63  1   195 1   63  1   7   255 195 1   63  1   195 1   63  1   7   255 255 4   97  1   255 4   108 1   255 4   108 
                                           1   9   5   111 1   9   5   111 1   58  5   111 1   58  5   111 1   68  5   108 1   68  5   108 1   68  5   97  1   68  5   97  1   58  5   94  1   58  5   94  1   9   5   94  1   9   5   94  1   255 4   97  1   7   255 255 4   67  1   255 4   77  1   255 
                                           4   77  1   9   5   80  1   9   5   80  1   58  5   80  1   58  5   80  1   68  5   77  1   68  5   77  1   68  5   67  1   68  5   67  1   58  5   63  1   58  5   63  1   9   5   63  1   9   5   63  1   255 4   67  1   7   255 255 4   178 1   255 4   189 
                                           1   255 4   189 1   9   5   192 1   9   5   192 1   58  5   192 1   58  5   192 1   68  5   189 1   68  5   189 1   68  5   178 1   68  5   178 1   58  5   175 1   58  5   175 1   9   5   175 1   9   5   175 1   255 4   178 1   7   255 255 4   209 1   255 
                                           4   219 1   255 4   219 1   9   5   223 1   9   5   223 1   58  5   223 1   58  5   223 1   68  5   219 1   68  5   219 1   68  5   209 1   68  5   209 1   58  5   206 1   58  5   206 1   9   5   206 1   9   5   206 1   255 4   209 1   7   255 41  5   223 
                                           1   41  5   224 1   41  5   224 1   41  5   225 1   41  5   225 1   40  5   226 1   40  5   226 1   40  5   227 1   40  5   227 1   39  5   228 1   39  5   228 1   38  5   229 1   38  5   229 1   37  5   229 1   37  5   229 1   36  5   230 1   36  5   230 
                                           1   35  5   230 1   35  5   230 1   34  5   230 1   34  5   230 1   33  5   230 1   33  5   230 1   32  5   230 1   32  5   230 1   31  5   230 1   31  5   230 1   30  5   230 1   30  5   230 1   29  5   229 1   29  5   229 1   28  5   229 1   28  5   229 
                                           1   27  5   228 1   27  5   228 1   27  5   227 1   27  5   227 1   26  5   226 1   26  5   226 1   26  5   225 1   26  5   225 1   26  5   224 1   26  5   224 1   26  5   223 1   26  5   223 1   26  5   222 1   26  5   222 1   26  5   221 1   26  5   221 
                                           1   26  5   220 1   26  5   220 1   27  5   219 1   27  5   219 1   27  5   218 1   27  5   218 1   28  5   217 1   28  5   217 1   29  5   216 1   29  5   216 1   30  5   216 1   30  5   216 1   31  5   215 1   31  5   215 1   32  5   215 1   32  5   215 
                                           1   33  5   215 1   33  5   215 1   34  5   215 1   34  5   215 1   35  5   215 1   35  5   215 1   36  5   216 1   36  5   216 1   37  5   216 1   37  5   216 1   38  5   217 1   38  5   217 1   39  5   218 1   39  5   218 1   40  5   219 1   40  5   219 
                                           1   40  5   220 1   40  5   220 1   41  5   221 1   41  5   221 1   41  5   222 1   41  5   222 1   41  5   223 1   7   255 18  5   223 1   49  5   223 1   7   255 33  5   207 1   33  5   238 1   7   255 41  5   63  1   41  5   64  1   41  5   64  1   41  
                                           5   65  1   41  5   65  1   40  5   66  1   40  5   66  1   40  5   67  1   40  5   67  1   39  5   68  1   39  5   68  1   38  5   69  1   38  5   69  1   37  5   70  1   37  5   70  1   36  5   70  1   36  5   70  1   35  5   71  1   35  5   71  1   34  
                                           5   71  1   34  5   71  1   33  5   71  1   33  5   71  1   32  5   71  1   32  5   71  1   31  5   71  1   31  5   71  1   30  5   70  1   30  5   70  1   29  5   70  1   29  5   70  1   28  5   69  1   28  5   69  1   27  5   68  1   27  5   68  1   27  
                                           5   67  1   27  5   67  1   26  5   66  1   26  5   66  1   26  5   65  1   26  5   65  1   26  5   64  1   26  5   64  1   26  5   63  1   26  5   63  1   26  5   62  1   26  5   62  1   26  5   61  1   26  5   61  1   26  5   60  1   26  5   60  1   27  
                                           5   59  1   27  5   59  1   27  5   58  1   27  5   58  1   28  5   57  1   28  5   57  1   29  5   57  1   29  5   57  1   30  5   56  1   30  5   56  1   31  5   56  1   31  5   56  1   32  5   56  1   32  5   56  1   33  5   56  1   33  5   56  1   34  
                                           5   56  1   34  5   56  1   35  5   56  1   35  5   56  1   36  5   56  1   36  5   56  1   37  5   57  1   37  5   57  1   38  5   57  1   38  5   57  1   39  5   58  1   39  5   58  1   40  5   59  1   40  5   59  1   40  5   60  1   40  5   60  1   41  
                                           5   61  1   41  5   61  1   41  5   62  1   41  5   62  1   41  5   63  1   7   255 18  5   63  1   49  5   63  1   7   255 33  5   48  1   33  5   79  1   7   255 237 5   63  1   237 5   64  1   237 5   64  1   237 5   65  1   237 5   65  1   237 5   66  
                                           1   237 5   66  1   236 5   67  1   236 5   67  1   235 5   68  1   235 5   68  1   235 5   69  1   235 5   69  1   234 5   70  1   234 5   70  1   233 5   70  1   233 5   70  1   232 5   71  1   232 5   71  1   231 5   71  1   231 5   71  1   230 5   71  
                                           1   230 5   71  1   228 5   71  1   228 5   71  1   227 5   71  1   227 5   71  1   226 5   70  1   226 5   70  1   225 5   70  1   225 5   70  1   225 5   69  1   225 5   69  1   224 5   68  1   224 5   68  1   223 5   67  1   223 5   67  1   223 5   66  
                                           1   223 5   66  1   222 5   65  1   222 5   65  1   222 5   64  1   222 5   64  1   222 5   63  1   222 5   63  1   222 5   62  1   222 5   62  1   222 5   61  1   222 5   61  1   223 5   60  1   223 5   60  1   223 5   59  1   223 5   59  1   224 5   58  
                                           1   224 5   58  1   225 5   57  1   225 5   57  1   226 5   56  1   226 5   56  1   227 5   56  1   227 5   56  1   228 5   56  1   228 5   56  1   230 5   56  1   230 5   56  1   231 5   56  1   231 5   56  1   232 5   56  1   232 5   56  1   233 5   56  
                                           1   233 5   56  1   234 5   57  1   234 5   57  1   235 5   57  1   235 5   57  1   235 5   58  1   235 5   58  1   236 5   59  1   236 5   59  1   237 5   60  1   237 5   60  1   237 5   61  1   237 5   61  1   237 5   62  1   237 5   62  1   237 5   63  
                                           1   7   255 214 5   63  1   245 5   63  1   7   255 230 5   48  1   230 5   79  1   7   255 237 5   223 1   237 5   224 1   237 5   224 1   237 5   225 1   237 5   225 1   237 5   226 1   237 5   226 1   236 5   227 1   236 5   227 1   235 5   228 1   235 
                                           5   228 1   235 5   229 1   235 5   229 1   234 5   229 1   234 5   229 1   233 5   230 1   233 5   230 1   232 5   230 1   232 5   230 1   231 5   230 1   231 5   230 1   230 5   230 1   230 5   230 1   228 5   230 1   228 5   230 1   227 5   230 1   227 
                                           5   230 1   226 5   230 1   226 5   230 1   225 5   229 1   225 5   229 1   224 5   228 1   224 5   228 1   223 5   227 1   223 5   227 1   223 5   226 1   223 5   226 1   222 5   225 1   222 5   225 1   222 5   224 1   222 5   224 1   222 5   223 1   222 
                                           5   223 1   222 5   222 1   222 5   222 1   222 5   221 1   222 5   221 1   223 5   220 1   223 5   220 1   223 5   219 1   223 5   219 1   224 5   218 1   224 5   218 1   225 5   217 1   225 5   217 1   225 5   216 1   225 5   216 1   226 5   216 1   226 
                                           5   216 1   227 5   215 1   227 5   215 1   228 5   215 1   228 5   215 1   230 5   215 1   230 5   215 1   231 5   215 1   231 5   215 1   232 5   215 1   232 5   215 1   233 5   216 1   233 5   216 1   234 5   216 1   234 5   216 1   235 5   217 1   235 
                                           5   217 1   235 5   218 1   235 5   218 1   236 5   219 1   236 5   219 1   237 5   220 1   237 5   220 1   237 5   221 1   237 5   221 1   237 5   222 1   237 5   222 1   237 5   223 1   7   255 214 5   223 1   245 5   223 1   7   255 230 5   207 1   230 
                                           5   238 1   7   255 203 1   63  1   203 1   64  1   203 1   64  1   203 1   65  1   203 1   65  1   202 1   66  1   202 1   66  1   202 1   67  1   202 1   67  1   201 1   68  1   201 1   68  1   200 1   69  1   200 1   69  1   199 1   70  1   199 1   70  
                                           1   198 1   70  1   198 1   70  1   197 1   71  1   197 1   71  1   196 1   71  1   196 1   71  1   195 1   71  1   195 1   71  1   194 1   71  1   194 1   71  1   193 1   71  1   193 1   71  1   192 1   70  1   192 1   70  1   191 1   70  1   191 1   70  
                                           1   190 1   69  1   190 1   69  1   189 1   68  1   189 1   68  1   189 1   67  1   189 1   67  1   188 1   66  1   188 1   66  1   188 1   65  1   188 1   65  1   188 1   64  1   188 1   64  1   188 1   63  1   188 1   63  1   188 1   62  1   188 1   62  
                                           1   188 1   61  1   188 1   61  1   188 1   60  1   188 1   60  1   189 1   59  1   189 1   59  1   189 1   58  1   189 1   58  1   190 1   57  1   190 1   57  1   191 1   57  1   191 1   57  1   192 1   56  1   192 1   56  1   193 1   56  1   193 1   56  
                                           1   194 1   56  1   194 1   56  1   195 1   56  1   195 1   56  1   196 1   56  1   196 1   56  1   197 1   56  1   197 1   56  1   198 1   56  1   198 1   56  1   199 1   57  1   199 1   57  1   200 1   57  1   200 1   57  1   201 1   58  1   201 1   58  
                                           1   202 1   59  1   202 1   59  1   202 1   60  1   202 1   60  1   203 1   61  1   203 1   61  1   203 1   62  1   203 1   62  1   203 1   63  1   7   255 180 1   63  1   211 1   63  1   7   255 195 1   48  1   195 1   79  1   7   255 203 1   223 1   203 
                                           1   224 1   203 1   224 1   203 1   225 1   203 1   225 1   202 1   226 1   202 1   226 1   202 1   227 1   202 1   227 1   201 1   228 1   201 1   228 1   200 1   229 1   200 1   229 1   199 1   229 1   199 1   229 1   198 1   230 1   198 1   230 1   197 
                                           )) "a")
 (_WriteStream FILE (vl-list->string (list 1   230 1   197 1   230 1   196 1   230 1   196 1   230 1   195 1   230 1   195 1   230 1   194 1   230 1   194 1   230 1   193 1   230 1   193 1   230 1   192 1   230 1   192 1   230 1   191 1   229 1   191 1   229 1   190 1   229 1   190 1   229 1   189 
                                           1   228 1   189 1   228 1   189 1   227 1   189 1   227 1   188 1   226 1   188 1   226 1   188 1   225 1   188 1   225 1   188 1   224 1   188 1   224 1   188 1   223 1   188 1   223 1   188 1   222 1   188 1   222 1   188 1   221 1   188 1   221 1   188 
                                           1   220 1   188 1   220 1   189 1   219 1   189 1   219 1   189 1   218 1   189 1   218 1   190 1   217 1   190 1   217 1   191 1   216 1   191 1   216 1   192 1   216 1   192 1   216 1   193 1   215 1   193 1   215 1   194 1   215 1   194 1   215 1   195 
                                           1   215 1   195 1   215 1   196 1   215 1   196 1   215 1   197 1   215 1   197 1   215 1   198 1   216 1   198 1   216 1   199 1   216 1   199 1   216 1   200 1   217 1   200 1   217 1   201 1   218 1   201 1   218 1   202 1   219 1   202 1   219 1   202 
                                           1   220 1   202 1   220 1   203 1   221 1   203 1   221 1   203 1   222 1   203 1   222 1   203 1   223 1   7   255 180 1   223 1   211 1   223 1   7   255 195 1   207 1   195 1   238 1   7   255 42  2   143 1   42  2   144 1   42  2   144 1   42  2   145 
                                           1   42  2   145 1   41  2   146 1   41  2   146 1   41  2   147 1   41  2   147 1   40  2   148 1   40  2   148 1   39  2   149 1   39  2   149 1   38  2   149 1   38  2   149 1   37  2   150 1   37  2   150 1   36  2   150 1   36  2   150 1   35  2   151 
                                           1   35  2   151 1   34  2   151 1   34  2   151 1   33  2   151 1   33  2   151 1   32  2   150 1   32  2   150 1   31  2   150 1   31  2   150 1   30  2   149 1   30  2   149 1   29  2   149 1   29  2   149 1   29  2   148 1   29  2   148 1   28  2   147 
                                           1   28  2   147 1   27  2   146 1   27  2   146 1   27  2   145 1   27  2   145 1   27  2   144 1   27  2   144 1   27  2   143 1   27  2   143 1   27  2   142 1   27  2   142 1   27  2   141 1   27  2   141 1   27  2   140 1   27  2   140 1   28  2   139 
                                           1   28  2   139 1   29  2   138 1   29  2   138 1   29  2   137 1   29  2   137 1   30  2   137 1   30  2   137 1   31  2   136 1   31  2   136 1   32  2   136 1   32  2   136 1   33  2   135 1   33  2   135 1   34  2   135 1   34  2   135 1   35  2   135 
                                           1   35  2   135 1   36  2   136 1   36  2   136 1   37  2   136 1   37  2   136 1   38  2   137 1   38  2   137 1   39  2   137 1   39  2   137 1   40  2   138 1   40  2   138 1   41  2   139 1   41  2   139 1   41  2   140 1   41  2   140 1   42  2   141 
                                           1   42  2   141 1   42  2   142 1   42  2   142 1   42  2   143 1   7   255 19  2   143 1   50  2   143 1   7   255 34  2   128 1   34  2   158 1   0   252 65  117 116 111 67  65  68  32  83  108 105 100 101 13  10  26  0   86  2   73  6   247 2   97  120 
                                           67  1   2   0   52  18  7   255 7   255 121 4   59  1   26  6   59  1   26  6   59  1   26  6   183 1   26  6   183 1   121 4   183 1   121 4   183 1   121 4   59  1   7   255 121 4   59  1   121 4   59  1   7   255 121 4   59  1   121 4   59  1   7   255 
                                           121 4   59  1   121 4   59  1   7   255 163 4   121 1   161 4   124 1   161 4   124 1   158 4   126 1   158 4   126 1   154 4   124 1   154 4   124 1   153 4   121 1   153 4   121 1   154 4   117 1   154 4   117 1   158 4   116 1   158 4   116 1   161 4   
                                           117 1   161 4   117 1   163 4   121 1   7   255 214 5   83  1   214 5   91  1   214 5   91  1   220 5   93  1   220 5   93  1   255 5   93  1   255 5   93  1   6   6   91  1   6   6   91  1   6   6   83  1   6   6   83  1   255 5   81  1   255 5   81  1   
                                           220 5   81  1   220 5   81  1   214 5   83  1   7   255 214 5   61  1   214 5   69  1   214 5   69  1   220 5   71  1   220 5   71  1   255 5   71  1   255 5   71  1   6   6   69  1   6   6   69  1   6   6   61  1   6   6   61  1   255 5   59  1   255 5   
                                           59  1   220 5   59  1   220 5   59  1   214 5   61  1   7   255 214 5   151 1   214 5   159 1   214 5   159 1   220 5   161 1   220 5   161 1   255 5   161 1   255 5   161 1   6   6   159 1   6   6   159 1   6   6   151 1   6   6   151 1   255 5   149 1   
                                           255 5   149 1   220 5   149 1   220 5   149 1   214 5   151 1   7   255 214 5   173 1   214 5   181 1   214 5   181 1   220 5   183 1   220 5   183 1   255 5   183 1   255 5   183 1   6   6   181 1   6   6   181 1   6   6   173 1   6   6   173 1   255 5   
                                           171 1   255 5   171 1   220 5   171 1   220 5   171 1   214 5   173 1   7   255 123 4   59  1   122 4   60  1   122 4   60  1   121 4   60  1   121 4   60  1   120 4   60  1   120 4   60  1   120 4   59  1   120 4   59  1   120 4   58  1   120 4   58  1   
                                           121 4   57  1   121 4   57  1   122 4   58  1   122 4   58  1   123 4   59  1   7   255 118 4   59  1   124 4   59  1   7   255 121 4   56  1   121 4   62  1   7   255 239 5   59  1   239 5   60  1   239 5   60  1   238 5   60  1   238 5   60  1   237 5   
                                           60  1   237 5   60  1   236 5   59  1   236 5   59  1   237 5   58  1   237 5   58  1   238 5   57  1   238 5   57  1   239 5   58  1   239 5   58  1   239 5   59  1   7   255 235 5   59  1   241 5   59  1   7   255 238 5   56  1   238 5   62  1   7   255 
                                           27  6   59  1   27  6   60  1   27  6   60  1   26  6   60  1   26  6   60  1   25  6   60  1   25  6   60  1   24  6   59  1   24  6   59  1   25  6   58  1   25  6   58  1   26  6   57  1   26  6   57  1   27  6   58  1   27  6   58  1   27  6   59  1   
                                           7   255 23  6   59  1   29  6   59  1   7   255 26  6   56  1   26  6   62  1   7   255 27  6   121 1   27  6   122 1   27  6   122 1   26  6   122 1   26  6   122 1   25  6   122 1   25  6   122 1   24  6   121 1   24  6   121 1   25  6   120 1   25  6   
                                           120 1   26  6   119 1   26  6   119 1   27  6   120 1   27  6   120 1   27  6   121 1   7   255 23  6   121 1   29  6   121 1   7   255 26  6   118 1   26  6   124 1   7   255 27  6   183 1   27  6   184 1   27  6   184 1   26  6   184 1   26  6   184 1   
                                           25  6   184 1   25  6   184 1   24  6   183 1   24  6   183 1   25  6   182 1   25  6   182 1   26  6   182 1   26  6   182 1   27  6   182 1   27  6   182 1   27  6   183 1   7   255 23  6   183 1   29  6   183 1   7   255 26  6   180 1   26  6   186 1   
                                           7   255 239 5   183 1   239 5   184 1   239 5   184 1   238 5   184 1   238 5   184 1   237 5   184 1   237 5   184 1   236 5   183 1   236 5   183 1   237 5   182 1   237 5   182 1   238 5   182 1   238 5   182 1   239 5   182 1   239 5   182 1   239 5   
                                           183 1   7   255 235 5   183 1   241 5   183 1   7   255 238 5   180 1   238 5   186 1   7   255 123 4   183 1   122 4   184 1   122 4   184 1   121 4   184 1   121 4   184 1   120 4   184 1   120 4   184 1   120 4   183 1   120 4   183 1   120 4   182 1   
                                           120 4   182 1   121 4   182 1   121 4   182 1   122 4   182 1   122 4   182 1   123 4   183 1   7   255 118 4   183 1   124 4   183 1   7   255 121 4   180 1   121 4   186 1   7   255 159 4   121 1   159 4   122 1   159 4   122 1   158 4   122 1   158 4   
                                           122 1   157 4   122 1   157 4   122 1   156 4   121 1   156 4   121 1   157 4   120 1   157 4   120 1   158 4   119 1   158 4   119 1   159 4   120 1   159 4   120 1   159 4   121 1   7   255 155 4   121 1   161 4   121 1   7   255 158 4   118 1   158 4   
                                           124 1   7   255 55  4   121 1   158 4   121 1   7   255 64  4   121 1   61  4   127 1   61  4   127 1   55  4   129 1   55  4   129 1   50  4   127 1   50  4   127 1   47  4   121 1   47  4   121 1   50  4   115 1   50  4   115 1   55  4   113 1   55  4   
                                           113 1   61  4   115 1   61  4   115 1   64  4   121 1   7   255 133 4   61  1   133 4   69  1   133 4   69  1   140 4   71  1   140 4   71  1   175 4   71  1   175 4   71  1   182 4   69  1   182 4   69  1   182 4   61  1   182 4   61  1   175 4   59  1   
                                           175 4   59  1   140 4   59  1   140 4   59  1   133 4   61  1   7   255 133 4   173 1   133 4   181 1   133 4   181 1   140 4   183 1   140 4   183 1   175 4   183 1   175 4   183 1   182 4   181 1   182 4   181 1   182 4   173 1   182 4   173 1   175 4   
                                           171 1   175 4   171 1   140 4   171 1   140 4   171 1   133 4   173 1   7   255 57  4   121 1   57  4   122 1   57  4   122 1   55  4   122 1   55  4   122 1   54  4   122 1   54  4   122 1   54  4   121 1   54  4   121 1   54  4   120 1   54  4   120 1   
                                           55  4   119 1   55  4   119 1   57  4   120 1   57  4   120 1   57  4   121 1   7   255 53  4   121 1   58  4   121 1   7   255 55  4   118 1   55  4   124 1   7   255 159 4   121 1   159 4   122 1   159 4   122 1   158 4   122 1   158 4   122 1   157 4   
                                           122 1   157 4   122 1   156 4   121 1   156 4   121 1   157 4   120 1   157 4   120 1   158 4   119 1   158 4   119 1   159 4   120 1   159 4   120 1   159 4   121 1   7   255 155 4   121 1   161 4   121 1   7   255 158 4   118 1   158 4   124 1   7   255 
                                           159 4   183 1   159 4   184 1   159 4   184 1   158 4   184 1   158 4   184 1   157 4   184 1   157 4   184 1   156 4   183 1   156 4   183 1   157 4   182 1   157 4   182 1   158 4   182 1   158 4   182 1   159 4   182 1   159 4   182 1   159 4   183 1   
                                           7   255 155 4   183 1   161 4   183 1   7   255 158 4   180 1   158 4   186 1   7   255 159 4   59  1   159 4   60  1   159 4   60  1   158 4   60  1   158 4   60  1   157 4   60  1   157 4   60  1   156 4   59  1   156 4   59  1   157 4   58  1   157 4   
                                           58  1   158 4   57  1   158 4   57  1   159 4   58  1   159 4   58  1   159 4   59  1   7   255 155 4   59  1   161 4   59  1   7   255 158 4   56  1   158 4   62  1   7   255 151 2   59  1   55  4   59  1   55  4   59  1   55  4   183 1   55  4   183 1   
                                           151 2   183 1   151 2   183 1   151 2   59  1   7   255 151 2   59  1   151 2   59  1   7   255 151 2   59  1   151 2   59  1   7   255 151 2   59  1   151 2   59  1   7   255 193 2   121 1   191 2   124 1   191 2   124 1   188 2   126 1   188 2   126 1   
                                           184 2   124 1   184 2   124 1   183 2   121 1   183 2   121 1   184 2   117 1   184 2   117 1   188 2   116 1   188 2   116 1   191 2   117 1   191 2   117 1   193 2   121 1   7   255 243 3   83  1   243 3   91  1   243 3   91  1   250 3   93  1   250 3   
                                           93  1   29  4   93  1   29  4   93  1   36  4   91  1   36  4   91  1   36  4   83  1   36  4   83  1   29  4   81  1   29  4   81  1   250 3   81  1   250 3   81  1   243 3   83  1   7   255 243 3   61  1   243 3   69  1   243 3   69  1   250 3   71  1   
                                           250 3   71  1   29  4   71  1   29  4   71  1   36  4   69  1   36  4   69  1   36  4   61  1   36  4   61  1   29  4   59  1   29  4   59  1   250 3   59  1   250 3   59  1   243 3   61  1   7   255 243 3   151 1   243 3   159 1   243 3   159 1   250 3   
                                           161 1   250 3   161 1   29  4   161 1   29  4   161 1   36  4   159 1   36  4   159 1   36  4   151 1   36  4   151 1   29  4   149 1   29  4   149 1   250 3   149 1   250 3   149 1   243 3   151 1   7   255 243 3   173 1   243 3   181 1   243 3   181 1   
                                           250 3   183 1   250 3   183 1   29  4   183 1   29  4   183 1   36  4   181 1   36  4   181 1   36  4   173 1   36  4   173 1   29  4   171 1   29  4   171 1   250 3   171 1   250 3   171 1   243 3   173 1   7   255 152 2   59  1   152 2   60  1   152 2   
                                           60  1   151 2   60  1   151 2   60  1   150 2   60  1   150 2   60  1   150 2   59  1   150 2   59  1   150 2   58  1   150 2   58  1   151 2   57  1   151 2   57  1   152 2   58  1   152 2   58  1   152 2   59  1   7   255 148 2   59  1   154 2   59  1   
                                           7   255 151 2   56  1   151 2   62  1   7   255 13  4   59  1   13  4   60  1   13  4   60  1   12  4   60  1   12  4   60  1   11  4   60  1   11  4   60  1   10  4   59  1   10  4   59  1   11  4   58  1   11  4   58  1   12  4   57  1   12  4   57  1   
                                           13  4   58  1   13  4   58  1   13  4   59  1   7   255 9   4   59  1   15  4   59  1   7   255 12  4   56  1   12  4   62  1   7   255 57  4   59  1   57  4   60  1   57  4   60  1   55  4   60  1   55  4   60  1   54  4   60  1   54  4   60  1   54  4   
                                           59  1   54  4   59  1   54  4   58  1   54  4   58  1   55  4   57  1   55  4   57  1   57  4   58  1   57  4   58  1   57  4   59  1   7   255 53  4   59  1   58  4   59  1   7   255 55  4   56  1   55  4   62  1   7   255 57  4   121 1   57  4   122 1   
                                           57  4   122 1   55  4   122 1   55  4   122 1   54  4   122 1   54  4   122 1   54  4   121 1   54  4   121 1   54  4   120 1   54  4   120 1   55  4   119 1   55  4   119 1   57  4   120 1   57  4   120 1   57  4   121 1   7   255 53  4   121 1   58  4   
                                           121 1   7   255 55  4   118 1   55  4   124 1   7   255 57  4   183 1   57  4   184 1   57  4   184 1   55  4   184 1   55  4   184 1   54  4   184 1   54  4   184 1   54  4   183 1   54  4   183 1   54  4   182 1   54  4   182 1   55  4   182 1   55  4   
                                           182 1   57  4   182 1   57  4   182 1   57  4   183 1   7   255 53  4   183 1   58  4   183 1   7   255 55  4   180 1   55  4   186 1   7   255 13  4   183 1   13  4   184 1   13  4   184 1   12  4   184 1   12  4   184 1   11  4   184 1   11  4   184 1   
                                           10  4   183 1   10  4   183 1   11  4   182 1   11  4   182 1   12  4   182 1   12  4   182 1   13  4   182 1   13  4   182 1   13  4   183 1   7   255 9   4   183 1   15  4   183 1   7   255 12  4   180 1   12  4   186 1   7   255 152 2   183 1   152 2   
                                           184 1   152 2   184 1   151 2   184 1   151 2   184 1   150 2   184 1   150 2   184 1   150 2   183 1   150 2   183 1   150 2   182 1   150 2   182 1   151 2   182 1   151 2   182 1   152 2   182 1   152 2   182 1   152 2   183 1   7   255 148 2   183 1   
                                           154 2   183 1   7   255 151 2   180 1   151 2   186 1   7   255 189 2   121 1   189 2   122 1   189 2   122 1   188 2   122 1   188 2   122 1   186 2   122 1   186 2   122 1   186 2   121 1   186 2   121 1   186 2   120 1   186 2   120 1   188 2   119 1   
                                           188 2   119 1   189 2   120 1   189 2   120 1   189 2   121 1   7   255 185 2   121 1   190 2   121 1   7   255 188 2   118 1   188 2   124 1   7   255 85  2   121 1   188 2   121 1   7   255 94  2   121 1   91  2   127 1   91  2   127 1   85  2   129 1   
                                           85  2   129 1   79  2   127 1   79  2   127 1   77  2   121 1   77  2   121 1   79  2   115 1   79  2   115 1   85  2   113 1   85  2   113 1   91  2   115 1   91  2   115 1   94  2   121 1   7   255 163 2   61  1   163 2   69  1   163 2   69  1   170 2   
                                           71  1   170 2   71  1   205 2   71  1   205 2   71  1   212 2   69  1   212 2   69  1   212 2   61  1   212 2   61  1   205 2   59  1   205 2   59  1   170 2   59  1   170 2   59  1   163 2   61  1   7   255 163 2   173 1   163 2   181 1   163 2   181 1   
                                           170 2   183 1   170 2   183 1   205 2   183 1   205 2   183 1   212 2   181 1   212 2   181 1   212 2   173 1   212 2   173 1   205 2   171 1   205 2   171 1   170 2   171 1   170 2   171 1   163 2   173 1   7   255 87  2   121 1   86  2   122 1   86  2   
                                           122 1   85  2   122 1   85  2   122 1   84  2   122 1   84  2   122 1   84  2   121 1   84  2   121 1   84  2   120 1   84  2   120 1   85  2   119 1   85  2   119 1   86  2   120 1   86  2   120 1   87  2   121 1   7   255 82  2   121 1   88  2   121 1   
                                           7   255 85  2   118 1   85  2   124 1   7   255 189 2   121 1   189 2   122 1   189 2   122 1   188 2   122 1   188 2   122 1   186 2   122 1   186 2   122 1   186 2   121 1   186 2   121 1   186 2   120 1   186 2   120 1   188 2   119 1   188 2   119 1   
                                           189 2   120 1   189 2   120 1   189 2   121 1   7   255 185 2   121 1   190 2   121 1   7   255 188 2   118 1   188 2   124 1   7   255 189 2   183 1   189 2   184 1   189 2   184 1   188 2   184 1   188 2   184 1   186 2   184 1   186 2   184 1   186 2   
                                           183 1   186 2   183 1   186 2   182 1   186 2   182 1   188 2   182 1   188 2   182 1   189 2   182 1   189 2   182 1   189 2   183 1   7   255 185 2   183 1   190 2   183 1   7   255 188 2   180 1   188 2   186 1   7   255 189 2   59  1   189 2   60  1   
                                           189 2   60  1   188 2   60  1   188 2   60  1   186 2   60  1   186 2   60  1   186 2   59  1   186 2   59  1   186 2   58  1   186 2   58  1   188 2   57  1   188 2   57  1   189 2   58  1   189 2   58  1   189 2   59  1   7   255 185 2   59  1   190 2   
                                           59  1   7   255 188 2   56  1   188 2   62  1   7   255 181 0   59  1   85  2   59  1   85  2   59  1   85  2   183 1   85  2   183 1   181 0   183 1   181 0   183 1   181 0   59  1   7   255 181 0   59  1   181 0   59  1   7   255 181 0   59  1   181 0   
                                           59  1   7   255 181 0   59  1   181 0   59  1   7   255 222 0   121 1   221 0   124 1   221 0   124 1   217 0   126 1   217 0   126 1   214 0   124 1   214 0   124 1   212 0   121 1   212 0   121 1   214 0   117 1   214 0   117 1   217 0   116 1   217 0   
                                           )) "a")
 (_WriteStream FILE (vl-list->string (list 116 1   221 0   117 1   221 0   117 1   222 0   121 1   7   255 17  2   83  1   17  2   91  1   17  2   91  1   24  2   93  1   24  2   93  1   59  2   93  1   59  2   93  1   66  2   91  1   66  2   91  1   66  2   83  1   66  2   83  1   59  2   81  1   
                                           59  2   81  1   24  2   81  1   24  2   81  1   17  2   83  1   7   255 17  2   61  1   17  2   69  1   17  2   69  1   24  2   71  1   24  2   71  1   59  2   71  1   59  2   71  1   66  2   69  1   66  2   69  1   66  2   61  1   66  2   61  1   59  2   
                                           59  1   59  2   59  1   24  2   59  1   24  2   59  1   17  2   61  1   7   255 17  2   151 1   17  2   159 1   17  2   159 1   24  2   161 1   24  2   161 1   59  2   161 1   59  2   161 1   66  2   159 1   66  2   159 1   66  2   151 1   66  2   151 1   
                                           59  2   149 1   59  2   149 1   24  2   149 1   24  2   149 1   17  2   151 1   7   255 17  2   173 1   17  2   181 1   17  2   181 1   24  2   183 1   24  2   183 1   59  2   183 1   59  2   183 1   66  2   181 1   66  2   181 1   66  2   173 1   66  2   
                                           173 1   59  2   171 1   59  2   171 1   24  2   171 1   24  2   171 1   17  2   173 1   7   255 182 0   59  1   182 0   60  1   182 0   60  1   181 0   60  1   181 0   60  1   180 0   60  1   180 0   60  1   179 0   59  1   179 0   59  1   180 0   58  1   
                                           180 0   58  1   181 0   57  1   181 0   57  1   182 0   58  1   182 0   58  1   182 0   59  1   7   255 178 0   59  1   184 0   59  1   7   255 181 0   56  1   181 0   62  1   7   255 43  2   59  1   42  2   60  1   42  2   60  1   41  2   60  1   41  2   
                                           60  1   40  2   60  1   40  2   60  1   40  2   59  1   40  2   59  1   40  2   58  1   40  2   58  1   41  2   57  1   41  2   57  1   42  2   58  1   42  2   58  1   43  2   59  1   7   255 38  2   59  1   44  2   59  1   7   255 41  2   56  1   41  2   
                                           62  1   7   255 87  2   59  1   86  2   60  1   86  2   60  1   85  2   60  1   85  2   60  1   84  2   60  1   84  2   60  1   84  2   59  1   84  2   59  1   84  2   58  1   84  2   58  1   85  2   57  1   85  2   57  1   86  2   58  1   86  2   58  1   
                                           87  2   59  1   7   255 82  2   59  1   88  2   59  1   7   255 85  2   56  1   85  2   62  1   7   255 87  2   121 1   86  2   122 1   86  2   122 1   85  2   122 1   85  2   122 1   84  2   122 1   84  2   122 1   84  2   121 1   84  2   121 1   84  2   
                                           120 1   84  2   120 1   85  2   119 1   85  2   119 1   86  2   120 1   86  2   120 1   87  2   121 1   7   255 82  2   121 1   88  2   121 1   7   255 85  2   118 1   85  2   124 1   7   255 87  2   183 1   86  2   184 1   86  2   184 1   85  2   184 1   
                                           85  2   184 1   84  2   184 1   84  2   184 1   84  2   183 1   84  2   183 1   84  2   182 1   84  2   182 1   85  2   182 1   85  2   182 1   86  2   182 1   86  2   182 1   87  2   183 1   7   255 82  2   183 1   88  2   183 1   7   255 85  2   180 1   
                                           85  2   186 1   7   255 43  2   183 1   42  2   184 1   42  2   184 1   41  2   184 1   41  2   184 1   40  2   184 1   40  2   184 1   40  2   183 1   40  2   183 1   40  2   182 1   40  2   182 1   41  2   182 1   41  2   182 1   42  2   182 1   42  2   
                                           182 1   43  2   183 1   7   255 38  2   183 1   44  2   183 1   7   255 41  2   180 1   41  2   186 1   7   255 182 0   183 1   182 0   184 1   182 0   184 1   181 0   184 1   181 0   184 1   180 0   184 1   180 0   184 1   179 0   183 1   179 0   183 1   
                                           180 0   182 1   180 0   182 1   181 0   182 1   181 0   182 1   182 0   182 1   182 0   182 1   182 0   183 1   7   255 178 0   183 1   184 0   183 1   7   255 181 0   180 1   181 0   186 1   7   255 219 0   121 1   218 0   122 1   218 0   122 1   217 0   
                                           122 1   217 0   122 1   216 0   122 1   216 0   122 1   216 0   121 1   216 0   121 1   216 0   120 1   216 0   120 1   217 0   119 1   217 0   119 1   218 0   120 1   218 0   120 1   219 0   121 1   7   255 214 0   121 1   220 0   121 1   7   255 217 0   
                                           118 1   217 0   124 1   7   255 30  0   63  1   125 0   63  1   125 0   63  1   125 0   97  1   125 0   97  1   225 0   97  1   225 0   97  1   225 0   145 1   225 0   145 1   125 0   145 1   125 0   145 1   125 0   179 1   125 0   179 1   30  0   179 1   
                                           30  0   179 1   30  0   63  1   7   255 30  0   63  1   30  0   63  1   7   255 30  0   63  1   30  0   63  1   7   255 30  0   63  1   30  0   63  1   7   255 229 0   133 1   222 0   137 1   222 0   137 1   213 0   137 1   213 0   137 1   205 0   133 1   
                                           205 0   133 1   201 0   125 1   201 0   125 1   201 0   117 1   201 0   117 1   205 0   109 1   205 0   109 1   213 0   105 1   213 0   105 1   222 0   105 1   222 0   105 1   229 0   109 1   7   255 229 0   109 1   229 0   133 1   7   255 200 0   87  1   
                                           200 0   94  1   200 0   94  1   207 0   97  1   207 0   97  1   242 0   97  1   242 0   97  1   249 0   94  1   249 0   94  1   249 0   87  1   249 0   87  1   242 0   84  1   242 0   84  1   207 0   84  1   207 0   84  1   200 0   87  1   7   255 200 0   
                                           65  1   200 0   72  1   200 0   72  1   207 0   75  1   207 0   75  1   242 0   75  1   242 0   75  1   249 0   72  1   249 0   72  1   249 0   65  1   249 0   65  1   242 0   63  1   242 0   63  1   207 0   63  1   207 0   63  1   200 0   65  1   7   255 
                                           200 0   148 1   200 0   155 1   200 0   155 1   207 0   157 1   207 0   157 1   242 0   157 1   242 0   157 1   249 0   155 1   249 0   155 1   249 0   148 1   249 0   148 1   242 0   145 1   242 0   145 1   207 0   145 1   207 0   145 1   200 0   148 1   
                                           7   255 200 0   169 1   200 0   177 1   200 0   177 1   207 0   179 1   207 0   179 1   242 0   179 1   242 0   179 1   249 0   177 1   249 0   177 1   249 0   169 1   249 0   169 1   242 0   167 1   242 0   167 1   207 0   167 1   207 0   167 1   200 0   
                                           169 1   7   255 32  0   63  1   31  0   64  1   31  0   64  1   30  0   64  1   30  0   64  1   29  0   64  1   29  0   64  1   29  0   63  1   29  0   63  1   29  0   61  1   29  0   61  1   30  0   61  1   30  0   61  1   31  0   61  1   31  0   61  1   
                                           32  0   63  1   7   255 27  0   63  1   33  0   63  1   7   255 30  0   60  1   30  0   65  1   7   255 65  0   63  1   65  0   64  1   65  0   64  1   64  0   64  1   64  0   64  1   63  0   64  1   63  0   64  1   62  0   63  1   62  0   63  1   63  0   
                                           61  1   63  0   61  1   64  0   61  1   64  0   61  1   65  0   61  1   65  0   61  1   65  0   63  1   7   255 61  0   63  1   67  0   63  1   7   255 64  0   60  1   64  0   65  1   7   255 226 0   63  1   226 0   64  1   226 0   64  1   225 0   64  1   
                                           225 0   64  1   224 0   64  1   224 0   64  1   223 0   63  1   223 0   63  1   224 0   61  1   224 0   61  1   225 0   61  1   225 0   61  1   226 0   61  1   226 0   61  1   226 0   63  1   7   255 222 0   63  1   228 0   63  1   7   255 225 0   60  1   
                                           225 0   65  1   7   255 226 0   179 1   226 0   180 1   226 0   180 1   225 0   181 1   225 0   181 1   224 0   180 1   224 0   180 1   223 0   179 1   223 0   179 1   224 0   178 1   224 0   178 1   225 0   178 1   225 0   178 1   226 0   178 1   226 0   
                                           178 1   226 0   179 1   7   255 222 0   179 1   228 0   179 1   7   255 225 0   176 1   225 0   182 1   7   255 65  0   179 1   65  0   180 1   65  0   180 1   64  0   181 1   64  0   181 1   63  0   180 1   63  0   180 1   62  0   179 1   62  0   179 1   
                                           63  0   178 1   63  0   178 1   64  0   178 1   64  0   178 1   65  0   178 1   65  0   178 1   65  0   179 1   7   255 61  0   179 1   67  0   179 1   7   255 64  0   176 1   64  0   182 1   7   255 32  0   179 1   31  0   180 1   31  0   180 1   30  0   
                                           181 1   30  0   181 1   29  0   180 1   29  0   180 1   29  0   179 1   29  0   179 1   29  0   178 1   29  0   178 1   30  0   178 1   30  0   178 1   31  0   178 1   31  0   178 1   32  0   179 1   7   255 27  0   179 1   33  0   179 1   7   255 30  0   
                                           176 1   30  0   182 1   7   255 219 0   121 1   218 0   122 1   218 0   122 1   217 0   122 1   217 0   122 1   216 0   122 1   216 0   122 1   216 0   121 1   216 0   121 1   216 0   120 1   216 0   120 1   217 0   119 1   217 0   119 1   218 0   120 1   
                                           218 0   120 1   219 0   121 1   7   255 214 0   121 1   220 0   121 1   7   255 217 0   118 1   217 0   124 1   7   255 65  0   121 1   65  0   122 1   65  0   122 1   64  0   122 1   64  0   122 1   63  0   122 1   63  0   122 1   62  0   121 1   62  0   
                                           121 1   63  0   120 1   63  0   120 1   64  0   119 1   64  0   119 1   65  0   120 1   65  0   120 1   65  0   121 1   7   255 61  0   121 1   67  0   121 1   7   255 64  0   118 1   64  0   124 1   7   255 39  0   65  1   39  0   72  1   39  0   72  1   
                                           46  0   75  1   46  0   75  1   81  0   75  1   81  0   75  1   88  0   72  1   88  0   72  1   88  0   65  1   88  0   65  1   81  0   63  1   81  0   63  1   46  0   63  1   46  0   63  1   39  0   65  1   7   255 39  0   169 1   39  0   177 1   39  0   
                                           177 1   46  0   179 1   46  0   179 1   81  0   179 1   81  0   179 1   88  0   177 1   88  0   177 1   88  0   169 1   88  0   169 1   81  0   167 1   81  0   167 1   46  0   167 1   46  0   167 1   39  0   169 1   0   252 65  117 116 111 67  65  68  32  
                                           83  108 105 100 101 13  10  26  0   86  2   73  6   247 2   97  120 67  1   2   0   52  18  7   255 7   255 175 4   69  1   45  6   69  1   45  6   69  1   45  6   184 1   45  6   184 1   175 4   184 1   175 4   184 1   175 4   69  1   7   255 175 4   69  
                                           1   175 4   69  1   7   255 175 4   69  1   175 4   69  1   7   255 175 4   69  1   175 4   69  1   7   255 181 5   93  1   181 5   101 1   181 5   101 1   188 5   103 1   188 5   103 1   224 5   103 1   224 5   103 1   231 5   101 1   231 5   101 1   231 
                                           5   93  1   231 5   93  1   224 5   91  1   224 5   91  1   188 5   91  1   188 5   91  1   181 5   93  1   7   255 181 5   71  1   181 5   79  1   181 5   79  1   188 5   81  1   188 5   81  1   224 5   81  1   224 5   81  1   231 5   79  1   231 5   79  
                                           1   231 5   71  1   231 5   71  1   224 5   69  1   224 5   69  1   188 5   69  1   188 5   69  1   181 5   71  1   7   255 181 5   152 1   181 5   159 1   181 5   159 1   188 5   162 1   188 5   162 1   224 5   162 1   224 5   162 1   231 5   159 1   231 
                                           5   159 1   231 5   152 1   231 5   152 1   224 5   149 1   224 5   149 1   188 5   149 1   188 5   149 1   181 5   152 1   7   255 181 5   174 1   181 5   182 1   181 5   182 1   188 5   184 1   188 5   184 1   224 5   184 1   224 5   184 1   231 5   182 
                                           1   231 5   182 1   231 5   174 1   231 5   174 1   224 5   172 1   224 5   172 1   188 5   172 1   188 5   172 1   181 5   174 1   7   255 237 5   93  1   237 5   101 1   237 5   101 1   244 5   103 1   244 5   103 1   24  6   103 1   24  6   103 1   31  
                                           6   101 1   31  6   101 1   31  6   93  1   31  6   93  1   24  6   91  1   24  6   91  1   244 5   91  1   244 5   91  1   237 5   93  1   7   255 237 5   71  1   237 5   79  1   237 5   79  1   244 5   81  1   244 5   81  1   24  6   81  1   24  6   81  
                                           1   31  6   79  1   31  6   79  1   31  6   71  1   31  6   71  1   24  6   69  1   24  6   69  1   244 5   69  1   244 5   69  1   237 5   71  1   7   255 237 5   152 1   237 5   159 1   237 5   159 1   244 5   162 1   244 5   162 1   24  6   162 1   24  
                                           6   162 1   31  6   159 1   31  6   159 1   31  6   152 1   31  6   152 1   24  6   149 1   24  6   149 1   244 5   149 1   244 5   149 1   237 5   152 1   7   255 237 5   174 1   237 5   182 1   237 5   182 1   244 5   184 1   244 5   184 1   24  6   184 
                                           1   24  6   184 1   31  6   182 1   31  6   182 1   31  6   174 1   31  6   174 1   24  6   172 1   24  6   172 1   244 5   172 1   244 5   172 1   237 5   174 1   7   255 179 4   69  1   179 4   71  1   179 4   71  1   177 4   73  1   177 4   73  1   175 
                                           4   73  1   175 4   73  1   173 4   73  1   173 4   73  1   171 4   71  1   171 4   71  1   171 4   69  1   171 4   69  1   171 4   67  1   171 4   67  1   173 4   65  1   173 4   65  1   175 4   64  1   175 4   64  1   177 4   65  1   177 4   65  1   179 
                                           4   67  1   179 4   67  1   179 4   69  1   7   255 166 4   69  1   184 4   69  1   7   255 175 4   60  1   175 4   78  1   7   255 179 4   184 1   179 4   186 1   179 4   186 1   177 4   188 1   177 4   188 1   175 4   188 1   175 4   188 1   173 4   188 
                                           1   173 4   188 1   171 4   186 1   171 4   186 1   171 4   184 1   171 4   184 1   171 4   182 1   171 4   182 1   173 4   180 1   173 4   180 1   175 4   180 1   175 4   180 1   177 4   180 1   177 4   180 1   179 4   182 1   179 4   182 1   179 4   184 
                                           1   7   255 166 4   184 1   184 4   184 1   7   255 175 4   175 1   175 4   193 1   7   255 206 4   126 1   205 4   129 1   205 4   129 1   204 4   130 1   204 4   130 1   202 4   131 1   202 4   131 1   199 4   130 1   199 4   130 1   198 4   129 1   198 
                                           4   129 1   197 4   126 1   197 4   126 1   198 4   124 1   198 4   124 1   199 4   123 1   199 4   123 1   202 4   122 1   202 4   122 1   204 4   123 1   204 4   123 1   205 4   124 1   205 4   124 1   206 4   126 1   7   255 193 4   126 1   210 4   126 
                                           1   7   255 202 4   118 1   202 4   135 1   7   255 49  6   184 1   48  6   186 1   48  6   186 1   47  6   188 1   47  6   188 1   45  6   188 1   45  6   188 1   42  6   188 1   42  6   188 1   41  6   186 1   41  6   186 1   40  6   184 1   40  6   184 
                                           1   41  6   182 1   41  6   182 1   42  6   180 1   42  6   180 1   45  6   180 1   45  6   180 1   47  6   180 1   47  6   180 1   48  6   182 1   48  6   182 1   49  6   184 1   7   255 36  6   184 1   53  6   184 1   7   255 45  6   175 1   45  6   193 
                                           1   7   255 49  6   69  1   48  6   71  1   48  6   71  1   47  6   73  1   47  6   73  1   45  6   73  1   45  6   73  1   42  6   73  1   42  6   73  1   41  6   71  1   41  6   71  1   40  6   69  1   40  6   69  1   41  6   67  1   41  6   67  1   42  
                                           6   65  1   42  6   65  1   45  6   64  1   45  6   64  1   47  6   65  1   47  6   65  1   48  6   67  1   48  6   67  1   49  6   69  1   7   255 36  6   69  1   53  6   69  1   7   255 45  6   60  1   45  6   78  1   7   255 238 5   184 1   238 5   186 
                                           1   238 5   186 1   236 5   188 1   236 5   188 1   234 5   188 1   234 5   188 1   232 5   188 1   232 5   188 1   230 5   186 1   230 5   186 1   230 5   184 1   230 5   184 1   230 5   182 1   230 5   182 1   232 5   180 1   232 5   180 1   234 5   180 
                                           1   234 5   180 1   236 5   180 1   236 5   180 1   238 5   182 1   238 5   182 1   238 5   184 1   7   255 225 5   184 1   243 5   184 1   7   255 234 5   175 1   234 5   193 1   7   255 238 5   69  1   238 5   71  1   238 5   71  1   236 5   73  1   236 
                                           5   73  1   234 5   73  1   234 5   73  1   232 5   73  1   232 5   73  1   230 5   71  1   230 5   71  1   230 5   69  1   230 5   69  1   230 5   67  1   230 5   67  1   232 5   65  1   232 5   65  1   234 5   64  1   234 5   64  1   236 5   65  1   236 
                                           5   65  1   238 5   67  1   238 5   67  1   238 5   69  1   7   255 225 5   69  1   243 5   69  1   7   255 234 5   60  1   234 5   78  1   7   255 108 4   126 1   202 4   126 1   7   255 177 4   93  1   177 4   101 1   177 4   101 1   184 4   103 1   184 
                                           4   103 1   219 4   103 1   219 4   103 1   226 4   101 1   226 4   101 1   226 4   93  1   226 4   93  1   219 4   91  1   219 4   91  1   184 4   91  1   184 4   91  1   177 4   93  1   7   255 177 4   71  1   177 4   79  1   177 4   79  1   184 4   81  
                                           1   184 4   81  1   219 4   81  1   219 4   81  1   226 4   79  1   226 4   79  1   226 4   71  1   226 4   71  1   219 4   69  1   219 4   69  1   184 4   69  1   184 4   69  1   177 4   71  1   7   255 177 4   152 1   177 4   159 1   177 4   159 1   184 
                                           4   162 1   184 4   162 1   219 4   162 1   219 4   162 1   226 4   159 1   226 4   159 1   226 4   152 1   226 4   152 1   219 4   149 1   219 4   149 1   184 4   149 1   184 4   149 1   177 4   152 1   7   255 177 4   174 1   177 4   182 1   177 4   182 
                                           1   184 4   184 1   184 4   184 1   219 4   184 1   219 4   184 1   226 4   182 1   226 4   182 1   226 4   174 1   226 4   174 1   219 4   172 1   219 4   172 1   184 4   172 1   184 4   172 1   177 4   174 1   7   255 113 4   126 1   113 4   128 1   113 
                                           4   128 1   112 4   129 1   112 4   129 1   112 4   130 1   112 4   130 1   111 4   130 1   111 4   130 1   110 4   131 1   110 4   131 1   108 4   131 1   108 4   131 1   107 4   131 1   107 4   131 1   106 4   130 1   106 4   130 1   105 4   130 1   105 
                                           4   130 1   105 4   129 1   105 4   129 1   104 4   128 1   104 4   128 1   104 4   126 1   104 4   126 1   104 4   125 1   104 4   125 1   105 4   124 1   105 4   124 1   105 4   123 1   105 4   123 1   106 4   123 1   106 4   123 1   107 4   122 1   107 
                                           )) "a")
 (_WriteStream FILE (vl-list->string (list 4   122 1   108 4   122 1   108 4   122 1   110 4   122 1   110 4   122 1   111 4   123 1   111 4   123 1   112 4   123 1   112 4   123 1   112 4   124 1   112 4   124 1   113 4   125 1   113 4   125 1   113 4   126 1   7   255 100 4   126 1   117 4   126 
                                           1   7   255 108 4   118 1   108 4   135 1   7   255 206 4   184 1   206 4   185 1   206 4   185 1   205 4   186 1   205 4   186 1   205 4   187 1   205 4   187 1   204 4   188 1   204 4   188 1   203 4   188 1   203 4   188 1   202 4   188 1   202 4   188 
                                           1   200 4   188 1   200 4   188 1   199 4   188 1   199 4   188 1   198 4   187 1   198 4   187 1   198 4   186 1   198 4   186 1   197 4   185 1   197 4   185 1   197 4   184 1   197 4   184 1   197 4   183 1   197 4   183 1   198 4   182 1   198 4   182 
                                           1   198 4   181 1   198 4   181 1   199 4   180 1   199 4   180 1   200 4   180 1   200 4   180 1   202 4   180 1   202 4   180 1   203 4   180 1   203 4   180 1   204 4   180 1   204 4   180 1   205 4   181 1   205 4   181 1   205 4   182 1   205 4   182 
                                           1   206 4   183 1   206 4   183 1   206 4   184 1   7   255 193 4   184 1   210 4   184 1   7   255 202 4   175 1   202 4   193 1   7   255 206 4   69  1   206 4   70  1   206 4   70  1   205 4   71  1   205 4   71  1   205 4   72  1   205 4   72  1   204 
                                           4   73  1   204 4   73  1   203 4   73  1   203 4   73  1   202 4   73  1   202 4   73  1   200 4   73  1   200 4   73  1   199 4   73  1   199 4   73  1   198 4   72  1   198 4   72  1   198 4   71  1   198 4   71  1   197 4   70  1   197 4   70  1   197 
                                           4   69  1   197 4   69  1   197 4   68  1   197 4   68  1   198 4   67  1   198 4   67  1   198 4   66  1   198 4   66  1   199 4   65  1   199 4   65  1   200 4   64  1   200 4   64  1   202 4   64  1   202 4   64  1   203 4   64  1   203 4   64  1   204 
                                           4   65  1   204 4   65  1   205 4   66  1   205 4   66  1   205 4   67  1   205 4   67  1   206 4   68  1   206 4   68  1   206 4   69  1   7   255 193 4   69  1   210 4   69  1   7   255 202 4   60  1   202 4   78  1   7   255 206 4   126 1   206 4   128 
                                           1   206 4   128 1   205 4   129 1   205 4   129 1   205 4   130 1   205 4   130 1   204 4   130 1   204 4   130 1   203 4   131 1   203 4   131 1   202 4   131 1   202 4   131 1   200 4   131 1   200 4   131 1   199 4   130 1   199 4   130 1   198 4   130 
                                           1   198 4   130 1   198 4   129 1   198 4   129 1   197 4   128 1   197 4   128 1   197 4   126 1   197 4   126 1   197 4   125 1   197 4   125 1   198 4   124 1   198 4   124 1   198 4   123 1   198 4   123 1   199 4   123 1   199 4   123 1   200 4   122 
                                           1   200 4   122 1   202 4   122 1   202 4   122 1   203 4   122 1   203 4   122 1   204 4   123 1   204 4   123 1   205 4   123 1   205 4   123 1   205 4   124 1   205 4   124 1   206 4   125 1   206 4   125 1   206 4   126 1   7   255 193 4   126 1   210 
                                           4   126 1   7   255 202 4   118 1   202 4   135 1   7   255 239 2   69  1   108 4   69  1   108 4   69  1   108 4   184 1   108 4   184 1   239 2   184 1   239 2   184 1   239 2   69  1   7   255 239 2   69  1   239 2   69  1   7   255 239 2   69  1   239 
                                           2   69  1   7   255 239 2   69  1   239 2   69  1   7   255 245 3   93  1   245 3   101 1   245 3   101 1   252 3   103 1   252 3   103 1   31  4   103 1   31  4   103 1   38  4   101 1   38  4   101 1   38  4   93  1   38  4   93  1   31  4   91  1   31  
                                           4   91  1   252 3   91  1   252 3   91  1   245 3   93  1   7   255 245 3   71  1   245 3   79  1   245 3   79  1   252 3   81  1   252 3   81  1   31  4   81  1   31  4   81  1   38  4   79  1   38  4   79  1   38  4   71  1   38  4   71  1   31  4   69  
                                           1   31  4   69  1   252 3   69  1   252 3   69  1   245 3   71  1   7   255 245 3   152 1   245 3   159 1   245 3   159 1   252 3   162 1   252 3   162 1   31  4   162 1   31  4   162 1   38  4   159 1   38  4   159 1   38  4   152 1   38  4   152 1   31  
                                           4   149 1   31  4   149 1   252 3   149 1   252 3   149 1   245 3   152 1   7   255 245 3   174 1   245 3   182 1   245 3   182 1   252 3   184 1   252 3   184 1   31  4   184 1   31  4   184 1   38  4   182 1   38  4   182 1   38  4   174 1   38  4   174 
                                           1   31  4   172 1   31  4   172 1   252 3   172 1   252 3   172 1   245 3   174 1   7   255 45  4   93  1   45  4   101 1   45  4   101 1   52  4   103 1   52  4   103 1   88  4   103 1   88  4   103 1   95  4   101 1   95  4   101 1   95  4   93  1   95  
                                           4   93  1   88  4   91  1   88  4   91  1   52  4   91  1   52  4   91  1   45  4   93  1   7   255 45  4   71  1   45  4   79  1   45  4   79  1   52  4   81  1   52  4   81  1   88  4   81  1   88  4   81  1   95  4   79  1   95  4   79  1   95  4   71  
                                           1   95  4   71  1   88  4   69  1   88  4   69  1   52  4   69  1   52  4   69  1   45  4   71  1   7   255 45  4   152 1   45  4   159 1   45  4   159 1   52  4   162 1   52  4   162 1   88  4   162 1   88  4   162 1   95  4   159 1   95  4   159 1   95  
                                           4   152 1   95  4   152 1   88  4   149 1   88  4   149 1   52  4   149 1   52  4   149 1   45  4   152 1   7   255 45  4   174 1   45  4   182 1   45  4   182 1   52  4   184 1   52  4   184 1   88  4   184 1   88  4   184 1   95  4   182 1   95  4   182 
                                           1   95  4   174 1   95  4   174 1   88  4   172 1   88  4   172 1   52  4   172 1   52  4   172 1   45  4   174 1   7   255 243 2   69  1   243 2   70  1   243 2   70  1   243 2   71  1   243 2   71  1   242 2   72  1   242 2   72  1   241 2   73  1   241 
                                           2   73  1   240 2   73  1   240 2   73  1   239 2   73  1   239 2   73  1   238 2   73  1   238 2   73  1   237 2   73  1   237 2   73  1   236 2   72  1   236 2   72  1   235 2   71  1   235 2   71  1   234 2   70  1   234 2   70  1   234 2   69  1   234 
                                           2   69  1   234 2   68  1   234 2   68  1   235 2   67  1   235 2   67  1   236 2   66  1   236 2   66  1   237 2   65  1   237 2   65  1   238 2   64  1   238 2   64  1   239 2   64  1   239 2   64  1   240 2   64  1   240 2   64  1   241 2   65  1   241 
                                           2   65  1   242 2   66  1   242 2   66  1   243 2   67  1   243 2   67  1   243 2   68  1   243 2   68  1   243 2   69  1   7   255 230 2   69  1   248 2   69  1   7   255 239 2   60  1   239 2   78  1   7   255 243 2   184 1   243 2   185 1   243 2   185 
                                           1   243 2   186 1   243 2   186 1   242 2   187 1   242 2   187 1   241 2   188 1   241 2   188 1   240 2   188 1   240 2   188 1   239 2   188 1   239 2   188 1   238 2   188 1   238 2   188 1   237 2   188 1   237 2   188 1   236 2   187 1   236 2   187 
                                           1   235 2   186 1   235 2   186 1   234 2   185 1   234 2   185 1   234 2   184 1   234 2   184 1   234 2   183 1   234 2   183 1   235 2   182 1   235 2   182 1   236 2   181 1   236 2   181 1   237 2   180 1   237 2   180 1   238 2   180 1   238 2   180 
                                           1   239 2   180 1   239 2   180 1   240 2   180 1   240 2   180 1   241 2   180 1   241 2   180 1   242 2   181 1   242 2   181 1   243 2   182 1   243 2   182 1   243 2   183 1   243 2   183 1   243 2   184 1   7   255 230 2   184 1   248 2   184 1   7   
                                           255 239 2   175 1   239 2   193 1   7   255 14  3   126 1   14  3   128 1   14  3   128 1   13  3   129 1   13  3   129 1   13  3   130 1   13  3   130 1   12  3   130 1   12  3   130 1   11  3   131 1   11  3   131 1   9   3   131 1   9   3   131 1   8   
                                           3   131 1   8   3   131 1   7   3   130 1   7   3   130 1   6   3   130 1   6   3   130 1   6   3   129 1   6   3   129 1   5   3   128 1   5   3   128 1   5   3   126 1   5   3   126 1   5   3   125 1   5   3   125 1   6   3   124 1   6   3   124 1   6   
                                           3   123 1   6   3   123 1   7   3   123 1   7   3   123 1   8   3   122 1   8   3   122 1   9   3   122 1   9   3   122 1   11  3   122 1   11  3   122 1   12  3   123 1   12  3   123 1   13  3   123 1   13  3   123 1   13  3   124 1   13  3   124 1   14  
                                           3   125 1   14  3   125 1   14  3   126 1   7   255 0   3   126 1   18  3   126 1   7   255 9   3   118 1   9   3   135 1   7   255 113 4   184 1   113 4   185 1   113 4   185 1   112 4   186 1   112 4   186 1   112 4   187 1   112 4   187 1   111 4   188 
                                           1   111 4   188 1   110 4   188 1   110 4   188 1   108 4   188 1   108 4   188 1   107 4   188 1   107 4   188 1   106 4   188 1   106 4   188 1   105 4   187 1   105 4   187 1   105 4   186 1   105 4   186 1   104 4   185 1   104 4   185 1   104 4   184 
                                           1   104 4   184 1   104 4   183 1   104 4   183 1   105 4   182 1   105 4   182 1   105 4   181 1   105 4   181 1   106 4   180 1   106 4   180 1   107 4   180 1   107 4   180 1   108 4   180 1   108 4   180 1   110 4   180 1   110 4   180 1   111 4   180 
                                           1   111 4   180 1   112 4   181 1   112 4   181 1   112 4   182 1   112 4   182 1   113 4   183 1   113 4   183 1   113 4   184 1   7   255 100 4   184 1   117 4   184 1   7   255 108 4   175 1   108 4   193 1   7   255 113 4   69  1   113 4   70  1   113 
                                           4   70  1   112 4   71  1   112 4   71  1   112 4   72  1   112 4   72  1   111 4   73  1   111 4   73  1   110 4   73  1   110 4   73  1   108 4   73  1   108 4   73  1   107 4   73  1   107 4   73  1   106 4   73  1   106 4   73  1   105 4   72  1   105 
                                           4   72  1   105 4   71  1   105 4   71  1   104 4   70  1   104 4   70  1   104 4   69  1   104 4   69  1   104 4   68  1   104 4   68  1   105 4   67  1   105 4   67  1   105 4   66  1   105 4   66  1   106 4   65  1   106 4   65  1   107 4   64  1   107 
                                           4   64  1   108 4   64  1   108 4   64  1   110 4   64  1   110 4   64  1   111 4   65  1   111 4   65  1   112 4   66  1   112 4   66  1   112 4   67  1   112 4   67  1   113 4   68  1   113 4   68  1   113 4   69  1   7   255 100 4   69  1   117 4   69  
                                           1   7   255 108 4   60  1   108 4   78  1   7   255 46  4   184 1   46  4   185 1   46  4   185 1   46  4   186 1   46  4   186 1   45  4   187 1   45  4   187 1   44  4   188 1   44  4   188 1   43  4   188 1   43  4   188 1   42  4   188 1   42  4   188 
                                           1   41  4   188 1   41  4   188 1   40  4   188 1   40  4   188 1   39  4   187 1   39  4   187 1   38  4   186 1   38  4   186 1   38  4   185 1   38  4   185 1   37  4   184 1   37  4   184 1   38  4   183 1   38  4   183 1   38  4   182 1   38  4   182 
                                           1   39  4   181 1   39  4   181 1   40  4   180 1   40  4   180 1   41  4   180 1   41  4   180 1   42  4   180 1   42  4   180 1   43  4   180 1   43  4   180 1   44  4   180 1   44  4   180 1   45  4   181 1   45  4   181 1   46  4   182 1   46  4   182 
                                           1   46  4   183 1   46  4   183 1   46  4   184 1   7   255 33  4   184 1   51  4   184 1   7   255 42  4   175 1   42  4   193 1   7   255 46  4   69  1   46  4   70  1   46  4   70  1   46  4   71  1   46  4   71  1   45  4   72  1   45  4   72  1   44  
                                           4   73  1   44  4   73  1   43  4   73  1   43  4   73  1   42  4   73  1   42  4   73  1   41  4   73  1   41  4   73  1   40  4   73  1   40  4   73  1   39  4   72  1   39  4   72  1   38  4   71  1   38  4   71  1   38  4   70  1   38  4   70  1   37  
                                           4   69  1   37  4   69  1   38  4   68  1   38  4   68  1   38  4   67  1   38  4   67  1   39  4   66  1   39  4   66  1   40  4   65  1   40  4   65  1   41  4   64  1   41  4   64  1   42  4   64  1   42  4   64  1   43  4   64  1   43  4   64  1   44  
                                           4   65  1   44  4   65  1   45  4   66  1   45  4   66  1   46  4   67  1   46  4   67  1   46  4   68  1   46  4   68  1   46  4   69  1   7   255 33  4   69  1   51  4   69  1   7   255 42  4   60  1   42  4   78  1   7   255 113 4   126 1   113 4   128 
                                           1   113 4   128 1   112 4   129 1   112 4   129 1   112 4   130 1   112 4   130 1   111 4   130 1   111 4   130 1   110 4   131 1   110 4   131 1   108 4   131 1   108 4   131 1   107 4   131 1   107 4   131 1   106 4   130 1   106 4   130 1   105 4   130 
                                           1   105 4   130 1   105 4   129 1   105 4   129 1   104 4   128 1   104 4   128 1   104 4   126 1   104 4   126 1   104 4   125 1   104 4   125 1   105 4   124 1   105 4   124 1   105 4   123 1   105 4   123 1   106 4   123 1   106 4   123 1   107 4   122 
                                           1   107 4   122 1   108 4   122 1   108 4   122 1   110 4   122 1   110 4   122 1   111 4   123 1   111 4   123 1   112 4   123 1   112 4   123 1   112 4   124 1   112 4   124 1   113 4   125 1   113 4   125 1   113 4   126 1   7   255 100 4   126 1   117 
                                           4   126 1   7   255 108 4   118 1   108 4   135 1   7   255 172 2   126 1   9   3   126 1   7   255 241 2   93  1   241 2   101 1   241 2   101 1   248 2   103 1   248 2   103 1   27  3   103 1   27  3   103 1   34  3   101 1   34  3   101 1   34  3   93  
                                           1   34  3   93  1   27  3   91  1   27  3   91  1   248 2   91  1   248 2   91  1   241 2   93  1   7   255 241 2   71  1   241 2   79  1   241 2   79  1   248 2   81  1   248 2   81  1   27  3   81  1   27  3   81  1   34  3   79  1   34  3   79  1   34  
                                           3   71  1   34  3   71  1   27  3   69  1   27  3   69  1   248 2   69  1   248 2   69  1   241 2   71  1   7   255 241 2   152 1   241 2   159 1   241 2   159 1   248 2   162 1   248 2   162 1   27  3   162 1   27  3   162 1   34  3   159 1   34  3   159 
                                           1   34  3   152 1   34  3   152 1   27  3   149 1   27  3   149 1   248 2   149 1   248 2   149 1   241 2   152 1   7   255 241 2   174 1   241 2   182 1   241 2   182 1   248 2   184 1   248 2   184 1   27  3   184 1   27  3   184 1   34  3   182 1   34  
                                           3   182 1   34  3   174 1   34  3   174 1   27  3   172 1   27  3   172 1   248 2   172 1   248 2   172 1   241 2   174 1   7   255 177 2   126 1   176 2   128 1   176 2   128 1   176 2   129 1   176 2   129 1   175 2   130 1   175 2   130 1   174 2   131 
                                           1   174 2   131 1   172 2   131 1   172 2   131 1   171 2   131 1   171 2   131 1   170 2   130 1   170 2   130 1   169 2   129 1   169 2   129 1   168 2   128 1   168 2   128 1   168 2   126 1   168 2   126 1   168 2   125 1   168 2   125 1   169 2   124 
                                           1   169 2   124 1   170 2   123 1   170 2   123 1   171 2   122 1   171 2   122 1   172 2   122 1   172 2   122 1   174 2   122 1   174 2   122 1   175 2   123 1   175 2   123 1   176 2   124 1   176 2   124 1   176 2   125 1   176 2   125 1   177 2   126 
                                           1   7   255 163 2   126 1   181 2   126 1   7   255 172 2   118 1   172 2   135 1   7   255 14  3   184 1   14  3   185 1   14  3   185 1   13  3   187 1   13  3   187 1   12  3   188 1   12  3   188 1   11  3   188 1   11  3   188 1   9   3   188 1   9   
                                           3   188 1   8   3   188 1   8   3   188 1   7   3   188 1   7   3   188 1   6   3   187 1   6   3   187 1   5   3   185 1   5   3   185 1   5   3   184 1   5   3   184 1   5   3   183 1   5   3   183 1   6   3   181 1   6   3   181 1   7   3   180 1   7   
                                           3   180 1   8   3   180 1   8   3   180 1   9   3   180 1   9   3   180 1   11  3   180 1   11  3   180 1   12  3   180 1   12  3   180 1   13  3   181 1   13  3   181 1   14  3   183 1   14  3   183 1   14  3   184 1   7   255 0   3   184 1   18  3   184 
                                           1   7   255 9   3   175 1   9   3   193 1   7   255 14  3   69  1   14  3   70  1   14  3   70  1   13  3   71  1   13  3   71  1   12  3   72  1   12  3   72  1   11  3   73  1   11  3   73  1   9   3   73  1   9   3   73  1   8   3   73  1   8   3   73  
                                           1   7   3   72  1   7   3   72  1   6   3   71  1   6   3   71  1   5   3   70  1   5   3   70  1   5   3   69  1   5   3   69  1   5   3   67  1   5   3   67  1   6   3   66  1   6   3   66  1   7   3   65  1   7   3   65  1   8   3   65  1   8   3   65  
                                           1   9   3   64  1   9   3   64  1   11  3   65  1   11  3   65  1   12  3   65  1   12  3   65  1   13  3   66  1   13  3   66  1   14  3   67  1   14  3   67  1   14  3   69  1   7   255 0   3   69  1   18  3   69  1   7   255 9   3   60  1   9   3   78  
                                           1   7   255 14  3   126 1   14  3   128 1   14  3   128 1   13  3   129 1   13  3   129 1   12  3   130 1   12  3   130 1   11  3   131 1   11  3   131 1   9   3   131 1   9   3   131 1   8   3   131 1   8   3   131 1   7   3   130 1   7   3   130 1   6   
                                           3   129 1   6   3   129 1   5   3   128 1   5   3   128 1   5   3   126 1   5   3   126 1   5   3   125 1   5   3   125 1   6   3   124 1   6   3   124 1   7   3   123 1   7   3   123 1   8   3   122 1   8   3   122 1   9   3   122 1   9   3   122 1   11  
                                           3   122 1   11  3   122 1   12  3   123 1   12  3   123 1   13  3   124 1   13  3   124 1   14  3   125 1   14  3   125 1   14  3   126 1   7   255 0   3   126 1   18  3   126 1   7   255 9   3   118 1   9   3   135 1   7   255 47  1   69  1   172 2   69  
                                           1   172 2   69  1   172 2   184 1   172 2   184 1   47  1   184 1   47  1   184 1   47  1   69  1   7   255 47  1   69  1   47  1   69  1   7   255 47  1   69  1   47  1   69  1   7   255 47  1   69  1   47  1   69  1   7   255 53  2   93  1   53  2   101 
                                           )) "a")
 (_WriteStream FILE (vl-list->string (list 1   53  2   101 1   60  2   103 1   60  2   103 1   95  2   103 1   95  2   103 1   102 2   101 1   102 2   101 1   102 2   93  1   102 2   93  1   95  2   91  1   95  2   91  1   60  2   91  1   60  2   91  1   53  2   93  1   7   255 53  2   71  1   53  
                                           2   79  1   53  2   79  1   60  2   81  1   60  2   81  1   95  2   81  1   95  2   81  1   102 2   79  1   102 2   79  1   102 2   71  1   102 2   71  1   95  2   69  1   95  2   69  1   60  2   69  1   60  2   69  1   53  2   71  1   7   255 53  2   152 
                                           1   53  2   159 1   53  2   159 1   60  2   162 1   60  2   162 1   95  2   162 1   95  2   162 1   102 2   159 1   102 2   159 1   102 2   152 1   102 2   152 1   95  2   149 1   95  2   149 1   60  2   149 1   60  2   149 1   53  2   152 1   7   255 53  
                                           2   174 1   53  2   182 1   53  2   182 1   60  2   184 1   60  2   184 1   95  2   184 1   95  2   184 1   102 2   182 1   102 2   182 1   102 2   174 1   102 2   174 1   95  2   172 1   95  2   172 1   60  2   172 1   60  2   172 1   53  2   174 1   7   
                                           255 109 2   93  1   109 2   101 1   109 2   101 1   116 2   103 1   116 2   103 1   152 2   103 1   152 2   103 1   159 2   101 1   159 2   101 1   159 2   93  1   159 2   93  1   152 2   91  1   152 2   91  1   116 2   91  1   116 2   91  1   109 2   93  
                                           1   7   255 109 2   71  1   109 2   79  1   109 2   79  1   116 2   81  1   116 2   81  1   152 2   81  1   152 2   81  1   159 2   79  1   159 2   79  1   159 2   71  1   159 2   71  1   152 2   69  1   152 2   69  1   116 2   69  1   116 2   69  1   109 
                                           2   71  1   7   255 109 2   152 1   109 2   159 1   109 2   159 1   116 2   162 1   116 2   162 1   152 2   162 1   152 2   162 1   159 2   159 1   159 2   159 1   159 2   152 1   159 2   152 1   152 2   149 1   152 2   149 1   116 2   149 1   116 2   149 
                                           1   109 2   152 1   7   255 109 2   174 1   109 2   182 1   109 2   182 1   116 2   184 1   116 2   184 1   152 2   184 1   152 2   184 1   159 2   182 1   159 2   182 1   159 2   174 1   159 2   174 1   152 2   172 1   152 2   172 1   116 2   172 1   116 
                                           2   172 1   109 2   174 1   7   255 51  1   69  1   51  1   70  1   51  1   70  1   50  1   71  1   50  1   71  1   49  1   72  1   49  1   72  1   48  1   73  1   48  1   73  1   47  1   73  1   47  1   73  1   45  1   73  1   45  1   73  1   44  1   72  
                                           1   44  1   72  1   43  1   71  1   43  1   71  1   42  1   70  1   42  1   70  1   42  1   69  1   42  1   69  1   42  1   67  1   42  1   67  1   43  1   66  1   43  1   66  1   44  1   65  1   44  1   65  1   45  1   65  1   45  1   65  1   47  1   64  
                                           1   47  1   64  1   48  1   65  1   48  1   65  1   49  1   65  1   49  1   65  1   50  1   66  1   50  1   66  1   51  1   67  1   51  1   67  1   51  1   69  1   7   255 38  1   69  1   55  1   69  1   7   255 47  1   60  1   47  1   78  1   7   255 51  
                                           1   184 1   51  1   185 1   51  1   185 1   50  1   187 1   50  1   187 1   49  1   188 1   49  1   188 1   48  1   188 1   48  1   188 1   47  1   188 1   47  1   188 1   45  1   188 1   45  1   188 1   44  1   188 1   44  1   188 1   43  1   187 1   43  
                                           1   187 1   42  1   185 1   42  1   185 1   42  1   184 1   42  1   184 1   42  1   183 1   42  1   183 1   43  1   181 1   43  1   181 1   44  1   180 1   44  1   180 1   45  1   180 1   45  1   180 1   47  1   180 1   47  1   180 1   48  1   180 1   48  
                                           1   180 1   49  1   180 1   49  1   180 1   50  1   181 1   50  1   181 1   51  1   183 1   51  1   183 1   51  1   184 1   7   255 38  1   184 1   55  1   184 1   7   255 47  1   175 1   47  1   193 1   7   255 78  1   126 1   77  1   128 1   77  1   128 
                                           1   77  1   129 1   77  1   129 1   76  1   130 1   76  1   130 1   75  1   131 1   75  1   131 1   73  1   131 1   73  1   131 1   72  1   131 1   72  1   131 1   71  1   130 1   71  1   130 1   70  1   129 1   70  1   129 1   69  1   128 1   69  1   128 
                                           1   69  1   126 1   69  1   126 1   69  1   125 1   69  1   125 1   70  1   124 1   70  1   124 1   71  1   123 1   71  1   123 1   72  1   122 1   72  1   122 1   73  1   122 1   73  1   122 1   75  1   122 1   75  1   122 1   76  1   123 1   76  1   123 
                                           1   77  1   124 1   77  1   124 1   77  1   125 1   77  1   125 1   78  1   126 1   7   255 64  1   126 1   82  1   126 1   7   255 73  1   118 1   73  1   135 1   7   255 177 2   184 1   176 2   185 1   176 2   185 1   176 2   187 1   176 2   187 1   175 
                                           2   188 1   175 2   188 1   174 2   188 1   174 2   188 1   172 2   188 1   172 2   188 1   171 2   188 1   171 2   188 1   170 2   188 1   170 2   188 1   169 2   187 1   169 2   187 1   168 2   185 1   168 2   185 1   168 2   184 1   168 2   184 1   168 
                                           2   183 1   168 2   183 1   169 2   181 1   169 2   181 1   170 2   180 1   170 2   180 1   171 2   180 1   171 2   180 1   172 2   180 1   172 2   180 1   174 2   180 1   174 2   180 1   175 2   180 1   175 2   180 1   176 2   181 1   176 2   181 1   176 
                                           2   183 1   176 2   183 1   177 2   184 1   7   255 163 2   184 1   181 2   184 1   7   255 172 2   175 1   172 2   193 1   7   255 177 2   69  1   176 2   70  1   176 2   70  1   176 2   71  1   176 2   71  1   175 2   72  1   175 2   72  1   174 2   73  
                                           1   174 2   73  1   172 2   73  1   172 2   73  1   171 2   73  1   171 2   73  1   170 2   72  1   170 2   72  1   169 2   71  1   169 2   71  1   168 2   70  1   168 2   70  1   168 2   69  1   168 2   69  1   168 2   67  1   168 2   67  1   169 2   66  
                                           1   169 2   66  1   170 2   65  1   170 2   65  1   171 2   65  1   171 2   65  1   172 2   64  1   172 2   64  1   174 2   65  1   174 2   65  1   175 2   65  1   175 2   65  1   176 2   66  1   176 2   66  1   176 2   67  1   176 2   67  1   177 2   69  
                                           1   7   255 163 2   69  1   181 2   69  1   7   255 172 2   60  1   172 2   78  1   7   255 110 2   184 1   110 2   185 1   110 2   185 1   109 2   187 1   109 2   187 1   108 2   188 1   108 2   188 1   107 2   188 1   107 2   188 1   106 2   188 1   106 
                                           2   188 1   104 2   188 1   104 2   188 1   103 2   188 1   103 2   188 1   102 2   187 1   102 2   187 1   101 2   185 1   101 2   185 1   101 2   184 1   101 2   184 1   101 2   183 1   101 2   183 1   102 2   181 1   102 2   181 1   103 2   180 1   103 
                                           2   180 1   104 2   180 1   104 2   180 1   106 2   180 1   106 2   180 1   107 2   180 1   107 2   180 1   108 2   180 1   108 2   180 1   109 2   181 1   109 2   181 1   110 2   183 1   110 2   183 1   110 2   184 1   7   255 97  2   184 1   114 2   184 
                                           1   7   255 106 2   175 1   106 2   193 1   7   255 110 2   69  1   110 2   70  1   110 2   70  1   109 2   71  1   109 2   71  1   108 2   72  1   108 2   72  1   107 2   73  1   107 2   73  1   106 2   73  1   106 2   73  1   104 2   73  1   104 2   73  
                                           1   103 2   72  1   103 2   72  1   102 2   71  1   102 2   71  1   101 2   70  1   101 2   70  1   101 2   69  1   101 2   69  1   101 2   67  1   101 2   67  1   102 2   66  1   102 2   66  1   103 2   65  1   103 2   65  1   104 2   65  1   104 2   65  
                                           1   106 2   64  1   106 2   64  1   107 2   65  1   107 2   65  1   108 2   65  1   108 2   65  1   109 2   66  1   109 2   66  1   110 2   67  1   110 2   67  1   110 2   69  1   7   255 97  2   69  1   114 2   69  1   7   255 106 2   60  1   106 2   78  
                                           1   7   255 177 2   126 1   176 2   128 1   176 2   128 1   176 2   129 1   176 2   129 1   175 2   130 1   175 2   130 1   174 2   131 1   174 2   131 1   172 2   131 1   172 2   131 1   171 2   131 1   171 2   131 1   170 2   130 1   170 2   130 1   169 
                                           2   129 1   169 2   129 1   168 2   128 1   168 2   128 1   168 2   126 1   168 2   126 1   168 2   125 1   168 2   125 1   169 2   124 1   169 2   124 1   170 2   123 1   170 2   123 1   171 2   122 1   171 2   122 1   172 2   122 1   172 2   122 1   174 
                                           2   122 1   174 2   122 1   175 2   123 1   175 2   123 1   176 2   124 1   176 2   124 1   176 2   125 1   176 2   125 1   177 2   126 1   7   255 163 2   126 1   181 2   126 1   7   255 172 2   118 1   172 2   135 1   7   255 27  0   69  1   161 0   69  
                                           1   161 0   69  1   161 0   103 1   161 0   103 1   101 1   103 1   101 1   103 1   101 1   149 1   101 1   149 1   161 0   149 1   161 0   149 1   161 0   184 1   161 0   184 1   27  0   184 1   27  0   184 1   27  0   69  1   7   255 27  0   69  1   27  
                                           0   69  1   7   255 27  0   69  1   27  0   69  1   7   255 27  0   69  1   27  0   69  1   7   255 85  1   138 1   83  1   140 1   83  1   140 1   80  1   141 1   80  1   141 1   77  1   142 1   77  1   142 1   75  1   143 1   75  1   143 1   72  1   143 
                                           1   72  1   143 1   69  1   142 1   69  1   142 1   66  1   141 1   66  1   141 1   64  1   140 1   64  1   140 1   61  1   138 1   61  1   138 1   60  1   136 1   60  1   136 1   58  1   133 1   58  1   133 1   57  1   131 1   57  1   131 1   57  1   128 
                                           1   57  1   128 1   57  1   125 1   57  1   125 1   57  1   122 1   57  1   122 1   58  1   119 1   58  1   119 1   60  1   117 1   60  1   117 1   61  1   115 1   61  1   115 1   64  1   113 1   64  1   113 1   66  1   111 1   66  1   111 1   69  1   110 
                                           1   69  1   110 1   72  1   110 1   72  1   110 1   75  1   110 1   75  1   110 1   77  1   110 1   77  1   110 1   80  1   111 1   80  1   111 1   83  1   113 1   83  1   113 1   85  1   115 1   7   255 85  1   115 1   85  1   138 1   7   255 20  1   93  
                                           1   20  1   101 1   20  1   101 1   27  1   103 1   27  1   103 1   63  1   103 1   63  1   103 1   70  1   101 1   70  1   101 1   70  1   93  1   70  1   93  1   63  1   91  1   63  1   91  1   27  1   91  1   27  1   91  1   20  1   93  1   7   255 20  
                                           1   71  1   20  1   79  1   20  1   79  1   27  1   81  1   27  1   81  1   63  1   81  1   63  1   81  1   70  1   79  1   70  1   79  1   70  1   71  1   70  1   71  1   63  1   69  1   63  1   69  1   27  1   69  1   27  1   69  1   20  1   71  1   7   
                                           255 20  1   152 1   20  1   159 1   20  1   159 1   27  1   162 1   27  1   162 1   63  1   162 1   63  1   162 1   70  1   159 1   70  1   159 1   70  1   152 1   70  1   152 1   63  1   149 1   63  1   149 1   27  1   149 1   27  1   149 1   20  1   152 
                                           1   7   255 20  1   174 1   20  1   182 1   20  1   182 1   27  1   184 1   27  1   184 1   63  1   184 1   63  1   184 1   70  1   182 1   70  1   182 1   70  1   174 1   70  1   174 1   63  1   172 1   63  1   172 1   27  1   172 1   27  1   172 1   20  
                                           1   174 1   7   255 77  1   93  1   77  1   101 1   77  1   101 1   83  1   103 1   83  1   103 1   119 1   103 1   119 1   103 1   126 1   101 1   126 1   101 1   126 1   93  1   126 1   93  1   119 1   91  1   119 1   91  1   83  1   91  1   83  1   91  
                                           1   77  1   93  1   7   255 77  1   71  1   77  1   79  1   77  1   79  1   83  1   81  1   83  1   81  1   119 1   81  1   119 1   81  1   126 1   79  1   126 1   79  1   126 1   71  1   126 1   71  1   119 1   69  1   119 1   69  1   83  1   69  1   83  
                                           1   69  1   77  1   71  1   7   255 77  1   152 1   77  1   159 1   77  1   159 1   83  1   162 1   83  1   162 1   119 1   162 1   119 1   162 1   126 1   159 1   126 1   159 1   126 1   152 1   126 1   152 1   119 1   149 1   119 1   149 1   83  1   149 
                                           1   83  1   149 1   77  1   152 1   7   255 77  1   174 1   77  1   182 1   77  1   182 1   83  1   184 1   83  1   184 1   119 1   184 1   119 1   184 1   126 1   182 1   126 1   182 1   126 1   174 1   126 1   174 1   119 1   172 1   119 1   172 1   83  
                                           1   172 1   83  1   172 1   77  1   174 1   7   255 63  0   126 1   63  0   128 1   63  0   128 1   62  0   129 1   62  0   129 1   61  0   130 1   61  0   130 1   60  0   131 1   60  0   131 1   58  0   131 1   58  0   131 1   57  0   131 1   57  0   131 
                                           1   56  0   130 1   56  0   130 1   55  0   129 1   55  0   129 1   54  0   128 1   54  0   128 1   54  0   126 1   54  0   126 1   54  0   125 1   54  0   125 1   55  0   124 1   55  0   124 1   56  0   123 1   56  0   123 1   57  0   122 1   57  0   122 
                                           1   58  0   122 1   58  0   122 1   60  0   122 1   60  0   122 1   61  0   123 1   61  0   123 1   62  0   124 1   62  0   124 1   63  0   125 1   63  0   125 1   63  0   126 1   7   255 50  0   126 1   67  0   126 1   7   255 58  0   118 1   58  0   135 
                                           1   7   255 34  0   71  1   34  0   79  1   34  0   79  1   41  0   81  1   41  0   81  1   76  0   81  1   76  0   81  1   83  0   79  1   83  0   79  1   83  0   71  1   83  0   71  1   76  0   69  1   76  0   69  1   41  0   69  1   41  0   69  1   34  
                                           0   71  1   7   255 34  0   174 1   34  0   182 1   34  0   182 1   41  0   184 1   41  0   184 1   76  0   184 1   76  0   184 1   83  0   182 1   83  0   182 1   83  0   174 1   83  0   174 1   76  0   172 1   76  0   172 1   41  0   172 1   41  0   172 
                                           1   34  0   174 1   7   255 78  1   184 1   77  1   185 1   77  1   185 1   77  1   187 1   77  1   187 1   76  1   188 1   76  1   188 1   75  1   188 1   75  1   188 1   73  1   188 1   73  1   188 1   72  1   188 1   72  1   188 1   71  1   188 1   71  
                                           1   188 1   70  1   187 1   70  1   187 1   69  1   185 1   69  1   185 1   69  1   184 1   69  1   184 1   69  1   183 1   69  1   183 1   70  1   181 1   70  1   181 1   71  1   180 1   71  1   180 1   72  1   180 1   72  1   180 1   73  1   180 1   73  
                                           1   180 1   75  1   180 1   75  1   180 1   76  1   180 1   76  1   180 1   77  1   181 1   77  1   181 1   77  1   183 1   77  1   183 1   78  1   184 1   7   255 64  1   184 1   82  1   184 1   7   255 73  1   175 1   73  1   193 1   7   255 78  1   69  
                                           1   77  1   70  1   77  1   70  1   77  1   71  1   77  1   71  1   76  1   72  1   76  1   72  1   75  1   73  1   75  1   73  1   73  1   73  1   73  1   73  1   72  1   73  1   72  1   73  1   71  1   72  1   71  1   72  1   70  1   71  1   70  1   71  
                                           1   69  1   70  1   69  1   70  1   69  1   69  1   69  1   69  1   69  1   67  1   69  1   67  1   70  1   66  1   70  1   66  1   71  1   65  1   71  1   65  1   72  1   65  1   72  1   65  1   73  1   64  1   73  1   64  1   75  1   65  1   75  1   65  
                                           1   76  1   65  1   76  1   65  1   77  1   66  1   77  1   66  1   77  1   67  1   77  1   67  1   78  1   69  1   7   255 64  1   69  1   82  1   69  1   7   255 73  1   60  1   73  1   78  1   7   255 78  1   126 1   77  1   128 1   77  1   128 1   77  
                                           1   129 1   77  1   129 1   76  1   130 1   76  1   130 1   75  1   131 1   75  1   131 1   73  1   131 1   73  1   131 1   72  1   131 1   72  1   131 1   71  1   130 1   71  1   130 1   70  1   129 1   70  1   129 1   69  1   128 1   69  1   128 1   69  
                                           1   126 1   69  1   126 1   69  1   125 1   69  1   125 1   70  1   124 1   70  1   124 1   71  1   123 1   71  1   123 1   72  1   122 1   72  1   122 1   73  1   122 1   73  1   122 1   75  1   122 1   75  1   122 1   76  1   123 1   76  1   123 1   77  
                                           1   124 1   77  1   124 1   77  1   125 1   77  1   125 1   78  1   126 1   7   255 64  1   126 1   82  1   126 1   7   255 73  1   118 1   73  1   135 1   7   255 32  0   184 1   32  0   185 1   32  0   185 1   31  0   187 1   31  0   187 1   30  0   188 
                                           1   30  0   188 1   29  0   188 1   29  0   188 1   27  0   188 1   27  0   188 1   26  0   188 1   26  0   188 1   25  0   188 1   25  0   188 1   24  0   187 1   24  0   187 1   23  0   185 1   23  0   185 1   23  0   184 1   23  0   184 1   23  0   183 
                                           1   23  0   183 1   24  0   181 1   24  0   181 1   25  0   180 1   25  0   180 1   26  0   180 1   26  0   180 1   27  0   180 1   27  0   180 1   29  0   180 1   29  0   180 1   30  0   180 1   30  0   180 1   31  0   181 1   31  0   181 1   32  0   183 
                                           1   32  0   183 1   32  0   184 1   7   255 18  0   184 1   36  0   184 1   7   255 27  0   175 1   27  0   193 1   7   255 32  0   69  1   32  0   70  1   32  0   70  1   31  0   71  1   31  0   71  1   30  0   72  1   30  0   72  1   29  0   73  1   29  
                                           0   73  1   27  0   73  1   27  0   73  1   26  0   73  1   26  0   73  1   25  0   72  1   25  0   72  1   24  0   71  1   24  0   71  1   23  0   70  1   23  0   70  1   23  0   69  1   23  0   69  1   23  0   67  1   23  0   67  1   24  0   66  1   24  
                                           0   66  1   25  0   65  1   25  0   65  1   26  0   65  1   26  0   65  1   27  0   64  1   27  0   64  1   29  0   65  1   29  0   65  1   30  0   65  1   30  0   65  1   31  0   66  1   31  0   66  1   32  0   67  1   32  0   67  1   32  0   69  1   7   
                                           255 18  0   69  1   36  0   69  1   7   255 27  0   60  1   27  0   78  1   7   255 63  0   69  1   63  0   70  1   63  0   70  1   62  0   71  1   62  0   71  1   61  0   72  1   61  0   72  1   60  0   73  1   60  0   73  1   58  0   73  1   58  0   73  
                                           )) "a")
 (_WriteStream FILE (vl-list->string (list 1   57  0   73  1   57  0   73  1   56  0   72  1   56  0   72  1   55  0   71  1   55  0   71  1   54  0   70  1   54  0   70  1   54  0   69  1   54  0   69  1   54  0   67  1   54  0   67  1   55  0   66  1   55  0   66  1   56  0   65  1   56  0   65  
                                           1   57  0   65  1   57  0   65  1   58  0   64  1   58  0   64  1   60  0   65  1   60  0   65  1   61  0   65  1   61  0   65  1   62  0   66  1   62  0   66  1   63  0   67  1   63  0   67  1   63  0   69  1   7   255 50  0   69  1   67  0   69  1   7   
                                           255 58  0   60  1   58  0   78  1   7   255 63  0   184 1   63  0   185 1   63  0   185 1   62  0   187 1   62  0   187 1   61  0   188 1   61  0   188 1   60  0   188 1   60  0   188 1   58  0   188 1   58  0   188 1   57  0   188 1   57  0   188 1   56  
                                           0   188 1   56  0   188 1   55  0   187 1   55  0   187 1   54  0   185 1   54  0   185 1   54  0   184 1   54  0   184 1   54  0   183 1   54  0   183 1   55  0   181 1   55  0   181 1   56  0   180 1   56  0   180 1   57  0   180 1   57  0   180 1   58  
                                           0   180 1   58  0   180 1   60  0   180 1   60  0   180 1   61  0   180 1   61  0   180 1   62  0   181 1   62  0   181 1   63  0   183 1   63  0   183 1   63  0   184 1   7   255 50  0   184 1   67  0   184 1   7   255 58  0   175 1   58  0   193 1   0   
                                           252 65  117 116 111 67  65  68  32  83  108 105 100 101 13  10  26  0   86  2   106 6   234 2   99  219 79  1   2   0   52  18  7   255 7   255 57  0   39  1   241 0   39  1   241 0   39  1   241 0   87  1   241 0   87  1   8   2   87  1   8   2   87  1   
                                           8   2   150 1   8   2   150 1   241 0   150 1   241 0   150 1   241 0   198 1   241 0   198 1   57  0   198 1   57  0   198 1   57  0   39  1   7   255 57  0   39  1   57  0   39  1   7   255 57  0   39  1   57  0   39  1   7   255 241 1   135 1   236 1   
                                           138 1   236 1   138 1   231 1   141 1   231 1   141 1   225 1   141 1   225 1   141 1   219 1   141 1   219 1   141 1   213 1   138 1   213 1   138 1   209 1   135 1   209 1   135 1   205 1   130 1   205 1   130 1   203 1   124 1   203 1   124 1   202 1   
                                           119 1   202 1   119 1   203 1   113 1   203 1   113 1   205 1   107 1   205 1   107 1   209 1   102 1   209 1   102 1   213 1   99  1   213 1   99  1   219 1   97  1   219 1   97  1   225 1   96  1   225 1   96  1   231 1   97  1   231 1   97  1   236 1   
                                           99  1   236 1   99  1   241 1   102 1   7   255 241 1   102 1   241 1   135 1   7   255 152 1   73  1   152 1   84  1   152 1   84  1   161 1   87  1   161 1   87  1   211 1   87  1   211 1   87  1   220 1   84  1   220 1   84  1   220 1   73  1   220 1   
                                           73  1   211 1   70  1   211 1   70  1   161 1   70  1   161 1   70  1   152 1   73  1   7   255 152 1   42  1   152 1   53  1   152 1   53  1   161 1   56  1   161 1   56  1   211 1   56  1   211 1   56  1   220 1   53  1   220 1   53  1   220 1   42  1   
                                           220 1   42  1   211 1   39  1   211 1   39  1   161 1   39  1   161 1   39  1   152 1   42  1   7   255 152 1   153 1   152 1   164 1   152 1   164 1   161 1   167 1   161 1   167 1   211 1   167 1   211 1   167 1   220 1   164 1   220 1   164 1   220 1   
                                           153 1   220 1   153 1   211 1   150 1   211 1   150 1   161 1   150 1   161 1   150 1   152 1   153 1   7   255 152 1   184 1   152 1   195 1   152 1   195 1   161 1   198 1   161 1   198 1   211 1   198 1   211 1   198 1   220 1   195 1   220 1   195 1   
                                           220 1   184 1   220 1   184 1   211 1   181 1   211 1   181 1   161 1   181 1   161 1   181 1   152 1   184 1   7   255 229 1   73  1   229 1   84  1   229 1   84  1   239 1   87  1   239 1   87  1   32  2   87  1   32  2   87  1   42  2   84  1   42  2   
                                           84  1   42  2   73  1   42  2   73  1   32  2   70  1   32  2   70  1   239 1   70  1   239 1   70  1   229 1   73  1   7   255 229 1   42  1   229 1   53  1   229 1   53  1   239 1   56  1   239 1   56  1   32  2   56  1   32  2   56  1   42  2   53  1   
                                           42  2   53  1   42  2   42  1   42  2   42  1   32  2   39  1   32  2   39  1   239 1   39  1   239 1   39  1   229 1   42  1   7   255 229 1   153 1   229 1   164 1   229 1   164 1   239 1   167 1   239 1   167 1   32  2   167 1   32  2   167 1   42  2   
                                           164 1   42  2   164 1   42  2   153 1   42  2   153 1   32  2   150 1   32  2   150 1   239 1   150 1   239 1   150 1   229 1   153 1   7   255 229 1   184 1   229 1   195 1   229 1   195 1   239 1   198 1   239 1   198 1   32  2   198 1   32  2   198 1   
                                           42  2   195 1   42  2   195 1   42  2   184 1   42  2   184 1   32  2   181 1   32  2   181 1   239 1   181 1   239 1   181 1   229 1   184 1   7   255 112 0   119 1   112 0   122 1   112 0   122 1   109 0   124 1   109 0   124 1   106 0   125 1   106 0   
                                           125 1   103 0   124 1   103 0   124 1   101 0   122 1   101 0   122 1   100 0   119 1   100 0   119 1   101 0   115 1   101 0   115 1   103 0   113 1   103 0   113 1   106 0   112 1   106 0   112 1   109 0   113 1   109 0   113 1   112 0   115 1   112 0   
                                           115 1   112 0   119 1   7   255 94  0   119 1   119 0   119 1   7   255 106 0   106 1   106 0   131 1   7   255 63  0   39  1   62  0   42  1   62  0   42  1   60  0   44  1   60  0   44  1   57  0   45  1   57  0   45  1   54  0   44  1   54  0   44  1   
                                           52  0   42  1   52  0   42  1   51  0   39  1   51  0   39  1   52  0   36  1   52  0   36  1   54  0   33  1   54  0   33  1   57  0   33  1   57  0   33  1   60  0   33  1   60  0   33  1   62  0   36  1   62  0   36  1   63  0   39  1   7   255 45  0   
                                           39  1   69  0   39  1   7   255 57  0   26  1   57  0   51  1   7   255 63  0   198 1   62  0   201 1   62  0   201 1   60  0   204 1   60  0   204 1   57  0   204 1   57  0   204 1   54  0   204 1   54  0   204 1   52  0   201 1   52  0   201 1   51  0   
                                           198 1   51  0   198 1   52  0   195 1   52  0   195 1   54  0   193 1   54  0   193 1   57  0   192 1   57  0   192 1   60  0   193 1   60  0   193 1   62  0   195 1   62  0   195 1   63  0   198 1   7   255 45  0   198 1   69  0   198 1   7   255 57  0   
                                           186 1   57  0   211 1   7   255 112 0   198 1   112 0   201 1   112 0   201 1   109 0   204 1   109 0   204 1   106 0   204 1   106 0   204 1   103 0   204 1   103 0   204 1   101 0   201 1   101 0   201 1   100 0   198 1   100 0   198 1   101 0   195 1   
                                           101 0   195 1   103 0   193 1   103 0   193 1   106 0   192 1   106 0   192 1   109 0   193 1   109 0   193 1   112 0   195 1   112 0   195 1   112 0   198 1   7   255 94  0   198 1   119 0   198 1   7   255 106 0   186 1   106 0   211 1   7   255 112 0   
                                           39  1   112 0   42  1   112 0   42  1   109 0   44  1   109 0   44  1   106 0   45  1   106 0   45  1   103 0   44  1   103 0   44  1   101 0   42  1   101 0   42  1   100 0   39  1   100 0   39  1   101 0   36  1   101 0   36  1   103 0   33  1   103 0   
                                           33  1   106 0   33  1   106 0   33  1   109 0   33  1   109 0   33  1   112 0   36  1   112 0   36  1   112 0   39  1   7   255 94  0   39  1   119 0   39  1   7   255 106 0   26  1   106 0   51  1   7   255 231 1   39  1   230 1   42  1   230 1   42  1   
                                           228 1   44  1   228 1   44  1   225 1   45  1   225 1   45  1   222 1   44  1   222 1   44  1   219 1   42  1   219 1   42  1   219 1   39  1   219 1   39  1   219 1   36  1   219 1   36  1   222 1   33  1   222 1   33  1   225 1   33  1   225 1   33  1   
                                           228 1   33  1   228 1   33  1   230 1   36  1   230 1   36  1   231 1   39  1   7   255 213 1   39  1   237 1   39  1   7   255 225 1   26  1   225 1   51  1   7   255 231 1   198 1   230 1   201 1   230 1   201 1   228 1   204 1   228 1   204 1   225 1   
                                           204 1   225 1   204 1   222 1   204 1   222 1   204 1   219 1   201 1   219 1   201 1   219 1   198 1   219 1   198 1   219 1   195 1   219 1   195 1   222 1   193 1   222 1   193 1   225 1   192 1   225 1   192 1   228 1   193 1   228 1   193 1   230 1   
                                           195 1   230 1   195 1   231 1   198 1   7   255 213 1   198 1   237 1   198 1   7   255 225 1   186 1   225 1   211 1   7   255 231 1   119 1   230 1   122 1   230 1   122 1   228 1   124 1   228 1   124 1   225 1   125 1   225 1   125 1   222 1   124 1   
                                           222 1   124 1   219 1   122 1   219 1   122 1   219 1   119 1   219 1   119 1   219 1   115 1   219 1   115 1   222 1   113 1   222 1   113 1   225 1   112 1   225 1   112 1   228 1   113 1   228 1   113 1   230 1   115 1   230 1   115 1   231 1   119 1   
                                           7   255 213 1   119 1   237 1   119 1   7   255 225 1   106 1   225 1   131 1   7   255 72  0   42  1   72  0   53  1   72  0   53  1   82  0   56  1   82  0   56  1   131 0   56  1   131 0   56  1   141 0   53  1   141 0   53  1   141 0   42  1   141 0   
                                           42  1   131 0   39  1   131 0   39  1   82  0   39  1   82  0   39  1   72  0   42  1   7   255 72  0   184 1   72  0   195 1   72  0   195 1   82  0   198 1   82  0   198 1   131 0   198 1   131 0   198 1   141 0   195 1   141 0   195 1   141 0   184 1   
                                           141 0   184 1   131 0   181 1   131 0   181 1   82  0   181 1   82  0   181 1   72  0   184 1   7   255 145 1   39  1   155 3   39  1   155 3   39  1   155 3   87  1   155 3   87  1   87  4   87  1   87  4   87  1   87  4   150 1   87  4   150 1   155 3   
                                           150 1   155 3   150 1   155 3   198 1   155 3   198 1   145 1   198 1   145 1   198 1   145 1   39  1   7   255 145 1   39  1   145 1   39  1   7   255 145 1   39  1   145 1   39  1   7   255 231 1   119 1   230 1   122 1   230 1   122 1   228 1   124 1   
                                           228 1   124 1   225 1   125 1   225 1   125 1   222 1   124 1   222 1   124 1   219 1   122 1   219 1   122 1   218 1   119 1   218 1   119 1   219 1   115 1   219 1   115 1   222 1   113 1   222 1   113 1   225 1   112 1   225 1   112 1   228 1   113 1   
                                           228 1   113 1   230 1   115 1   230 1   115 1   231 1   119 1   7   255 75  4   135 1   70  4   138 1   70  4   138 1   64  4   141 1   64  4   141 1   58  4   141 1   58  4   141 1   53  4   141 1   53  4   141 1   47  4   138 1   47  4   138 1   42  4   
                                           135 1   42  4   135 1   39  4   130 1   39  4   130 1   36  4   124 1   36  4   124 1   36  4   119 1   36  4   119 1   36  4   113 1   36  4   113 1   39  4   107 1   39  4   107 1   42  4   102 1   42  4   102 1   47  4   99  1   47  4   99  1   53  4   
                                           97  1   53  4   97  1   58  4   96  1   58  4   96  1   64  4   97  1   64  4   97  1   70  4   99  1   70  4   99  1   75  4   102 1   7   255 75  4   102 1   75  4   135 1   7   255 153 3   73  1   153 3   84  1   153 3   84  1   163 3   87  1   163 3   
                                           87  1   212 3   87  1   212 3   87  1   222 3   84  1   222 3   84  1   222 3   73  1   222 3   73  1   212 3   70  1   212 3   70  1   163 3   70  1   163 3   70  1   153 3   73  1   7   255 153 3   42  1   153 3   53  1   153 3   53  1   163 3   56  1   
                                           163 3   56  1   212 3   56  1   212 3   56  1   222 3   53  1   222 3   53  1   222 3   42  1   222 3   42  1   212 3   39  1   212 3   39  1   163 3   39  1   163 3   39  1   153 3   42  1   7   255 153 3   153 1   153 3   164 1   153 3   164 1   163 3   
                                           167 1   163 3   167 1   212 3   167 1   212 3   167 1   222 3   164 1   222 3   164 1   222 3   153 1   222 3   153 1   212 3   150 1   212 3   150 1   163 3   150 1   163 3   150 1   153 3   153 1   7   255 153 3   184 1   153 3   195 1   153 3   195 1   
                                           163 3   198 1   163 3   198 1   212 3   198 1   212 3   198 1   222 3   195 1   222 3   195 1   222 3   184 1   222 3   184 1   212 3   181 1   212 3   181 1   163 3   181 1   163 3   181 1   153 3   184 1   7   255 231 3   73  1   231 3   84  1   231 3   
                                           84  1   241 3   87  1   241 3   87  1   34  4   87  1   34  4   87  1   44  4   84  1   44  4   84  1   44  4   73  1   44  4   73  1   34  4   70  1   34  4   70  1   241 3   70  1   241 3   70  1   231 3   73  1   7   255 231 3   42  1   231 3   53  1   
                                           231 3   53  1   241 3   56  1   241 3   56  1   34  4   56  1   34  4   56  1   44  4   53  1   44  4   53  1   44  4   42  1   44  4   42  1   34  4   39  1   34  4   39  1   241 3   39  1   241 3   39  1   231 3   42  1   7   255 231 3   153 1   231 3   
                                           164 1   231 3   164 1   241 3   167 1   241 3   167 1   34  4   167 1   34  4   167 1   44  4   164 1   44  4   164 1   44  4   153 1   44  4   153 1   34  4   150 1   34  4   150 1   241 3   150 1   241 3   150 1   231 3   153 1   7   255 231 3   184 1   
                                           231 3   195 1   231 3   195 1   241 3   198 1   241 3   198 1   34  4   198 1   34  4   198 1   44  4   195 1   44  4   195 1   44  4   184 1   44  4   184 1   34  4   181 1   34  4   181 1   241 3   181 1   241 3   181 1   231 3   184 1   7   255 53  4   
                                           73  1   53  4   84  1   53  4   84  1   63  4   87  1   63  4   87  1   112 4   87  1   112 4   87  1   122 4   84  1   122 4   84  1   122 4   73  1   122 4   73  1   112 4   70  1   112 4   70  1   63  4   70  1   63  4   70  1   53  4   73  1   7   255 
                                           53  4   42  1   53  4   53  1   53  4   53  1   63  4   56  1   63  4   56  1   112 4   56  1   112 4   56  1   122 4   53  1   122 4   53  1   122 4   42  1   122 4   42  1   112 4   39  1   112 4   39  1   63  4   39  1   63  4   39  1   53  4   42  1   
                                           7   255 53  4   153 1   53  4   164 1   53  4   164 1   63  4   167 1   63  4   167 1   112 4   167 1   112 4   167 1   122 4   164 1   122 4   164 1   122 4   153 1   122 4   153 1   112 4   150 1   112 4   150 1   63  4   150 1   63  4   150 1   53  4   
                                           153 1   7   255 53  4   184 1   53  4   195 1   53  4   195 1   63  4   198 1   63  4   198 1   112 4   198 1   112 4   198 1   122 4   195 1   122 4   195 1   122 4   184 1   122 4   184 1   112 4   181 1   112 4   181 1   63  4   181 1   63  4   181 1   
                                           53  4   184 1   7   255 231 1   119 1   230 1   122 1   230 1   122 1   228 1   124 1   228 1   124 1   225 1   125 1   225 1   125 1   222 1   124 1   222 1   124 1   219 1   122 1   219 1   122 1   219 1   119 1   219 1   119 1   219 1   115 1   219 1   
                                           115 1   222 1   113 1   222 1   113 1   225 1   112 1   225 1   112 1   228 1   113 1   228 1   113 1   230 1   115 1   230 1   115 1   231 1   119 1   7   255 213 1   119 1   237 1   119 1   7   255 225 1   106 1   225 1   131 1   7   255 151 1   39  1   
                                           150 1   42  1   150 1   42  1   148 1   44  1   148 1   44  1   145 1   45  1   145 1   45  1   142 1   44  1   142 1   44  1   140 1   42  1   140 1   42  1   139 1   39  1   139 1   39  1   140 1   36  1   140 1   36  1   142 1   33  1   142 1   33  1   
                                           145 1   33  1   145 1   33  1   148 1   33  1   148 1   33  1   150 1   36  1   150 1   36  1   151 1   39  1   7   255 133 1   39  1   157 1   39  1   7   255 145 1   26  1   145 1   51  1   7   255 151 1   198 1   150 1   201 1   150 1   201 1   148 1   
                                           204 1   148 1   204 1   145 1   204 1   145 1   204 1   142 1   204 1   142 1   204 1   140 1   201 1   140 1   201 1   139 1   198 1   139 1   198 1   140 1   195 1   140 1   195 1   142 1   193 1   142 1   193 1   145 1   192 1   145 1   192 1   148 1   
                                           193 1   148 1   193 1   150 1   195 1   150 1   195 1   151 1   198 1   7   255 133 1   198 1   157 1   198 1   7   255 145 1   186 1   145 1   211 1   7   255 15  4   198 1   15  4   201 1   15  4   201 1   12  4   204 1   12  4   204 1   9   4   204 1   
                                           9   4   204 1   6   4   204 1   6   4   204 1   4   4   201 1   4   4   201 1   3   4   198 1   3   4   198 1   4   4   195 1   4   4   195 1   6   4   193 1   6   4   193 1   9   4   192 1   9   4   192 1   12  4   193 1   12  4   193 1   15  4   195 1   
                                           15  4   195 1   15  4   198 1   7   255 253 3   198 1   22  4   198 1   7   255 9   4   186 1   9   4   211 1   7   255 15  4   39  1   15  4   42  1   15  4   42  1   12  4   44  1   12  4   44  1   9   4   45  1   9   4   45  1   6   4   44  1   6   4   
                                           44  1   4   4   42  1   4   4   42  1   3   4   39  1   3   4   39  1   4   4   36  1   4   4   36  1   6   4   33  1   6   4   33  1   9   4   33  1   9   4   33  1   12  4   33  1   12  4   33  1   15  4   36  1   15  4   36  1   15  4   39  1   7   255 
                                           253 3   39  1   22  4   39  1   7   255 9   4   26  1   9   4   51  1   7   255 65  4   119 1   64  4   122 1   64  4   122 1   62  4   124 1   62  4   124 1   58  4   125 1   58  4   125 1   55  4   124 1   55  4   124 1   53  4   122 1   53  4   122 1   
                                           52  4   119 1   52  4   119 1   53  4   115 1   53  4   115 1   55  4   113 1   55  4   113 1   58  4   112 1   58  4   112 1   62  4   113 1   62  4   113 1   64  4   115 1   64  4   115 1   65  4   119 1   7   255 46  4   119 1   71  4   119 1   7   255 
                                           58  4   106 1   58  4   131 1   7   255 235 3   39  1   56  6   39  1   56  6   39  1   56  6   198 1   56  6   198 1   235 3   198 1   235 3   198 1   235 3   39  1   7   255 235 3   39  1   235 3   39  1   7   255 235 3   39  1   235 3   39  1   7   255 
                                           )) "a")
 (_WriteStream FILE (vl-list->string (list 65  4   119 1   64  4   122 1   64  4   122 1   62  4   124 1   62  4   124 1   58  4   125 1   58  4   125 1   55  4   124 1   55  4   124 1   53  4   122 1   53  4   122 1   52  4   119 1   52  4   119 1   53  4   115 1   53  4   115 1   55  4   113 1   
                                           55  4   113 1   58  4   112 1   58  4   112 1   62  4   113 1   62  4   113 1   64  4   115 1   64  4   115 1   65  4   119 1   7   255 159 5   73  1   159 5   84  1   159 5   84  1   169 5   87  1   169 5   87  1   218 5   87  1   218 5   87  1   228 5   
                                           84  1   228 5   84  1   228 5   73  1   228 5   73  1   218 5   70  1   218 5   70  1   169 5   70  1   169 5   70  1   159 5   73  1   7   255 159 5   42  1   159 5   53  1   159 5   53  1   169 5   56  1   169 5   56  1   218 5   56  1   218 5   56  1   
                                           228 5   53  1   228 5   53  1   228 5   42  1   228 5   42  1   218 5   39  1   218 5   39  1   169 5   39  1   169 5   39  1   159 5   42  1   7   255 159 5   153 1   159 5   164 1   159 5   164 1   169 5   167 1   169 5   167 1   218 5   167 1   218 5   
                                           167 1   228 5   164 1   228 5   164 1   228 5   153 1   228 5   153 1   218 5   150 1   218 5   150 1   169 5   150 1   169 5   150 1   159 5   153 1   7   255 159 5   184 1   159 5   195 1   159 5   195 1   169 5   198 1   169 5   198 1   218 5   198 1   
                                           218 5   198 1   228 5   195 1   228 5   195 1   228 5   184 1   228 5   184 1   218 5   181 1   218 5   181 1   169 5   181 1   169 5   181 1   159 5   184 1   7   255 237 5   73  1   237 5   84  1   237 5   84  1   247 5   87  1   247 5   87  1   40  6   
                                           87  1   40  6   87  1   50  6   84  1   50  6   84  1   50  6   73  1   50  6   73  1   40  6   70  1   40  6   70  1   247 5   70  1   247 5   70  1   237 5   73  1   7   255 237 5   42  1   237 5   53  1   237 5   53  1   247 5   56  1   247 5   56  1   
                                           40  6   56  1   40  6   56  1   50  6   53  1   50  6   53  1   50  6   42  1   50  6   42  1   40  6   39  1   40  6   39  1   247 5   39  1   247 5   39  1   237 5   42  1   7   255 237 5   153 1   237 5   164 1   237 5   164 1   247 5   167 1   247 5   
                                           167 1   40  6   167 1   40  6   167 1   50  6   164 1   50  6   164 1   50  6   153 1   50  6   153 1   40  6   150 1   40  6   150 1   247 5   150 1   247 5   150 1   237 5   153 1   7   255 237 5   184 1   237 5   195 1   237 5   195 1   247 5   198 1   
                                           247 5   198 1   40  6   198 1   40  6   198 1   50  6   195 1   50  6   195 1   50  6   184 1   50  6   184 1   40  6   181 1   40  6   181 1   247 5   181 1   247 5   181 1   237 5   184 1   7   255 65  4   119 1   64  4   122 1   64  4   122 1   62  4   
                                           124 1   62  4   124 1   58  4   125 1   58  4   125 1   55  4   124 1   55  4   124 1   53  4   122 1   53  4   122 1   52  4   119 1   52  4   119 1   53  4   115 1   53  4   115 1   55  4   113 1   55  4   113 1   58  4   112 1   58  4   112 1   62  4   
                                           113 1   62  4   113 1   64  4   115 1   64  4   115 1   65  4   119 1   7   255 46  4   119 1   71  4   119 1   7   255 58  4   106 1   58  4   131 1   7   255 241 3   39  1   240 3   42  1   240 3   42  1   238 3   44  1   238 3   44  1   235 3   45  1   
                                           235 3   45  1   232 3   44  1   232 3   44  1   229 3   42  1   229 3   42  1   229 3   39  1   229 3   39  1   229 3   36  1   229 3   36  1   232 3   33  1   232 3   33  1   235 3   33  1   235 3   33  1   238 3   33  1   238 3   33  1   240 3   36  1   
                                           240 3   36  1   241 3   39  1   7   255 222 3   39  1   247 3   39  1   7   255 235 3   26  1   235 3   51  1   7   255 241 3   198 1   240 3   201 1   240 3   201 1   238 3   204 1   238 3   204 1   235 3   204 1   235 3   204 1   232 3   204 1   232 3   
                                           204 1   229 3   201 1   229 3   201 1   229 3   198 1   229 3   198 1   229 3   195 1   229 3   195 1   232 3   193 1   232 3   193 1   235 3   192 1   235 3   192 1   238 3   193 1   238 3   193 1   240 3   195 1   240 3   195 1   241 3   198 1   7   255 
                                           222 3   198 1   247 3   198 1   7   255 235 3   186 1   235 3   211 1   7   255 238 5   198 1   238 5   201 1   238 5   201 1   235 5   204 1   235 5   204 1   232 5   204 1   232 5   204 1   229 5   204 1   229 5   204 1   227 5   201 1   227 5   201 1   
                                           226 5   198 1   226 5   198 1   227 5   195 1   227 5   195 1   229 5   193 1   229 5   193 1   232 5   192 1   232 5   192 1   235 5   193 1   235 5   193 1   238 5   195 1   238 5   195 1   238 5   198 1   7   255 220 5   198 1   245 5   198 1   7   255 
                                           232 5   186 1   232 5   211 1   7   255 238 5   39  1   238 5   42  1   238 5   42  1   235 5   44  1   235 5   44  1   232 5   45  1   232 5   45  1   229 5   44  1   229 5   44  1   227 5   42  1   227 5   42  1   226 5   39  1   226 5   39  1   227 5   
                                           36  1   227 5   36  1   229 5   33  1   229 5   33  1   232 5   33  1   232 5   33  1   235 5   33  1   235 5   33  1   238 5   36  1   238 5   36  1   238 5   39  1   7   255 220 5   39  1   245 5   39  1   7   255 232 5   26  1   232 5   51  1   7   255 
                                           62  6   198 1   61  6   201 1   61  6   201 1   59  6   204 1   59  6   204 1   56  6   204 1   56  6   204 1   53  6   204 1   53  6   204 1   51  6   201 1   51  6   201 1   50  6   198 1   50  6   198 1   51  6   195 1   51  6   195 1   53  6   193 1   
                                           53  6   193 1   56  6   192 1   56  6   192 1   59  6   193 1   59  6   193 1   61  6   195 1   61  6   195 1   62  6   198 1   7   255 44  6   198 1   68  6   198 1   7   255 56  6   186 1   56  6   211 1   7   255 62  6   39  1   61  6   42  1   61  6   
                                           42  1   59  6   44  1   59  6   44  1   56  6   45  1   56  6   45  1   53  6   44  1   53  6   44  1   51  6   42  1   51  6   42  1   50  6   39  1   50  6   39  1   51  6   36  1   51  6   36  1   53  6   33  1   53  6   33  1   56  6   33  1   56  6   
                                           33  1   59  6   33  1   59  6   33  1   61  6   36  1   61  6   36  1   62  6   39  1   7   255 44  6   39  1   68  6   39  1   7   255 56  6   26  1   56  6   51  1   0   252 65  117 116 111 67  65  68  32  83  108 105 100 101 13  10  26  0   86  2   73  
                                           6   247 2   97  120 67  1   2   0   52  18  51  255 51  255 96  0   34  1   131 3   34  1   131 3   34  1   131 3   248 1   131 3   248 1   96  0   248 1   96  0   248 1   96  0   34  1   7   255 7   255 96  0   34  1   131 3   34  1   131 3   34  1   131 
                                           3   248 1   131 3   248 1   96  0   248 1   96  0   248 1   96  0   34  1   7   255 96  0   34  1   96  0   34  1   7   255 96  0   34  1   96  0   34  1   7   255 96  0   34  1   96  0   34  1   7   255 182 2   38  1   182 2   52  1   182 2   52  1   195 
                                           2   56  1   195 2   56  1   3   3   56  1   3   3   56  1   15  3   52  1   15  3   52  1   15  3   38  1   15  3   38  1   3   3   34  1   3   3   34  1   195 2   34  1   195 2   34  1   182 2   38  1   7   255 182 2   230 1   182 2   244 1   182 2   244 
                                           1   195 2   248 1   195 2   248 1   3   3   248 1   3   3   248 1   15  3   244 1   15  3   244 1   15  3   230 1   15  3   230 1   3   3   226 1   3   3   226 1   195 2   226 1   195 2   226 1   182 2   230 1   7   255 99  0   34  1   98  0   36  1   98  
                                           0   36  1   96  0   37  1   96  0   37  1   94  0   36  1   94  0   36  1   94  0   34  1   94  0   34  1   94  0   32  1   94  0   32  1   96  0   31  1   96  0   31  1   98  0   32  1   98  0   32  1   99  0   34  1   7   255 91  0   34  1   102 0   34  
                                           1   7   255 96  0   29  1   96  0   40  1   7   255 206 0   34  1   205 0   36  1   205 0   36  1   203 0   37  1   203 0   37  1   201 0   36  1   201 0   36  1   201 0   34  1   201 0   34  1   201 0   32  1   201 0   32  1   203 0   31  1   203 0   31  
                                           1   205 0   32  1   205 0   32  1   206 0   34  1   7   255 198 0   34  1   209 0   34  1   7   255 203 0   29  1   203 0   40  1   7   255 229 2   34  1   229 2   36  1   229 2   36  1   227 2   37  1   227 2   37  1   225 2   36  1   225 2   36  1   224 
                                           2   34  1   224 2   34  1   225 2   32  1   225 2   32  1   227 2   31  1   227 2   31  1   229 2   32  1   229 2   32  1   229 2   34  1   7   255 221 2   34  1   232 2   34  1   7   255 227 2   29  1   227 2   40  1   7   255 134 3   34  1   133 3   36  
                                           1   133 3   36  1   131 3   37  1   131 3   37  1   129 3   36  1   129 3   36  1   129 3   34  1   129 3   34  1   129 3   32  1   129 3   32  1   131 3   31  1   131 3   31  1   133 3   32  1   133 3   32  1   134 3   34  1   7   255 126 3   34  1   137 
                                           3   34  1   7   255 131 3   29  1   131 3   40  1   7   255 134 3   248 1   133 3   250 1   133 3   250 1   131 3   251 1   131 3   251 1   129 3   250 1   129 3   250 1   129 3   248 1   129 3   248 1   129 3   246 1   129 3   246 1   131 3   245 1   131 
                                           3   245 1   133 3   246 1   133 3   246 1   134 3   248 1   7   255 126 3   248 1   137 3   248 1   7   255 131 3   243 1   131 3   254 1   7   255 229 2   248 1   229 2   250 1   229 2   250 1   227 2   251 1   227 2   251 1   225 2   250 1   225 2   250 
                                           1   224 2   248 1   224 2   248 1   225 2   246 1   225 2   246 1   227 2   245 1   227 2   245 1   229 2   246 1   229 2   246 1   229 2   248 1   7   255 221 2   248 1   232 2   248 1   7   255 227 2   243 1   227 2   254 1   7   255 206 0   248 1   205 
                                           0   250 1   205 0   250 1   203 0   251 1   203 0   251 1   201 0   250 1   201 0   250 1   201 0   248 1   201 0   248 1   201 0   246 1   201 0   246 1   203 0   245 1   203 0   245 1   205 0   246 1   205 0   246 1   206 0   248 1   7   255 198 0   248 
                                           1   209 0   248 1   7   255 203 0   243 1   203 0   254 1   7   255 99  0   248 1   98  0   250 1   98  0   250 1   96  0   251 1   96  0   251 1   94  0   250 1   94  0   250 1   94  0   248 1   94  0   248 1   94  0   246 1   94  0   246 1   96  0   245 
                                           1   96  0   245 1   98  0   246 1   98  0   246 1   99  0   248 1   7   255 91  0   248 1   102 0   248 1   7   255 96  0   243 1   96  0   254 1   7   255 206 0   141 1   205 0   143 1   205 0   143 1   203 0   144 1   203 0   144 1   201 0   143 1   201 
                                           0   143 1   201 0   141 1   201 0   141 1   201 0   139 1   201 0   139 1   203 0   138 1   203 0   138 1   205 0   139 1   205 0   139 1   206 0   141 1   7   255 198 0   141 1   209 0   141 1   7   255 203 0   136 1   203 0   147 1   7   255 134 3   141 
                                           1   133 3   143 1   133 3   143 1   131 3   144 1   131 3   144 1   129 3   143 1   129 3   143 1   128 3   141 1   128 3   141 1   129 3   139 1   129 3   139 1   131 3   138 1   131 3   138 1   133 3   139 1   133 3   139 1   134 3   141 1   7   255 126 
                                           3   141 1   136 3   141 1   7   255 131 3   136 1   131 3   147 1   7   255 159 0   230 1   159 0   244 1   159 0   244 1   171 0   248 1   171 0   248 1   236 0   248 1   236 0   248 1   248 0   244 1   248 0   244 1   248 0   230 1   248 0   230 1   236 
                                           0   226 1   236 0   226 1   171 0   226 1   171 0   226 1   159 0   230 1   7   255 159 0   38  1   159 0   52  1   159 0   52  1   171 0   56  1   171 0   56  1   236 0   56  1   236 0   56  1   248 0   52  1   248 0   52  1   248 0   38  1   248 0   38  
                                           1   236 0   34  1   236 0   34  1   171 0   34  1   171 0   34  1   159 0   38  1   51  255 51  255 131 3   141 1   211 3   248 1   211 3   248 1   235 5   248 1   235 5   248 1   235 5   34  1   235 5   34  1   211 3   34  1   211 3   34  1   131 3   141 
                                           1   7   255 7   255 211 3   34  1   235 5   34  1   235 5   34  1   235 5   248 1   235 5   248 1   211 3   248 1   211 3   248 1   211 3   34  1   7   255 211 3   34  1   211 3   34  1   7   255 211 3   34  1   211 3   34  1   7   255 211 3   34  1   211 
                                           3   34  1   7   255 131 3   141 1   211 3   141 1   7   255 145 3   141 1   144 3   146 1   144 3   146 1   142 3   150 1   142 3   150 1   139 3   153 1   139 3   153 1   135 3   155 1   135 3   155 1   131 3   155 1   131 3   155 1   126 3   155 1   126 
                                           3   155 1   122 3   153 1   122 3   153 1   119 3   150 1   119 3   150 1   117 3   146 1   117 3   146 1   117 3   141 1   117 3   141 1   117 3   137 1   117 3   137 1   119 3   133 1   119 3   133 1   122 3   130 1   122 3   130 1   126 3   128 1   126 
                                           3   128 1   131 3   127 1   131 3   127 1   135 3   128 1   135 3   128 1   139 3   130 1   139 3   130 1   142 3   133 1   142 3   133 1   144 3   137 1   144 3   137 1   145 3   141 1   7   255 249 4   37  1   249 4   45  1   249 4   45  1   0   5   48  
                                           1   0   5   48  1   40  5   48  1   40  5   48  1   48  5   45  1   48  5   45  1   48  5   37  1   48  5   37  1   40  5   34  1   40  5   34  1   0   5   34  1   0   5   34  1   249 4   37  1   7   255 249 4   237 1   249 4   246 1   249 4   246 1   0   
                                           5   248 1   0   5   248 1   40  5   248 1   40  5   248 1   48  5   246 1   48  5   246 1   48  5   237 1   48  5   237 1   40  5   234 1   40  5   234 1   0   5   234 1   0   5   234 1   249 4   237 1   7   255 214 3   34  1   213 3   36  1   213 3   36  
                                           1   211 3   37  1   211 3   37  1   209 3   36  1   209 3   36  1   209 3   34  1   209 3   34  1   209 3   32  1   209 3   32  1   211 3   31  1   211 3   31  1   213 3   32  1   213 3   32  1   214 3   34  1   7   255 206 3   34  1   217 3   34  1   7   
                                           255 211 3   29  1   211 3   40  1   7   255 23  5   34  1   22  5   36  1   22  5   36  1   20  5   37  1   20  5   37  1   19  5   36  1   19  5   36  1   18  5   34  1   18  5   34  1   19  5   32  1   19  5   32  1   20  5   31  1   20  5   31  1   22  
                                           5   32  1   22  5   32  1   23  5   34  1   7   255 15  5   34  1   26  5   34  1   7   255 20  5   29  1   20  5   40  1   7   255 23  5   248 1   22  5   250 1   22  5   250 1   20  5   251 1   20  5   251 1   19  5   250 1   19  5   250 1   18  5   248 
                                           1   18  5   248 1   19  5   246 1   19  5   246 1   20  5   245 1   20  5   245 1   22  5   246 1   22  5   246 1   23  5   248 1   7   255 15  5   248 1   26  5   248 1   7   255 20  5   243 1   20  5   254 1   7   255 237 5   248 1   236 5   250 1   236 
                                           5   250 1   235 5   251 1   235 5   251 1   233 5   250 1   233 5   250 1   232 5   248 1   232 5   248 1   233 5   246 1   233 5   246 1   235 5   245 1   235 5   245 1   236 5   246 1   236 5   246 1   237 5   248 1   7   255 229 5   248 1   240 5   248 
                                           1   7   255 235 5   243 1   235 5   254 1   7   255 237 5   34  1   236 5   36  1   236 5   36  1   235 5   37  1   235 5   37  1   233 5   36  1   233 5   36  1   232 5   34  1   232 5   34  1   233 5   32  1   233 5   32  1   235 5   31  1   235 5   31  
                                           1   236 5   32  1   236 5   32  1   237 5   34  1   7   255 229 5   34  1   240 5   34  1   7   255 235 5   29  1   235 5   40  1   7   255 214 3   248 1   213 3   250 1   213 3   250 1   211 3   251 1   211 3   251 1   209 3   250 1   209 3   250 1   209 
                                           3   248 1   209 3   248 1   209 3   246 1   209 3   246 1   211 3   245 1   211 3   245 1   213 3   246 1   213 3   246 1   214 3   248 1   7   255 206 3   248 1   217 3   248 1   7   255 211 3   243 1   211 3   254 1   7   255 134 3   141 1   133 3   143 
                                           1   133 3   143 1   131 3   144 1   131 3   144 1   129 3   143 1   129 3   143 1   128 3   141 1   128 3   141 1   129 3   139 1   129 3   139 1   131 3   138 1   131 3   138 1   133 3   139 1   133 3   139 1   134 3   141 1   7   255 126 3   141 1   136 
                                           3   141 1   7   255 131 3   136 1   131 3   147 1   0   252 65  117 116 111 67  65  68  32  83  108 105 100 101 13  10  26  0   86  2   73  6   31  3   200 70  51  1   2   0   52  18  7   255 7   255 38  0   236 1   37  0   239 1   37  0   239 1   34  0   
                                           242 1   34  0   242 1   31  0   243 1   31  0   243 1   28  0   242 1   28  0   242 1   25  0   239 1   25  0   239 1   24  0   236 1   24  0   236 1   25  0   233 1   25  0   233 1   28  0   230 1   28  0   230 1   31  0   229 1   31  0   229 1   34  0   
                                           230 1   34  0   230 1   37  0   233 1   37  0   233 1   38  0   236 1   7   255 18  0   236 1   45  0   236 1   7   255 31  0   223 1   31  0   250 1   7   255 38  0   60  1   37  0   64  1   37  0   64  1   34  0   66  1   34  0   66  1   31  0   67  1   
                                           31  0   67  1   28  0   66  1   28  0   66  1   25  0   64  1   25  0   64  1   24  0   60  1   24  0   60  1   25  0   57  1   25  0   57  1   28  0   54  1   28  0   54  1   31  0   54  1   31  0   54  1   34  0   54  1   34  0   54  1   37  0   57  1   
                                           37  0   57  1   38  0   60  1   7   255 18  0   60  1   45  0   60  1   7   255 31  0   47  1   31  0   74  1   7   255 255 1   60  1   254 1   64  1   254 1   64  1   252 1   66  1   252 1   66  1   248 1   67  1   248 1   67  1   245 1   66  1   245 1   
                                           66  1   243 1   64  1   243 1   64  1   242 1   60  1   242 1   60  1   243 1   57  1   243 1   57  1   245 1   54  1   245 1   54  1   248 1   54  1   248 1   54  1   252 1   54  1   252 1   54  1   254 1   57  1   254 1   57  1   255 1   60  1   7   255 
                                           )) "a")
 (_WriteStream FILE (vl-list->string (list 235 1   60  1   6   2   60  1   7   255 248 1   47  1   248 1   74  1   7   255 255 1   236 1   254 1   239 1   254 1   239 1   252 1   242 1   252 1   242 1   248 1   243 1   248 1   243 1   245 1   242 1   245 1   242 1   243 1   239 1   243 1   239 1   
                                           242 1   236 1   242 1   236 1   243 1   233 1   243 1   233 1   245 1   230 1   245 1   230 1   248 1   229 1   248 1   229 1   252 1   230 1   252 1   230 1   254 1   233 1   254 1   233 1   255 1   236 1   7   255 235 1   236 1   6   2   236 1   7   255 
                                           248 1   223 1   248 1   250 1   7   255 112 0   60  1   111 0   64  1   111 0   64  1   109 0   66  1   109 0   66  1   105 0   67  1   105 0   67  1   102 0   66  1   102 0   66  1   100 0   64  1   100 0   64  1   99  0   60  1   99  0   60  1   100 0   
                                           57  1   100 0   57  1   102 0   54  1   102 0   54  1   105 0   54  1   105 0   54  1   109 0   54  1   109 0   54  1   111 0   57  1   111 0   57  1   112 0   60  1   7   255 92  0   60  1   119 0   60  1   7   255 105 0   47  1   105 0   74  1   7   255 
                                           112 0   236 1   111 0   239 1   111 0   239 1   109 0   242 1   109 0   242 1   105 0   243 1   105 0   243 1   102 0   242 1   102 0   242 1   100 0   239 1   100 0   239 1   99  0   236 1   99  0   236 1   100 0   233 1   100 0   233 1   102 0   230 1   
                                           102 0   230 1   105 0   229 1   105 0   229 1   109 0   230 1   109 0   230 1   111 0   233 1   111 0   233 1   112 0   236 1   7   255 92  0   236 1   119 0   236 1   7   255 105 0   223 1   105 0   250 1   7   255 112 0   148 1   111 0   152 1   111 0   
                                           152 1   109 0   154 1   109 0   154 1   105 0   155 1   105 0   155 1   102 0   154 1   102 0   154 1   100 0   152 1   100 0   152 1   99  0   148 1   99  0   148 1   100 0   145 1   100 0   145 1   102 0   142 1   102 0   142 1   105 0   141 1   105 0   
                                           141 1   109 0   142 1   109 0   142 1   111 0   145 1   111 0   145 1   112 0   148 1   7   255 92  0   148 1   119 0   148 1   7   255 105 0   135 1   105 0   162 1   7   255 68  0   64  1   68  0   76  1   68  0   76  1   78  0   79  1   78  0   79  1   
                                           133 0   79  1   133 0   79  1   143 0   76  1   143 0   76  1   143 0   64  1   143 0   64  1   133 0   60  1   133 0   60  1   78  0   60  1   78  0   60  1   68  0   64  1   7   255 68  0   221 1   68  0   233 1   68  0   233 1   78  0   236 1   78  0   
                                           236 1   133 0   236 1   133 0   236 1   143 0   233 1   143 0   233 1   143 0   221 1   143 0   221 1   133 0   217 1   133 0   217 1   78  0   217 1   78  0   217 1   68  0   221 1   7   255 211 1   221 1   211 1   233 1   211 1   233 1   221 1   236 1   
                                           221 1   236 1   20  2   236 1   20  2   236 1   30  2   233 1   30  2   233 1   30  2   221 1   30  2   221 1   20  2   217 1   20  2   217 1   221 1   217 1   221 1   217 1   211 1   221 1   7   255 211 1   187 1   211 1   199 1   211 1   199 1   221 1   
                                           202 1   221 1   202 1   20  2   202 1   20  2   202 1   30  2   199 1   30  2   199 1   30  2   187 1   30  2   187 1   20  2   183 1   20  2   183 1   221 1   183 1   221 1   183 1   211 1   187 1   7   255 211 1   98  1   211 1   110 1   211 1   110 1   
                                           221 1   113 1   221 1   113 1   20  2   113 1   20  2   113 1   30  2   110 1   30  2   110 1   30  2   98  1   30  2   98  1   20  2   94  1   20  2   94  1   221 1   94  1   221 1   94  1   211 1   98  1   7   255 211 1   64  1   211 1   76  1   211 1   
                                           76  1   221 1   79  1   221 1   79  1   20  2   79  1   20  2   79  1   30  2   76  1   30  2   76  1   30  2   64  1   30  2   64  1   20  2   60  1   20  2   60  1   221 1   60  1   221 1   60  1   211 1   64  1   7   255 31  0   60  1   192 0   60  1   
                                           192 0   60  1   192 0   113 1   192 0   113 1   114 2   113 1   114 2   113 1   114 2   183 1   114 2   183 1   192 0   183 1   192 0   183 1   192 0   236 1   192 0   236 1   31  0   236 1   31  0   236 1   31  0   60  1   7   255 31  0   60  1   31  0   
                                           60  1   7   255 31  0   60  1   31  0   60  1   7   255 169 0   159 1   172 0   160 1   172 0   160 1   177 0   165 1   177 0   165 1   177 0   131 1   7   255 234 1   148 1   233 1   152 1   233 1   152 1   230 1   154 1   230 1   154 1   227 1   155 1   
                                           227 1   155 1   223 1   154 1   223 1   154 1   221 1   152 1   221 1   152 1   220 1   148 1   220 1   148 1   221 1   145 1   221 1   145 1   223 1   142 1   223 1   142 1   227 1   141 1   227 1   141 1   230 1   142 1   230 1   142 1   233 1   145 1   
                                           233 1   145 1   234 1   148 1   7   255 213 1   148 1   240 1   148 1   7   255 227 1   135 1   227 1   162 1   7   255 239 1   148 1   238 1   153 1   238 1   153 1   235 1   156 1   235 1   156 1   231 1   159 1   231 1   159 1   227 1   160 1   227 1   
                                           160 1   222 1   159 1   222 1   159 1   219 1   156 1   219 1   156 1   216 1   153 1   216 1   153 1   215 1   148 1   215 1   148 1   216 1   144 1   216 1   144 1   219 1   140 1   219 1   140 1   222 1   137 1   222 1   137 1   227 1   136 1   227 1   
                                           136 1   231 1   137 1   231 1   137 1   235 1   140 1   235 1   140 1   238 1   144 1   238 1   144 1   239 1   148 1   7   255 166 5   60  1   165 5   64  1   165 5   64  1   163 5   66  1   163 5   66  1   159 5   67  1   159 5   67  1   156 5   66  1   
                                           156 5   66  1   153 5   64  1   153 5   64  1   152 5   60  1   152 5   60  1   153 5   57  1   153 5   57  1   156 5   54  1   156 5   54  1   159 5   54  1   159 5   54  1   163 5   54  1   163 5   54  1   165 5   57  1   165 5   57  1   166 5   60  1   
                                           7   255 146 5   60  1   173 5   60  1   7   255 159 5   47  1   159 5   74  1   7   255 166 5   236 1   165 5   239 1   165 5   239 1   163 5   242 1   163 5   242 1   159 5   243 1   159 5   243 1   156 5   242 1   156 5   242 1   153 5   239 1   153 5   
                                           239 1   152 5   236 1   152 5   236 1   153 5   233 1   153 5   233 1   156 5   230 1   156 5   230 1   159 5   229 1   159 5   229 1   163 5   230 1   163 5   230 1   165 5   233 1   165 5   233 1   166 5   236 1   7   255 146 5   236 1   173 5   236 1   
                                           7   255 159 5   223 1   159 5   250 1   7   255 20  4   148 1   19  4   152 1   19  4   152 1   16  4   154 1   16  4   154 1   13  4   155 1   13  4   155 1   9   4   154 1   9   4   154 1   7   4   152 1   7   4   152 1   6   4   148 1   6   4   148 1   
                                           7   4   145 1   7   4   145 1   9   4   142 1   9   4   142 1   13  4   141 1   13  4   141 1   16  4   142 1   16  4   142 1   19  4   145 1   19  4   145 1   20  4   148 1   7   255 255 3   148 1   26  4   148 1   7   255 13  4   135 1   13  4   162 1   
                                           7   255 173 5   148 1   171 5   153 1   171 5   153 1   168 5   157 1   168 5   157 1   163 5   158 1   163 5   158 1   157 5   157 1   157 5   157 1   154 5   153 1   154 5   153 1   152 5   148 1   152 5   148 1   154 5   143 1   154 5   143 1   157 5   
                                           139 1   157 5   139 1   163 5   138 1   163 5   138 1   168 5   139 1   168 5   139 1   171 5   143 1   171 5   143 1   173 5   148 1   1   255 1   255 169 5   148 1   168 5   152 1   168 5   152 1   166 5   154 1   166 5   154 1   163 5   155 1   163 5   
                                           155 1   159 5   154 1   159 5   154 1   157 5   152 1   157 5   152 1   156 5   148 1   156 5   148 1   157 5   145 1   157 5   145 1   159 5   142 1   159 5   142 1   163 5   141 1   163 5   141 1   166 5   142 1   166 5   142 1   168 5   145 1   168 5   
                                           145 1   169 5   148 1   1   255 149 5   148 1   176 5   148 1   1   255 163 5   135 1   163 5   162 1   7   255 7   255 121 5   187 1   121 5   199 1   121 5   199 1   132 5   202 1   132 5   202 1   186 5   202 1   186 5   202 1   197 5   199 1   197 5   
                                           199 1   197 5   187 1   197 5   187 1   186 5   183 1   186 5   183 1   132 5   183 1   132 5   183 1   121 5   187 1   7   255 121 5   98  1   121 5   110 1   121 5   110 1   132 5   113 1   132 5   113 1   186 5   113 1   186 5   113 1   197 5   110 1   
                                           197 5   110 1   197 5   98  1   197 5   98  1   186 5   94  1   186 5   94  1   132 5   94  1   132 5   94  1   121 5   98  1   7   255 121 5   64  1   121 5   76  1   121 5   76  1   132 5   79  1   132 5   79  1   186 5   79  1   186 5   79  1   197 5   
                                           76  1   197 5   76  1   197 5   64  1   197 5   64  1   186 5   60  1   186 5   60  1   132 5   60  1   132 5   60  1   121 5   64  1   7   255 121 5   221 1   121 5   233 1   121 5   233 1   132 5   236 1   132 5   236 1   186 5   236 1   186 5   236 1   
                                           197 5   233 1   197 5   233 1   197 5   221 1   197 5   221 1   186 5   217 1   186 5   217 1   132 5   217 1   132 5   217 1   121 5   221 1   7   255 20  4   148 1   19  4   152 1   19  4   152 1   16  4   154 1   16  4   154 1   13  4   155 1   13  4   
                                           155 1   9   4   154 1   9   4   154 1   7   4   152 1   7   4   152 1   6   4   148 1   6   4   148 1   7   4   145 1   7   4   145 1   9   4   142 1   9   4   142 1   13  4   141 1   13  4   141 1   16  4   142 1   16  4   142 1   19  4   145 1   19  4   
                                           145 1   20  4   148 1   7   255 13  4   114 1   28  6   114 1   28  6   114 1   28  6   182 1   28  6   182 1   13  4   182 1   13  4   182 1   13  4   114 1   7   255 13  4   114 1   13  4   114 1   7   255 13  4   114 1   13  4   114 1   7   255 72  4   
                                           165 1   90  4   165 1   90  4   165 1   80  4   152 1   80  4   152 1   85  4   152 1   85  4   152 1   88  4   151 1   88  4   151 1   90  4   149 1   90  4   149 1   92  4   144 1   92  4   144 1   92  4   141 1   92  4   141 1   90  4   136 1   90  4   
                                           136 1   87  4   133 1   87  4   133 1   82  4   131 1   82  4   131 1   77  4   131 1   77  4   131 1   72  4   133 1   72  4   133 1   71  4   135 1   71  4   135 1   69  4   138 1   7   255 35  6   236 1   34  6   239 1   34  6   239 1   32  6   242 1   
                                           32  6   242 1   28  6   243 1   28  6   243 1   25  6   242 1   25  6   242 1   22  6   239 1   22  6   239 1   22  6   236 1   22  6   236 1   22  6   233 1   22  6   233 1   25  6   230 1   25  6   230 1   28  6   229 1   28  6   229 1   32  6   230 1   
                                           32  6   230 1   34  6   233 1   34  6   233 1   35  6   236 1   7   255 15  6   236 1   42  6   236 1   7   255 28  6   223 1   28  6   250 1   7   255 35  6   60  1   34  6   64  1   34  6   64  1   32  6   66  1   32  6   66  1   28  6   67  1   28  6   
                                           67  1   25  6   66  1   25  6   66  1   22  6   64  1   22  6   64  1   22  6   60  1   22  6   60  1   22  6   57  1   22  6   57  1   25  6   54  1   25  6   54  1   28  6   54  1   28  6   54  1   32  6   54  1   32  6   54  1   34  6   57  1   34  6   
                                           57  1   35  6   60  1   7   255 15  6   60  1   42  6   60  1   7   255 28  6   47  1   28  6   74  1   7   255 179 1   60  1   178 1   64  1   178 1   64  1   175 1   66  1   175 1   66  1   172 1   67  1   172 1   67  1   169 1   66  1   169 1   66  1   
                                           166 1   64  1   166 1   64  1   165 1   60  1   165 1   60  1   166 1   57  1   166 1   57  1   169 1   54  1   169 1   54  1   172 1   54  1   172 1   54  1   175 1   54  1   175 1   54  1   178 1   57  1   178 1   57  1   179 1   60  1   7   255 159 1   
                                           60  1   186 1   60  1   7   255 172 1   47  1   172 1   74  1   7   255 179 1   236 1   178 1   239 1   178 1   239 1   175 1   242 1   175 1   242 1   172 1   243 1   172 1   243 1   169 1   242 1   169 1   242 1   166 1   239 1   166 1   239 1   165 1   
                                           236 1   165 1   236 1   166 1   233 1   166 1   233 1   169 1   230 1   169 1   230 1   172 1   229 1   172 1   229 1   175 1   230 1   175 1   230 1   178 1   233 1   178 1   233 1   179 1   236 1   7   255 159 1   236 1   186 1   236 1   7   255 172 1   
                                           223 1   172 1   250 1   3   255 3   255 169 5   148 1   168 5   152 1   168 5   152 1   166 5   154 1   166 5   154 1   163 5   155 1   163 5   155 1   159 5   154 1   159 5   154 1   157 5   152 1   157 5   152 1   156 5   148 1   156 5   148 1   157 5   
                                           145 1   157 5   145 1   159 5   142 1   159 5   142 1   163 5   141 1   163 5   141 1   166 5   142 1   166 5   142 1   168 5   145 1   168 5   145 1   169 5   148 1   3   255 149 5   148 1   176 5   148 1   3   255 163 5   135 1   163 5   162 1   3   255 
                                           207 2   148 1   206 2   152 1   206 2   152 1   203 2   154 1   203 2   154 1   200 2   155 1   200 2   155 1   197 2   154 1   197 2   154 1   194 2   152 1   194 2   152 1   193 2   148 1   193 2   148 1   194 2   145 1   194 2   145 1   197 2   142 1   
                                           197 2   142 1   200 2   141 1   200 2   141 1   203 2   142 1   203 2   142 1   206 2   145 1   206 2   145 1   207 2   148 1   3   255 187 2   148 1   214 2   148 1   3   255 200 2   135 1   200 2   162 1   7   255 7   255 210 2   148 1   209 2   153 1   
                                           209 2   153 1   205 2   157 1   205 2   157 1   200 2   158 1   200 2   158 1   195 2   157 1   195 2   157 1   191 2   153 1   191 2   153 1   190 2   148 1   190 2   148 1   191 2   143 1   191 2   143 1   195 2   139 1   195 2   139 1   200 2   138 1   
                                           200 2   138 1   205 2   139 1   205 2   139 1   209 2   143 1   209 2   143 1   210 2   148 1   7   255 172 1   60  1   28  6   60  1   28  6   60  1   28  6   236 1   28  6   236 1   172 1   236 1   172 1   236 1   172 1   60  1   7   255 172 1   60  1   
                                           172 1   60  1   7   255 173 5   148 1   171 5   153 1   171 5   153 1   168 5   157 1   168 5   157 1   163 5   158 1   163 5   158 1   157 5   157 1   157 5   157 1   154 5   153 1   154 5   153 1   152 5   148 1   152 5   148 1   154 5   143 1   154 5   
                                           143 1   157 5   139 1   157 5   139 1   163 5   138 1   163 5   138 1   168 5   139 1   168 5   139 1   171 5   143 1   171 5   143 1   173 5   148 1   7   255 16  3   165 1   0   3   143 1   0   3   143 1   24  3   143 1   7   255 16  3   165 1   16  3   
                                           131 1   1   255 1   255 207 2   148 1   206 2   152 1   206 2   152 1   203 2   154 1   203 2   154 1   200 2   155 1   200 2   155 1   197 2   154 1   197 2   154 1   194 2   152 1   194 2   152 1   193 2   148 1   193 2   148 1   194 2   145 1   194 2   
                                           145 1   197 2   142 1   197 2   142 1   200 2   141 1   200 2   141 1   203 2   142 1   203 2   142 1   206 2   145 1   206 2   145 1   207 2   148 1   1   255 187 2   148 1   214 2   148 1   1   255 200 2   135 1   200 2   162 1   7   255 7   255 210 2   
                                           148 1   209 2   153 1   209 2   153 1   205 2   157 1   205 2   157 1   200 2   158 1   200 2   158 1   195 2   157 1   195 2   157 1   191 2   153 1   191 2   153 1   190 2   148 1   190 2   148 1   191 2   143 1   191 2   143 1   195 2   139 1   195 2   
                                           139 1   200 2   138 1   200 2   138 1   205 2   139 1   205 2   139 1   209 2   143 1   209 2   143 1   210 2   148 1   7   255 167 3   60  1   166 3   64  1   166 3   64  1   164 3   66  1   164 3   66  1   161 3   67  1   161 3   67  1   157 3   66  1   
                                           157 3   66  1   155 3   64  1   155 3   64  1   154 3   60  1   154 3   60  1   155 3   57  1   155 3   57  1   157 3   54  1   157 3   54  1   161 3   54  1   161 3   54  1   164 3   54  1   164 3   54  1   166 3   57  1   166 3   57  1   167 3   60  1   
                                           7   255 147 3   60  1   174 3   60  1   7   255 161 3   47  1   161 3   74  1   7   255 167 3   236 1   166 3   239 1   166 3   239 1   164 3   242 1   164 3   242 1   161 3   243 1   161 3   243 1   157 3   242 1   157 3   242 1   155 3   239 1   155 3   
                                           239 1   154 3   236 1   154 3   236 1   155 3   233 1   155 3   233 1   157 3   230 1   157 3   230 1   161 3   229 1   161 3   229 1   164 3   230 1   164 3   230 1   166 3   233 1   166 3   233 1   167 3   236 1   7   255 147 3   236 1   174 3   236 1   
                                           7   255 161 3   223 1   161 3   250 1   7   255 234 1   148 1   233 1   152 1   233 1   152 1   230 1   154 1   230 1   154 1   227 1   155 1   227 1   155 1   223 1   154 1   223 1   154 1   221 1   152 1   221 1   152 1   220 1   148 1   220 1   148 1   
                                           221 1   145 1   221 1   145 1   223 1   142 1   223 1   142 1   227 1   141 1   227 1   141 1   230 1   142 1   230 1   142 1   233 1   145 1   233 1   145 1   234 1   148 1   7   255 213 1   148 1   240 1   148 1   7   255 227 1   135 1   227 1   162 1   
                                           7   255 20  4   148 1   19  4   152 1   19  4   152 1   16  4   154 1   16  4   154 1   13  4   155 1   13  4   155 1   9   4   154 1   9   4   154 1   7   4   152 1   7   4   152 1   6   4   148 1   6   4   148 1   7   4   145 1   7   4   145 1   9   4   
                                           142 1   9   4   142 1   13  4   141 1   13  4   141 1   16  4   142 1   16  4   142 1   19  4   145 1   19  4   145 1   20  4   148 1   7   255 255 3   148 1   26  4   148 1   7   255 13  4   135 1   13  4   162 1   7   255 24  4   148 1   24  4   153 1   
                                           24  4   153 1   21  4   156 1   21  4   156 1   17  4   159 1   17  4   159 1   13  4   160 1   13  4   160 1   8   4   159 1   8   4   159 1   4   4   156 1   4   4   156 1   2   4   153 1   2   4   153 1   1   4   148 1   1   4   148 1   2   4   144 1   
                                           )) "a")
 (_WriteStream FILE (vl-list->string (list 2   4   144 1   4   4   140 1   4   4   140 1   8   4   137 1   8   4   137 1   13  4   136 1   13  4   136 1   17  4   137 1   17  4   137 1   21  4   140 1   21  4   140 1   24  4   144 1   24  4   144 1   24  4   148 1   7   255 123 3   221 1   123 3   
                                           233 1   123 3   233 1   133 3   236 1   133 3   236 1   188 3   236 1   188 3   236 1   198 3   233 1   198 3   233 1   198 3   221 1   198 3   221 1   188 3   217 1   188 3   217 1   133 3   217 1   133 3   217 1   123 3   221 1   7   255 123 3   187 1   
                                           123 3   199 1   123 3   199 1   133 3   202 1   133 3   202 1   188 3   202 1   188 3   202 1   198 3   199 1   198 3   199 1   198 3   187 1   198 3   187 1   188 3   183 1   188 3   183 1   133 3   183 1   133 3   183 1   123 3   187 1   7   255 123 3   
                                           98  1   123 3   110 1   123 3   110 1   133 3   113 1   133 3   113 1   188 3   113 1   188 3   113 1   198 3   110 1   198 3   110 1   198 3   98  1   198 3   98  1   188 3   94  1   188 3   94  1   133 3   94  1   133 3   94  1   123 3   98  1   7   255 
                                           123 3   64  1   123 3   76  1   123 3   76  1   133 3   79  1   133 3   79  1   188 3   79  1   188 3   79  1   198 3   76  1   198 3   76  1   198 3   64  1   198 3   64  1   188 3   60  1   188 3   60  1   133 3   60  1   133 3   60  1   123 3   64  1   
                                           7   255 234 1   148 1   233 1   152 1   233 1   152 1   230 1   154 1   230 1   154 1   227 1   155 1   227 1   155 1   223 1   154 1   223 1   154 1   221 1   152 1   221 1   152 1   220 1   148 1   220 1   148 1   221 1   145 1   221 1   145 1   223 1   
                                           142 1   223 1   142 1   227 1   141 1   227 1   141 1   230 1   142 1   230 1   142 1   233 1   145 1   233 1   145 1   234 1   148 1   7   255 179 1   114 1   13  4   114 1   13  4   114 1   13  4   182 1   13  4   182 1   179 1   182 1   179 1   182 1   
                                           179 1   114 1   7   255 179 1   114 1   179 1   114 1   7   255 179 1   114 1   179 1   114 1   7   255 29  2   157 1   29  2   159 1   29  2   159 1   30  2   162 1   30  2   162 1   32  2   163 1   32  2   163 1   35  2   165 1   35  2   165 1   42  2   
                                           165 1   42  2   165 1   45  2   163 1   45  2   163 1   47  2   162 1   47  2   162 1   48  2   159 1   48  2   159 1   48  2   155 1   48  2   155 1   47  2   152 1   47  2   152 1   43  2   147 1   43  2   147 1   27  2   131 1   27  2   131 1   50  2   
                                           131 1   0   252 65  117 116 111 67  65  68  32  83  108 105 100 101 13  10  26  0   86  2   106 6   234 2   99  219 79  1   2   0   52  18  51  255 51  255 48  0   207 0   61  6   207 0   61  6   207 0   61  6   27  2   61  6   27  2   48  0   27  2   48  
                                           0   27  2   48  0   207 0   7   255 7   255 48  0   207 0   61  6   207 0   61  6   207 0   61  6   27  2   61  6   27  2   48  0   27  2   48  0   27  2   48  0   207 0   7   255 48  0   207 0   48  0   207 0   7   255 48  0   207 0   48  0   207 0   7   
                                           255 162 4   213 0   162 4   233 0   162 4   233 0   180 4   239 0   180 4   239 0   18  5   239 0   18  5   239 0   36  5   233 0   36  5   233 0   36  5   213 0   36  5   213 0   18  5   207 0   18  5   207 0   180 4   207 0   180 4   207 0   162 4   213 
                                           0   7   255 162 4   1   2   162 4   21  2   162 4   21  2   180 4   27  2   180 4   27  2   18  5   27  2   18  5   27  2   36  5   21  2   36  5   21  2   36  5   1   2   36  5   1   2   18  5   251 1   18  5   251 1   180 4   251 1   180 4   251 1   162 
                                           4   1   2   7   255 73  1   117 1   73  1   120 1   73  1   120 1   72  1   123 1   72  1   123 1   70  1   126 1   70  1   126 1   67  1   128 1   67  1   128 1   64  1   129 1   64  1   129 1   61  1   130 1   61  1   130 1   57  1   129 1   57  1   129 
                                           1   54  1   128 1   54  1   128 1   52  1   126 1   52  1   126 1   49  1   123 1   49  1   123 1   48  1   120 1   48  1   120 1   48  1   117 1   48  1   117 1   48  1   114 1   48  1   114 1   49  1   111 1   49  1   111 1   52  1   108 1   52  1   108 
                                           1   54  1   106 1   54  1   106 1   57  1   105 1   57  1   105 1   61  1   104 1   61  1   104 1   64  1   105 1   64  1   105 1   67  1   106 1   67  1   106 1   70  1   108 1   70  1   108 1   72  1   111 1   72  1   111 1   73  1   114 1   73  1   114 
                                           1   73  1   117 1   7   255 35  1   117 1   86  1   117 1   7   255 61  1   91  1   61  1   143 1   7   255 252 0   213 0   252 0   233 0   252 0   233 0   14  1   239 0   14  1   239 0   107 1   239 0   107 1   239 0   126 1   233 0   126 1   233 0   126 
                                           1   213 0   126 1   213 0   107 1   207 0   107 1   207 0   14  1   207 0   14  1   207 0   252 0   213 0   7   255 252 0   1   2   252 0   21  2   252 0   21  2   14  1   27  2   14  1   27  2   107 1   27  2   107 1   27  2   126 1   21  2   126 1   21  
                                           2   126 1   1   2   126 1   1   2   107 1   251 1   107 1   251 1   14  1   251 1   14  1   251 1   252 0   1   2   7   255 61  0   207 0   60  0   210 0   60  0   210 0   59  0   213 0   59  0   213 0   57  0   216 0   57  0   216 0   54  0   218 0   54  
                                           0   218 0   51  0   219 0   51  0   219 0   48  0   220 0   48  0   220 0   44  0   219 0   44  0   219 0   41  0   218 0   41  0   218 0   39  0   216 0   39  0   216 0   37  0   213 0   37  0   213 0   35  0   210 0   35  0   210 0   35  0   207 0   35  
                                           0   207 0   35  0   203 0   35  0   203 0   37  0   200 0   37  0   200 0   39  0   198 0   39  0   198 0   41  0   196 0   41  0   196 0   44  0   194 0   44  0   194 0   48  0   194 0   48  0   194 0   51  0   194 0   51  0   194 0   54  0   196 0   54  
                                           0   196 0   57  0   198 0   57  0   198 0   59  0   200 0   59  0   200 0   60  0   203 0   60  0   203 0   61  0   207 0   7   255 22  0   207 0   73  0   207 0   7   255 48  0   181 0   48  0   232 0   7   255 73  1   207 0   73  1   210 0   73  1   210 
                                           0   72  1   213 0   72  1   213 0   70  1   216 0   70  1   216 0   67  1   218 0   67  1   218 0   64  1   219 0   64  1   219 0   61  1   220 0   61  1   220 0   57  1   219 0   57  1   219 0   54  1   218 0   54  1   218 0   52  1   216 0   52  1   216 
                                           0   49  1   213 0   49  1   213 0   48  1   210 0   48  1   210 0   48  1   207 0   48  1   207 0   48  1   203 0   48  1   203 0   49  1   200 0   49  1   200 0   52  1   198 0   52  1   198 0   54  1   196 0   54  1   196 0   57  1   194 0   57  1   194 
                                           0   61  1   194 0   61  1   194 0   64  1   194 0   64  1   194 0   67  1   196 0   67  1   196 0   70  1   198 0   70  1   198 0   72  1   200 0   72  1   200 0   73  1   203 0   73  1   203 0   73  1   207 0   7   255 35  1   207 0   86  1   207 0   7   
                                           255 61  1   181 0   61  1   232 0   7   255 240 4   207 0   240 4   210 0   240 4   210 0   238 4   213 0   238 4   213 0   236 4   216 0   236 4   216 0   234 4   218 0   234 4   218 0   230 4   219 0   230 4   219 0   227 4   220 0   227 4   220 0   224 
                                           4   219 0   224 4   219 0   221 4   218 0   221 4   218 0   218 4   216 0   218 4   216 0   216 4   213 0   216 4   213 0   215 4   210 0   215 4   210 0   214 4   207 0   214 4   207 0   215 4   203 0   215 4   203 0   216 4   200 0   216 4   200 0   218 
                                           4   198 0   218 4   198 0   221 4   196 0   221 4   196 0   224 4   194 0   224 4   194 0   227 4   194 0   227 4   194 0   230 4   194 0   230 4   194 0   234 4   196 0   234 4   196 0   236 4   198 0   236 4   198 0   238 4   200 0   238 4   200 0   240 
                                           4   203 0   240 4   203 0   240 4   207 0   7   255 202 4   207 0   253 4   207 0   7   255 227 4   181 0   227 4   232 0   7   255 74  6   207 0   73  6   210 0   73  6   210 0   72  6   213 0   72  6   213 0   70  6   216 0   70  6   216 0   67  6   218 
                                           0   67  6   218 0   64  6   219 0   64  6   219 0   61  6   220 0   61  6   220 0   58  6   219 0   58  6   219 0   54  6   218 0   54  6   218 0   52  6   216 0   52  6   216 0   50  6   213 0   50  6   213 0   48  6   210 0   48  6   210 0   48  6   207 
                                           0   48  6   207 0   48  6   203 0   48  6   203 0   50  6   200 0   50  6   200 0   52  6   198 0   52  6   198 0   54  6   196 0   54  6   196 0   58  6   194 0   58  6   194 0   61  6   194 0   61  6   194 0   64  6   194 0   64  6   194 0   67  6   196 
                                           0   67  6   196 0   70  6   198 0   70  6   198 0   72  6   200 0   72  6   200 0   73  6   203 0   73  6   203 0   74  6   207 0   7   255 35  6   207 0   86  6   207 0   7   255 61  6   181 0   61  6   232 0   7   255 74  6   27  2   73  6   31  2   73  
                                           6   31  2   72  6   34  2   72  6   34  2   70  6   36  2   70  6   36  2   67  6   38  2   67  6   38  2   64  6   40  2   64  6   40  2   61  6   40  2   61  6   40  2   58  6   40  2   58  6   40  2   54  6   38  2   54  6   38  2   52  6   36  2   52  
                                           6   36  2   50  6   34  2   50  6   34  2   48  6   31  2   48  6   31  2   48  6   27  2   48  6   27  2   48  6   24  2   48  6   24  2   50  6   21  2   50  6   21  2   52  6   18  2   52  6   18  2   54  6   16  2   54  6   16  2   58  6   15  2   58  
                                           6   15  2   61  6   15  2   61  6   15  2   64  6   15  2   64  6   15  2   67  6   16  2   67  6   16  2   70  6   18  2   70  6   18  2   72  6   21  2   72  6   21  2   73  6   24  2   73  6   24  2   74  6   27  2   7   255 35  6   27  2   86  6   27  
                                           2   7   255 61  6   2   2   61  6   53  2   7   255 240 4   27  2   240 4   31  2   240 4   31  2   238 4   34  2   238 4   34  2   236 4   36  2   236 4   36  2   234 4   38  2   234 4   38  2   230 4   40  2   230 4   40  2   227 4   40  2   227 4   40  
                                           2   224 4   40  2   224 4   40  2   221 4   38  2   221 4   38  2   218 4   36  2   218 4   36  2   216 4   34  2   216 4   34  2   215 4   31  2   215 4   31  2   214 4   27  2   214 4   27  2   215 4   24  2   215 4   24  2   216 4   21  2   216 4   21  
                                           2   218 4   18  2   218 4   18  2   221 4   16  2   221 4   16  2   224 4   15  2   224 4   15  2   227 4   15  2   227 4   15  2   230 4   15  2   230 4   15  2   234 4   16  2   234 4   16  2   236 4   18  2   236 4   18  2   238 4   21  2   238 4   21  
                                           2   240 4   24  2   240 4   24  2   240 4   27  2   7   255 202 4   27  2   253 4   27  2   7   255 227 4   2   2   227 4   53  2   7   255 73  1   27  2   73  1   31  2   73  1   31  2   72  1   34  2   72  1   34  2   70  1   36  2   70  1   36  2   67  
                                           1   38  2   67  1   38  2   64  1   40  2   64  1   40  2   61  1   40  2   61  1   40  2   57  1   40  2   57  1   40  2   54  1   38  2   54  1   38  2   52  1   36  2   52  1   36  2   49  1   34  2   49  1   34  2   48  1   31  2   48  1   31  2   48  
                                           1   27  2   48  1   27  2   48  1   24  2   48  1   24  2   49  1   21  2   49  1   21  2   52  1   18  2   52  1   18  2   54  1   16  2   54  1   16  2   57  1   15  2   57  1   15  2   61  1   15  2   61  1   15  2   64  1   15  2   64  1   15  2   67  
                                           1   16  2   67  1   16  2   70  1   18  2   70  1   18  2   72  1   21  2   72  1   21  2   73  1   24  2   73  1   24  2   73  1   27  2   7   255 35  1   27  2   86  1   27  2   7   255 61  1   2   2   61  1   53  2   7   255 61  0   27  2   60  0   31  
                                           2   60  0   31  2   59  0   34  2   59  0   34  2   57  0   36  2   57  0   36  2   54  0   38  2   54  0   38  2   51  0   40  2   51  0   40  2   48  0   40  2   48  0   40  2   44  0   40  2   44  0   40  2   41  0   38  2   41  0   38  2   39  0   36  
                                           2   39  0   36  2   37  0   34  2   37  0   34  2   35  0   31  2   35  0   31  2   35  0   27  2   35  0   27  2   35  0   24  2   35  0   24  2   37  0   21  2   37  0   21  2   39  0   18  2   39  0   18  2   41  0   16  2   41  0   16  2   44  0   15  
                                           2   44  0   15  2   48  0   15  2   48  0   15  2   51  0   15  2   51  0   15  2   54  0   16  2   54  0   16  2   57  0   18  2   57  0   18  2   59  0   21  2   59  0   21  2   60  0   24  2   60  0   24  2   61  0   27  2   7   255 22  0   27  2   73  
                                           0   27  2   7   255 48  0   2   2   48  0   53  2   0   252 65  117 116 111 67  65  68  32  83  108 105 100 101 13  10  26  0   86  2   73  6   247 2   97  120 67  1   2   0   52  18  7   255 7   255 215 1   255 0   14  6   255 0   14  6   255 0   14  6   
                                           4   2   14  6   4   2   215 1   4   2   215 1   4   2   215 1   255 0   7   255 215 1   255 0   215 1   255 0   7   255 215 1   255 0   215 1   255 0   7   255 215 1   255 0   215 1   255 0   7   255 67  2   130 1   64  2   137 1   64  2   137 1   57  2   
                                           140 1   57  2   140 1   50  2   137 1   50  2   137 1   47  2   130 1   47  2   130 1   50  2   122 1   50  2   122 1   57  2   119 1   57  2   119 1   64  2   122 1   64  2   122 1   67  2   130 1   7   255 4   5   59  1   4   5   77  1   4   5   77  1   
                                           19  5   83  1   19  5   83  1   97  5   83  1   97  5   83  1   112 5   77  1   112 5   77  1   112 5   59  1   112 5   59  1   97  5   53  1   97  5   53  1   19  5   53  1   19  5   53  1   4   5   59  1   7   255 4   5   5   1   4   5   23  1   4   5   
                                           23  1   19  5   29  1   19  5   29  1   97  5   29  1   97  5   29  1   112 5   23  1   112 5   23  1   112 5   5   1   112 5   5   1   97  5   255 0   97  5   255 0   19  5   255 0   19  5   255 0   4   5   5   1   7   255 4   5   182 1   4   5   201 1   
                                           4   5   201 1   19  5   207 1   19  5   207 1   97  5   207 1   97  5   207 1   112 5   201 1   112 5   201 1   112 5   182 1   112 5   182 1   97  5   177 1   97  5   177 1   19  5   177 1   19  5   177 1   4   5   182 1   7   255 4   5   236 1   4   5   
                                           255 1   4   5   255 1   19  5   4   2   19  5   4   2   97  5   4   2   97  5   4   2   112 5   255 1   112 5   255 1   112 5   236 1   112 5   236 1   97  5   231 1   97  5   231 1   19  5   231 1   19  5   231 1   4   5   236 1   7   255 134 5   59  1   
                                           134 5   77  1   134 5   77  1   149 5   83  1   149 5   83  1   227 5   83  1   227 5   83  1   242 5   77  1   242 5   77  1   242 5   59  1   242 5   59  1   227 5   53  1   227 5   53  1   149 5   53  1   149 5   53  1   134 5   59  1   7   255 134 5   
                                           5   1   134 5   23  1   134 5   23  1   149 5   29  1   149 5   29  1   227 5   29  1   227 5   29  1   242 5   23  1   242 5   23  1   242 5   5   1   242 5   5   1   227 5   255 0   227 5   255 0   149 5   255 0   149 5   255 0   134 5   5   1   7   255 
                                           134 5   182 1   134 5   201 1   134 5   201 1   149 5   207 1   149 5   207 1   227 5   207 1   227 5   207 1   242 5   201 1   242 5   201 1   242 5   182 1   242 5   182 1   227 5   177 1   227 5   177 1   149 5   177 1   149 5   177 1   134 5   182 1   
                                           7   255 134 5   236 1   134 5   255 1   134 5   255 1   149 5   4   2   149 5   4   2   227 5   4   2   227 5   4   2   242 5   255 1   242 5   255 1   242 5   236 1   242 5   236 1   227 5   231 1   227 5   231 1   149 5   231 1   149 5   231 1   134 5   
                                           236 1   7   255 218 1   255 0   217 1   1   1   217 1   1   1   215 1   2   1   215 1   2   1   213 1   1   1   213 1   1   1   212 1   255 0   212 1   255 0   213 1   253 0   213 1   253 0   215 1   252 0   215 1   252 0   217 1   253 0   217 1   253 0   
                                           218 1   255 0   7   255 208 1   255 0   221 1   255 0   7   255 215 1   248 0   215 1   6   1   7   255 218 1   4   2   217 1   7   2   217 1   7   2   215 1   8   2   215 1   8   2   213 1   7   2   213 1   7   2   212 1   4   2   212 1   4   2   213 1   
                                           2   2   213 1   2   2   215 1   1   2   215 1   1   2   217 1   2   2   217 1   2   2   218 1   4   2   7   255 208 1   4   2   221 1   4   2   7   255 215 1   254 1   215 1   11  2   7   255 60  2   130 1   59  2   132 1   59  2   132 1   57  2   133 1   
                                           57  2   133 1   55  2   132 1   55  2   132 1   54  2   130 1   54  2   130 1   55  2   127 1   55  2   127 1   57  2   126 1   57  2   126 1   59  2   127 1   59  2   127 1   60  2   130 1   7   255 50  2   130 1   64  2   130 1   7   255 57  2   123 1   
                                           57  2   136 1   7   255 18  6   255 0   17  6   1   1   17  6   1   1   14  6   2   1   14  6   2   1   12  6   1   1   12  6   1   1   11  6   255 0   11  6   255 0   12  6   253 0   12  6   253 0   14  6   252 0   14  6   252 0   17  6   253 0   17  6   
                                           253 0   18  6   255 0   7   255 8   6   255 0   21  6   255 0   7   255 14  6   248 0   14  6   6   1   7   255 18  6   4   2   17  6   7   2   17  6   7   2   14  6   8   2   14  6   8   2   12  6   7   2   12  6   7   2   11  6   4   2   11  6   4   2   
                                           12  6   2   2   12  6   2   2   14  6   1   2   14  6   1   2   17  6   2   2   17  6   2   2   18  6   4   2   7   255 8   6   4   2   21  6   4   2   7   255 14  6   254 1   14  6   11  2   7   255 126 5   255 0   125 5   1   1   125 5   1   1   123 5   
                                           2   1   123 5   2   1   121 5   1   1   121 5   1   1   120 5   255 0   120 5   255 0   121 5   253 0   121 5   253 0   123 5   252 0   123 5   252 0   125 5   253 0   125 5   253 0   126 5   255 0   7   255 117 5   255 0   130 5   255 0   7   255 123 5   
                                           )) "a")
 (_WriteStream FILE (vl-list->string (list 248 0   123 5   6   1   7   255 126 5   4   2   125 5   7   2   125 5   7   2   123 5   8   2   123 5   8   2   121 5   7   2   121 5   7   2   120 5   4   2   120 5   4   2   121 5   2   2   121 5   2   2   123 5   1   2   123 5   1   2   125 5   2   2   
                                           125 5   2   2   126 5   4   2   7   255 117 5   4   2   130 5   4   2   7   255 123 5   254 1   123 5   11  2   7   255 62  0   255 0   51  1   255 0   51  1   255 0   51  1   83  1   51  1   83  1   57  2   83  1   57  2   83  1   57  2   177 1   57  2   
                                           177 1   51  1   177 1   51  1   177 1   51  1   4   2   51  1   4   2   62  0   4   2   62  0   4   2   62  0   255 0   7   255 62  0   255 0   62  0   255 0   7   255 62  0   255 0   62  0   255 0   7   255 62  0   255 0   62  0   255 0   7   255 83  2   
                                           156 1   67  2   166 1   67  2   166 1   47  2   166 1   47  2   166 1   31  2   156 1   31  2   156 1   21  2   139 1   21  2   139 1   21  2   120 1   21  2   120 1   31  2   103 1   31  2   103 1   47  2   94  1   47  2   94  1   67  2   94  1   67  2   
                                           94  1   83  2   103 1   7   255 83  2   103 1   83  2   156 1   7   255 253 1   59  1   253 1   77  1   253 1   77  1   14  2   83  1   14  2   83  1   100 2   83  1   100 2   83  1   117 2   77  1   117 2   77  1   117 2   59  1   117 2   59  1   100 2   
                                           53  1   100 2   53  1   14  2   53  1   14  2   53  1   253 1   59  1   7   255 253 1   5   1   253 1   23  1   253 1   23  1   14  2   29  1   14  2   29  1   100 2   29  1   100 2   29  1   117 2   23  1   117 2   23  1   117 2   5   1   117 2   5   1   
                                           100 2   255 0   100 2   255 0   14  2   255 0   14  2   255 0   253 1   5   1   7   255 253 1   182 1   253 1   201 1   253 1   201 1   14  2   207 1   14  2   207 1   100 2   207 1   100 2   207 1   117 2   201 1   117 2   201 1   117 2   182 1   117 2   
                                           182 1   100 2   177 1   100 2   177 1   14  2   177 1   14  2   177 1   253 1   182 1   7   255 253 1   236 1   253 1   255 1   253 1   255 1   14  2   4   2   14  2   4   2   100 2   4   2   100 2   4   2   117 2   255 1   117 2   255 1   117 2   236 1   
                                           117 2   236 1   100 2   231 1   100 2   231 1   14  2   231 1   14  2   231 1   253 1   236 1   7   255 163 0   255 0   162 0   1   1   162 0   1   1   160 0   2   1   160 0   2   1   158 0   1   1   158 0   1   1   157 0   255 0   157 0   255 0   158 0   
                                           253 0   158 0   253 0   160 0   252 0   160 0   252 0   162 0   253 0   162 0   253 0   163 0   255 0   7   255 154 0   255 0   167 0   255 0   7   255 160 0   248 0   160 0   6   1   7   255 60  2   255 0   59  2   1   1   59  2   1   1   57  2   2   1   
                                           57  2   2   1   55  2   1   1   55  2   1   1   54  2   255 0   54  2   255 0   55  2   253 0   55  2   253 0   57  2   252 0   57  2   252 0   59  2   253 0   59  2   253 0   60  2   255 0   7   255 50  2   255 0   64  2   255 0   7   255 57  2   248 0   
                                           57  2   6   1   7   255 60  2   4   2   59  2   7   2   59  2   7   2   57  2   8   2   57  2   8   2   55  2   7   2   55  2   7   2   54  2   4   2   54  2   4   2   55  2   2   2   55  2   2   2   57  2   1   2   57  2   1   2   59  2   2   2   59  2   
                                           2   2   60  2   4   2   7   255 50  2   4   2   64  2   4   2   7   255 57  2   254 1   57  2   11  2   7   255 60  2   130 1   59  2   132 1   59  2   132 1   57  2   133 1   57  2   133 1   55  2   132 1   55  2   132 1   54  2   130 1   54  2   130 1   
                                           55  2   127 1   55  2   127 1   57  2   126 1   57  2   126 1   59  2   127 1   59  2   127 1   60  2   130 1   7   255 50  2   130 1   64  2   130 1   7   255 57  2   123 1   57  2   136 1   7   255 163 0   4   2   162 0   7   2   162 0   7   2   160 0   
                                           8   2   160 0   8   2   158 0   7   2   158 0   7   2   157 0   4   2   157 0   4   2   158 0   2   2   158 0   2   2   160 0   1   2   160 0   1   2   162 0   2   2   162 0   2   2   163 0   4   2   7   255 154 0   4   2   167 0   4   2   7   255 160 0   
                                           254 1   160 0   11  2   7   255 65  0   4   2   64  0   7   2   64  0   7   2   62  0   8   2   62  0   8   2   60  0   7   2   60  0   7   2   59  0   4   2   59  0   4   2   60  0   2   2   60  0   2   2   62  0   1   2   62  0   1   2   64  0   2   2   
                                           64  0   2   2   65  0   4   2   7   255 55  0   4   2   69  0   4   2   7   255 62  0   254 1   62  0   11  2   7   255 65  0   255 0   64  0   1   1   64  0   1   1   62  0   2   1   62  0   2   1   60  0   1   1   60  0   1   1   59  0   255 0   59  0   
                                           255 0   60  0   253 0   60  0   253 0   62  0   252 0   62  0   252 0   64  0   253 0   64  0   253 0   65  0   255 0   7   255 55  0   255 0   69  0   255 0   7   255 62  0   248 0   62  0   6   1   7   255 163 0   130 1   162 0   132 1   162 0   132 1   
                                           160 0   133 1   160 0   133 1   158 0   132 1   158 0   132 1   157 0   130 1   157 0   130 1   158 0   127 1   158 0   127 1   160 0   126 1   160 0   126 1   162 0   127 1   162 0   127 1   163 0   130 1   7   255 154 0   130 1   167 0   130 1   7   255 
                                           160 0   123 1   160 0   136 1   7   255 100 0   5   1   100 0   23  1   100 0   23  1   117 0   29  1   117 0   29  1   203 0   29  1   203 0   29  1   220 0   23  1   220 0   23  1   220 0   5   1   220 0   5   1   203 0   255 0   203 0   255 0   117 0   
                                           255 0   117 0   255 0   100 0   5   1   7   255 100 0   236 1   100 0   255 1   100 0   255 1   117 0   4   2   117 0   4   2   203 0   4   2   203 0   4   2   220 0   255 1   220 0   255 1   220 0   236 1   220 0   236 1   203 0   231 1   203 0   231 1   
                                           117 0   231 1   117 0   231 1   100 0   236 1   0   252 65  117 116 111 67  65  68  32  83  108 105 100 101 13  10  26  0   86  2   106 6   234 2   99  219 79  1   2   0   52  18  7   255 7   255 25  0   26  1   234 0   26  1   234 0   26  1   234 0   81  
                                           1   234 0   81  1   44  2   81  1   44  2   81  1   44  2   153 1   44  2   153 1   234 0   153 1   234 0   153 1   234 0   207 1   234 0   207 1   25  0   207 1   25  0   207 1   25  0   26  1   7   255 25  0   26  1   25  0   26  1   7   255 25  0   26  
                                           1   25  0   26  1   7   255 18  2   135 1   13  2   139 1   13  2   139 1   7   2   142 1   7   2   142 1   0   2   143 1   0   2   143 1   249 1   142 1   249 1   142 1   243 1   139 1   243 1   139 1   238 1   135 1   238 1   135 1   234 1   130 1   234 
                                           1   130 1   231 1   123 1   231 1   123 1   230 1   117 1   230 1   117 1   231 1   110 1   231 1   110 1   234 1   104 1   234 1   104 1   238 1   98  1   238 1   98  1   243 1   94  1   243 1   94  1   249 1   92  1   249 1   92  1   0   2   91  1   0   
                                           2   91  1   7   2   92  1   7   2   92  1   13  2   94  1   13  2   94  1   18  2   98  1   7   255 18  2   98  1   18  2   135 1   7   255 173 1   65  1   173 1   77  1   173 1   77  1   184 1   81  1   184 1   81  1   240 1   81  1   240 1   81  1   251 
                                           1   77  1   251 1   77  1   251 1   65  1   251 1   65  1   240 1   61  1   240 1   61  1   184 1   61  1   184 1   61  1   173 1   65  1   7   255 173 1   30  1   173 1   42  1   173 1   42  1   184 1   46  1   184 1   46  1   240 1   46  1   240 1   46  
                                           1   251 1   42  1   251 1   42  1   251 1   30  1   251 1   30  1   240 1   26  1   240 1   26  1   184 1   26  1   184 1   26  1   173 1   30  1   7   255 173 1   156 1   173 1   168 1   173 1   168 1   184 1   172 1   184 1   172 1   240 1   172 1   240 
                                           1   172 1   251 1   168 1   251 1   168 1   251 1   156 1   251 1   156 1   240 1   153 1   240 1   153 1   184 1   153 1   184 1   153 1   173 1   156 1   7   255 173 1   191 1   173 1   203 1   173 1   203 1   184 1   207 1   184 1   207 1   240 1   207 
                                           1   240 1   207 1   251 1   203 1   251 1   203 1   251 1   191 1   251 1   191 1   240 1   188 1   240 1   188 1   184 1   188 1   184 1   188 1   173 1   191 1   7   255 5   2   65  1   5   2   77  1   5   2   77  1   16  2   81  1   16  2   81  1   72  
                                           2   81  1   72  2   81  1   83  2   77  1   83  2   77  1   83  2   65  1   83  2   65  1   72  2   61  1   72  2   61  1   16  2   61  1   16  2   61  1   5   2   65  1   7   255 5   2   30  1   5   2   42  1   5   2   42  1   16  2   46  1   16  2   46  
                                           1   72  2   46  1   72  2   46  1   83  2   42  1   83  2   42  1   83  2   30  1   83  2   30  1   72  2   26  1   72  2   26  1   16  2   26  1   16  2   26  1   5   2   30  1   7   255 5   2   156 1   5   2   168 1   5   2   168 1   16  2   172 1   16  
                                           2   172 1   72  2   172 1   72  2   172 1   83  2   168 1   83  2   168 1   83  2   156 1   83  2   156 1   72  2   153 1   72  2   153 1   16  2   153 1   16  2   153 1   5   2   156 1   7   255 5   2   191 1   5   2   203 1   5   2   203 1   16  2   207 
                                           1   16  2   207 1   72  2   207 1   72  2   207 1   83  2   203 1   83  2   203 1   83  2   191 1   83  2   191 1   72  2   188 1   72  2   188 1   16  2   188 1   16  2   188 1   5   2   191 1   7   255 88  0   117 1   87  0   120 1   87  0   120 1   84  
                                           0   123 1   84  0   123 1   81  0   124 1   81  0   124 1   77  0   123 1   77  0   123 1   75  0   120 1   75  0   120 1   74  0   117 1   74  0   117 1   75  0   113 1   75  0   113 1   77  0   111 1   77  0   111 1   81  0   110 1   81  0   110 1   84  
                                           0   111 1   84  0   111 1   87  0   113 1   87  0   113 1   88  0   117 1   7   255 67  0   117 1   95  0   117 1   7   255 81  0   103 1   81  0   131 1   7   255 7   2   26  1   6   2   30  1   6   2   30  1   3   2   32  1   3   2   32  1   0   2   33  
                                           1   0   2   33  1   253 1   32  1   253 1   32  1   250 1   30  1   250 1   30  1   249 1   26  1   249 1   26  1   250 1   23  1   250 1   23  1   253 1   20  1   253 1   20  1   0   2   19  1   0   2   19  1   3   2   20  1   3   2   20  1   6   2   23  
                                           1   6   2   23  1   7   2   26  1   7   255 242 1   26  1   14  2   26  1   7   255 0   2   12  1   0   2   40  1   7   255 7   2   207 1   6   2   211 1   6   2   211 1   3   2   213 1   3   2   213 1   0   2   214 1   0   2   214 1   253 1   213 1   253 
                                           1   213 1   250 1   211 1   250 1   211 1   249 1   207 1   249 1   207 1   250 1   204 1   250 1   204 1   253 1   201 1   253 1   201 1   0   2   200 1   0   2   200 1   3   2   201 1   3   2   201 1   6   2   204 1   6   2   204 1   7   2   207 1   7   
                                           255 242 1   207 1   14  2   207 1   7   255 0   2   193 1   0   2   221 1   7   255 7   2   117 1   6   2   120 1   6   2   120 1   3   2   123 1   3   2   123 1   0   2   124 1   0   2   124 1   253 1   123 1   253 1   123 1   250 1   120 1   250 1   120 
                                           1   249 1   117 1   249 1   117 1   250 1   113 1   250 1   113 1   253 1   111 1   253 1   111 1   0   2   110 1   0   2   110 1   3   2   111 1   3   2   111 1   6   2   113 1   6   2   113 1   7   2   117 1   7   255 242 1   117 1   14  2   117 1   7   
                                           255 0   2   103 1   0   2   131 1   7   255 32  0   26  1   31  0   30  1   31  0   30  1   29  0   32  1   29  0   32  1   25  0   33  1   25  0   33  1   22  0   32  1   22  0   32  1   19  0   30  1   19  0   30  1   18  0   26  1   18  0   26  1   19  
                                           0   23  1   19  0   23  1   22  0   20  1   22  0   20  1   25  0   19  1   25  0   19  1   29  0   20  1   29  0   20  1   31  0   23  1   31  0   23  1   32  0   26  1   7   255 11  0   26  1   39  0   26  1   7   255 25  0   12  1   25  0   40  1   7   
                                           255 88  0   26  1   87  0   30  1   87  0   30  1   84  0   32  1   84  0   32  1   81  0   33  1   81  0   33  1   77  0   32  1   77  0   32  1   75  0   30  1   75  0   30  1   74  0   26  1   74  0   26  1   75  0   23  1   75  0   23  1   77  0   20  
                                           1   77  0   20  1   81  0   19  1   81  0   19  1   84  0   20  1   84  0   20  1   87  0   23  1   87  0   23  1   88  0   26  1   7   255 67  0   26  1   95  0   26  1   7   255 81  0   12  1   81  0   40  1   7   255 88  0   207 1   87  0   211 1   87  
                                           0   211 1   84  0   213 1   84  0   213 1   81  0   214 1   81  0   214 1   77  0   213 1   77  0   213 1   75  0   211 1   75  0   211 1   74  0   207 1   74  0   207 1   75  0   204 1   75  0   204 1   77  0   201 1   77  0   201 1   81  0   200 1   81  
                                           0   200 1   84  0   201 1   84  0   201 1   87  0   204 1   87  0   204 1   88  0   207 1   7   255 67  0   207 1   95  0   207 1   7   255 81  0   193 1   81  0   221 1   7   255 32  0   207 1   31  0   211 1   31  0   211 1   29  0   213 1   29  0   213 
                                           1   25  0   214 1   25  0   214 1   22  0   213 1   22  0   213 1   19  0   211 1   19  0   211 1   18  0   207 1   18  0   207 1   19  0   204 1   19  0   204 1   22  0   201 1   22  0   201 1   25  0   200 1   25  0   200 1   29  0   201 1   29  0   201 
                                           1   31  0   204 1   31  0   204 1   32  0   207 1   7   255 11  0   207 1   39  0   207 1   7   255 25  0   193 1   25  0   221 1   7   255 42  0   30  1   42  0   42  1   42  0   42  1   53  0   46  1   53  0   46  1   109 0   46  1   109 0   46  1   120 
                                           0   42  1   120 0   42  1   120 0   30  1   120 0   30  1   109 0   26  1   109 0   26  1   53  0   26  1   53  0   26  1   42  0   30  1   7   255 42  0   191 1   42  0   203 1   42  0   203 1   53  0   207 1   53  0   207 1   109 0   207 1   109 0   207 
                                           1   120 0   203 1   120 0   203 1   120 0   191 1   120 0   191 1   109 0   188 1   109 0   188 1   53  0   188 1   53  0   188 1   42  0   191 1   7   255 166 1   26  1   68  6   26  1   68  6   26  1   68  6   207 1   68  6   207 1   166 1   207 1   166 
                                           1   207 1   166 1   26  1   7   255 166 1   26  1   166 1   26  1   7   255 166 1   26  1   166 1   26  1   7   255 7   2   117 1   6   2   120 1   6   2   120 1   4   2   123 1   4   2   123 1   0   2   124 1   0   2   124 1   252 1   123 1   252 1   123 
                                           1   250 1   120 1   250 1   120 1   249 1   117 1   249 1   117 1   250 1   113 1   250 1   113 1   252 1   110 1   252 1   110 1   0   2   109 1   0   2   109 1   4   2   110 1   4   2   110 1   6   2   113 1   6   2   113 1   7   2   117 1   7   255 11  
                                           5   65  1   11  5   77  1   11  5   77  1   22  5   81  1   22  5   81  1   78  5   81  1   78  5   81  1   89  5   77  1   89  5   77  1   89  5   65  1   89  5   65  1   78  5   61  1   78  5   61  1   22  5   61  1   22  5   61  1   11  5   65  1   7   
                                           255 11  5   30  1   11  5   42  1   11  5   42  1   22  5   46  1   22  5   46  1   78  5   46  1   78  5   46  1   89  5   42  1   89  5   42  1   89  5   30  1   89  5   30  1   78  5   26  1   78  5   26  1   22  5   26  1   22  5   26  1   11  5   30  
                                           1   7   255 11  5   156 1   11  5   168 1   11  5   168 1   22  5   172 1   22  5   172 1   78  5   172 1   78  5   172 1   89  5   168 1   89  5   168 1   89  5   156 1   89  5   156 1   78  5   153 1   78  5   153 1   22  5   153 1   22  5   153 1   11  
                                           5   156 1   7   255 11  5   191 1   11  5   203 1   11  5   203 1   22  5   207 1   22  5   207 1   78  5   207 1   78  5   207 1   89  5   203 1   89  5   203 1   89  5   191 1   89  5   191 1   78  5   188 1   78  5   188 1   22  5   188 1   22  5   188 
                                           1   11  5   191 1   7   255 99  5   65  1   99  5   77  1   99  5   77  1   110 5   81  1   110 5   81  1   166 5   81  1   166 5   81  1   177 5   77  1   177 5   77  1   177 5   65  1   177 5   65  1   166 5   61  1   166 5   61  1   110 5   61  1   110 
                                           5   61  1   99  5   65  1   7   255 99  5   30  1   99  5   42  1   99  5   42  1   110 5   46  1   110 5   46  1   166 5   46  1   166 5   46  1   177 5   42  1   177 5   42  1   177 5   30  1   177 5   30  1   166 5   26  1   166 5   26  1   110 5   26  
                                           1   110 5   26  1   99  5   30  1   7   255 99  5   156 1   99  5   168 1   99  5   168 1   110 5   172 1   110 5   172 1   166 5   172 1   166 5   172 1   177 5   168 1   177 5   168 1   177 5   156 1   177 5   156 1   166 5   153 1   166 5   153 1   110 
                                           5   153 1   110 5   153 1   99  5   156 1   7   255 99  5   191 1   99  5   203 1   99  5   203 1   110 5   207 1   110 5   207 1   166 5   207 1   166 5   207 1   177 5   203 1   177 5   203 1   177 5   191 1   177 5   191 1   166 5   188 1   166 5   188 
                                           1   110 5   188 1   110 5   188 1   99  5   191 1   7   255 7   2   117 1   6   2   120 1   6   2   120 1   3   2   123 1   3   2   123 1   0   2   124 1   0   2   124 1   253 1   123 1   253 1   123 1   250 1   120 1   250 1   120 1   249 1   117 1   249 
                                           1   117 1   250 1   113 1   250 1   113 1   253 1   111 1   253 1   111 1   0   2   110 1   0   2   110 1   3   2   111 1   3   2   111 1   6   2   113 1   6   2   113 1   7   2   117 1   7   255 242 1   117 1   14  2   117 1   7   255 0   2   103 1   0   
                                           2   131 1   7   255 101 5   26  1   100 5   30  1   100 5   30  1   98  5   32  1   98  5   32  1   94  5   33  1   94  5   33  1   91  5   32  1   91  5   32  1   88  5   30  1   88  5   30  1   87  5   26  1   87  5   26  1   88  5   23  1   88  5   23  
                                           )) "a")
 (_WriteStream FILE (vl-list->string (list 1   91  5   20  1   91  5   20  1   94  5   19  1   94  5   19  1   98  5   20  1   98  5   20  1   100 5   23  1   100 5   23  1   101 5   26  1   7   255 80  5   26  1   108 5   26  1   7   255 94  5   12  1   94  5   40  1   7   255 101 5   207 1   100 
                                           5   211 1   100 5   211 1   98  5   213 1   98  5   213 1   94  5   214 1   94  5   214 1   91  5   213 1   91  5   213 1   88  5   211 1   88  5   211 1   87  5   207 1   87  5   207 1   88  5   204 1   88  5   204 1   91  5   201 1   91  5   201 1   94  
                                           5   200 1   94  5   200 1   98  5   201 1   98  5   201 1   100 5   204 1   100 5   204 1   101 5   207 1   7   255 80  5   207 1   108 5   207 1   7   255 94  5   193 1   94  5   221 1   7   255 75  6   207 1   74  6   211 1   74  6   211 1   71  6   213 
                                           1   71  6   213 1   68  6   214 1   68  6   214 1   64  6   213 1   64  6   213 1   62  6   211 1   62  6   211 1   61  6   207 1   61  6   207 1   62  6   204 1   62  6   204 1   64  6   201 1   64  6   201 1   68  6   200 1   68  6   200 1   71  6   201 
                                           1   71  6   201 1   74  6   204 1   74  6   204 1   75  6   207 1   7   255 54  6   207 1   82  6   207 1   7   255 68  6   193 1   68  6   221 1   7   255 75  6   26  1   74  6   30  1   74  6   30  1   71  6   32  1   71  6   32  1   68  6   33  1   68  
                                           6   33  1   64  6   32  1   64  6   32  1   62  6   30  1   62  6   30  1   61  6   26  1   61  6   26  1   62  6   23  1   62  6   23  1   64  6   20  1   64  6   20  1   68  6   19  1   68  6   19  1   71  6   20  1   71  6   20  1   74  6   23  1   74  
                                           6   23  1   75  6   26  1   7   255 54  6   26  1   82  6   26  1   7   255 68  6   12  1   68  6   40  1   7   255 173 1   26  1   172 1   30  1   172 1   30  1   169 1   32  1   169 1   32  1   166 1   33  1   166 1   33  1   162 1   32  1   162 1   32  
                                           1   160 1   30  1   160 1   30  1   159 1   26  1   159 1   26  1   160 1   23  1   160 1   23  1   162 1   20  1   162 1   20  1   166 1   19  1   166 1   19  1   169 1   20  1   169 1   20  1   172 1   23  1   172 1   23  1   173 1   26  1   7   255 152 
                                           1   26  1   180 1   26  1   7   255 166 1   12  1   166 1   40  1   7   255 173 1   207 1   172 1   211 1   172 1   211 1   169 1   213 1   169 1   213 1   166 1   214 1   166 1   214 1   162 1   213 1   162 1   213 1   160 1   211 1   160 1   211 1   159 
                                           1   207 1   159 1   207 1   160 1   204 1   160 1   204 1   162 1   201 1   162 1   201 1   166 1   200 1   166 1   200 1   169 1   201 1   169 1   201 1   172 1   204 1   172 1   204 1   173 1   207 1   7   255 152 1   207 1   180 1   207 1   7   255 166 
                                           1   193 1   166 1   221 1   0   252 65  117 116 111 67  65  68  32  83  108 105 100 101 13  10  26  0   86  2   73  6   247 2   97  120 67  1   2   0   52  18  7   255 7   255 249 1   27  1   17  6   27  1   17  6   27  1   17  6   212 1   17  6   212 1   
                                           249 1   212 1   249 1   212 1   249 1   27  1   7   255 249 1   27  1   249 1   27  1   7   255 249 1   27  1   249 1   27  1   7   255 249 1   27  1   249 1   27  1   7   255 55  2   120 1   53  2   125 1   53  2   125 1   47  2   127 1   47  2   127 1   
                                           42  2   125 1   42  2   125 1   40  2   120 1   40  2   120 1   42  2   114 1   42  2   114 1   47  2   112 1   47  2   112 1   53  2   114 1   53  2   114 1   55  2   120 1   7   255 95  5   67  1   95  5   79  1   95  5   79  1   105 5   83  1   105 5   
                                           83  1   157 5   83  1   157 5   83  1   167 5   79  1   167 5   79  1   167 5   67  1   167 5   67  1   157 5   63  1   157 5   63  1   105 5   63  1   105 5   63  1   95  5   67  1   7   255 95  5   31  1   95  5   43  1   95  5   43  1   105 5   47  1   
                                           105 5   47  1   157 5   47  1   157 5   47  1   167 5   43  1   167 5   43  1   167 5   31  1   167 5   31  1   157 5   27  1   157 5   27  1   105 5   27  1   105 5   27  1   95  5   31  1   7   255 95  5   196 1   95  5   209 1   95  5   209 1   105 5   
                                           212 1   105 5   212 1   157 5   212 1   157 5   212 1   167 5   209 1   167 5   209 1   167 5   196 1   167 5   196 1   157 5   192 1   157 5   192 1   105 5   192 1   105 5   192 1   95  5   196 1   7   255 182 5   67  1   182 5   79  1   182 5   79  1   
                                           193 5   83  1   193 5   83  1   244 5   83  1   244 5   83  1   255 5   79  1   255 5   79  1   255 5   67  1   255 5   67  1   244 5   63  1   244 5   63  1   193 5   63  1   193 5   63  1   182 5   67  1   7   255 182 5   31  1   182 5   43  1   182 5   
                                           43  1   193 5   47  1   193 5   47  1   244 5   47  1   244 5   47  1   255 5   43  1   255 5   43  1   255 5   31  1   255 5   31  1   244 5   27  1   244 5   27  1   193 5   27  1   193 5   27  1   182 5   31  1   7   255 182 5   196 1   182 5   209 1   
                                           182 5   209 1   193 5   212 1   193 5   212 1   244 5   212 1   244 5   212 1   255 5   209 1   255 5   209 1   255 5   196 1   255 5   196 1   244 5   192 1   244 5   192 1   193 5   192 1   193 5   192 1   182 5   196 1   7   255 50  2   120 1   49  2   
                                           121 1   49  2   121 1   47  2   122 1   47  2   122 1   46  2   121 1   46  2   121 1   45  2   120 1   45  2   120 1   46  2   118 1   46  2   118 1   47  2   118 1   47  2   118 1   49  2   118 1   49  2   118 1   50  2   120 1   7   255 43  2   120 1   
                                           52  2   120 1   7   255 47  2   115 1   47  2   124 1   7   255 251 1   27  1   250 1   29  1   250 1   29  1   249 1   29  1   249 1   29  1   247 1   29  1   247 1   29  1   247 1   27  1   247 1   27  1   247 1   25  1   247 1   25  1   249 1   25  1   
                                           249 1   25  1   250 1   25  1   250 1   25  1   251 1   27  1   7   255 244 1   27  1   253 1   27  1   7   255 249 1   23  1   249 1   31  1   7   255 19  6   27  1   19  6   29  1   19  6   29  1   17  6   29  1   17  6   29  1   16  6   29  1   16  6   
                                           29  1   15  6   27  1   15  6   27  1   16  6   25  1   16  6   25  1   17  6   25  1   17  6   25  1   19  6   25  1   19  6   25  1   19  6   27  1   7   255 13  6   27  1   21  6   27  1   7   255 17  6   23  1   17  6   31  1   7   255 19  6   212 1   
                                           19  6   214 1   19  6   214 1   17  6   215 1   17  6   215 1   16  6   214 1   16  6   214 1   15  6   212 1   15  6   212 1   16  6   211 1   16  6   211 1   17  6   210 1   17  6   210 1   19  6   211 1   19  6   211 1   19  6   212 1   7   255 13  6   
                                           212 1   21  6   212 1   7   255 17  6   208 1   17  6   217 1   7   255 251 1   212 1   250 1   214 1   250 1   214 1   249 1   215 1   249 1   215 1   247 1   214 1   247 1   214 1   247 1   212 1   247 1   212 1   247 1   211 1   247 1   211 1   249 1   
                                           210 1   249 1   210 1   250 1   211 1   250 1   211 1   251 1   212 1   7   255 244 1   212 1   253 1   212 1   7   255 249 1   208 1   249 1   217 1   7   255 95  5   173 1   95  5   160 1   95  5   160 1   105 5   156 1   105 5   156 1   157 5   156 1   
                                           157 5   156 1   167 5   160 1   167 5   160 1   167 5   173 1   167 5   173 1   157 5   176 1   157 5   176 1   105 5   176 1   105 5   176 1   95  5   173 1   7   255 182 5   173 1   182 5   160 1   182 5   160 1   193 5   156 1   193 5   156 1   244 5   
                                           156 1   244 5   156 1   255 5   160 1   255 5   160 1   255 5   173 1   255 5   173 1   244 5   176 1   244 5   176 1   193 5   176 1   193 5   176 1   182 5   173 1   7   255 177 5   27  1   176 5   29  1   176 5   29  1   175 5   29  1   175 5   29  1   
                                           173 5   29  1   173 5   29  1   173 5   27  1   173 5   27  1   173 5   25  1   173 5   25  1   175 5   25  1   175 5   25  1   176 5   25  1   176 5   25  1   177 5   27  1   7   255 170 5   27  1   179 5   27  1   7   255 175 5   23  1   175 5   31  1   
                                           7   255 177 5   212 1   176 5   214 1   176 5   214 1   175 5   215 1   175 5   215 1   173 5   214 1   173 5   214 1   173 5   212 1   173 5   212 1   173 5   211 1   173 5   211 1   175 5   210 1   175 5   210 1   176 5   211 1   176 5   211 1   177 5   
                                           212 1   7   255 170 5   212 1   179 5   212 1   7   255 175 5   208 1   175 5   217 1   7   255 46  0   32  1   118 1   32  1   118 1   32  1   118 1   88  1   118 1   88  1   93  2   88  1   93  2   88  1   93  2   151 1   93  2   151 1   118 1   151 1   
                                           118 1   151 1   118 1   207 1   118 1   207 1   46  0   207 1   46  0   207 1   46  0   32  1   7   255 46  0   32  1   46  0   32  1   7   255 46  0   32  1   46  0   32  1   7   255 46  0   32  1   46  0   32  1   7   255 65  2   137 1   54  2   144 1   
                                           54  2   144 1   41  2   144 1   41  2   144 1   30  2   137 1   30  2   137 1   23  2   126 1   23  2   126 1   23  2   113 1   23  2   113 1   30  2   102 1   30  2   102 1   41  2   96  1   41  2   96  1   54  2   96  1   54  2   96  1   65  2   102 1   
                                           7   255 65  2   102 1   65  2   137 1   7   255 217 1   72  1   217 1   85  1   217 1   85  1   229 1   88  1   229 1   88  1   30  2   88  1   30  2   88  1   42  2   85  1   42  2   85  1   42  2   72  1   42  2   72  1   30  2   68  1   30  2   68  1   
                                           229 1   68  1   229 1   68  1   217 1   72  1   7   255 217 1   36  1   217 1   49  1   217 1   49  1   229 1   52  1   229 1   52  1   30  2   52  1   30  2   52  1   42  2   49  1   42  2   49  1   42  2   36  1   42  2   36  1   30  2   32  1   30  2   
                                           32  1   229 1   32  1   229 1   32  1   217 1   36  1   7   255 217 1   155 1   217 1   167 1   217 1   167 1   229 1   171 1   229 1   171 1   30  2   171 1   30  2   171 1   42  2   167 1   42  2   167 1   42  2   155 1   42  2   155 1   30  2   151 1   
                                           30  2   151 1   229 1   151 1   229 1   151 1   217 1   155 1   7   255 217 1   191 1   217 1   203 1   217 1   203 1   229 1   207 1   229 1   207 1   30  2   207 1   30  2   207 1   42  2   203 1   42  2   203 1   42  2   191 1   42  2   191 1   30  2   
                                           187 1   30  2   187 1   229 1   187 1   229 1   187 1   217 1   191 1   7   255 53  2   72  1   53  2   85  1   53  2   85  1   64  2   88  1   64  2   88  1   122 2   88  1   122 2   88  1   133 2   85  1   133 2   85  1   133 2   72  1   133 2   72  1   
                                           122 2   68  1   122 2   68  1   64  2   68  1   64  2   68  1   53  2   72  1   7   255 53  2   36  1   53  2   49  1   53  2   49  1   64  2   52  1   64  2   52  1   122 2   52  1   122 2   52  1   133 2   49  1   133 2   49  1   133 2   36  1   133 2   
                                           36  1   122 2   32  1   122 2   32  1   64  2   32  1   64  2   32  1   53  2   36  1   7   255 53  2   155 1   53  2   167 1   53  2   167 1   64  2   171 1   64  2   171 1   122 2   171 1   122 2   171 1   133 2   167 1   133 2   167 1   133 2   155 1   
                                           133 2   155 1   122 2   151 1   122 2   151 1   64  2   151 1   64  2   151 1   53  2   155 1   7   255 53  2   191 1   53  2   203 1   53  2   203 1   64  2   207 1   64  2   207 1   122 2   207 1   122 2   207 1   133 2   203 1   133 2   203 1   133 2   
                                           191 1   133 2   191 1   122 2   187 1   122 2   187 1   64  2   187 1   64  2   187 1   53  2   191 1   7   255 48  0   32  1   48  0   34  1   48  0   34  1   46  0   35  1   46  0   35  1   45  0   34  1   45  0   34  1   44  0   32  1   44  0   32  1   
                                           45  0   31  1   45  0   31  1   46  0   30  1   46  0   30  1   48  0   31  1   48  0   31  1   48  0   32  1   7   255 42  0   32  1   51  0   32  1   7   255 46  0   28  1   46  0   37  1   7   255 136 0   32  1   135 0   34  1   135 0   34  1   134 0   
                                           35  1   134 0   35  1   132 0   34  1   132 0   34  1   131 0   32  1   131 0   32  1   132 0   31  1   132 0   31  1   134 0   30  1   134 0   30  1   135 0   31  1   135 0   31  1   136 0   32  1   7   255 129 0   32  1   138 0   32  1   7   255 134 0   
                                           28  1   134 0   37  1   7   255 50  2   32  1   49  2   34  1   49  2   34  1   47  2   35  1   47  2   35  1   46  2   34  1   46  2   34  1   45  2   32  1   45  2   32  1   46  2   31  1   46  2   31  1   47  2   30  1   47  2   30  1   49  2   31  1   
                                           49  2   31  1   50  2   32  1   7   255 43  2   32  1   52  2   32  1   7   255 47  2   28  1   47  2   37  1   7   255 50  2   207 1   49  2   209 1   49  2   209 1   47  2   209 1   47  2   209 1   46  2   209 1   46  2   209 1   45  2   207 1   45  2   
                                           207 1   46  2   205 1   46  2   205 1   47  2   205 1   47  2   205 1   49  2   205 1   49  2   205 1   50  2   207 1   7   255 43  2   207 1   52  2   207 1   7   255 47  2   203 1   47  2   211 1   7   255 136 0   120 1   135 0   121 1   135 0   121 1   
                                           134 0   122 1   134 0   122 1   132 0   121 1   132 0   121 1   131 0   120 1   131 0   120 1   132 0   118 1   132 0   118 1   134 0   118 1   134 0   118 1   135 0   118 1   135 0   118 1   136 0   120 1   7   255 129 0   120 1   138 0   120 1   7   255 
                                           134 0   115 1   134 0   124 1   7   255 136 0   207 1   135 0   209 1   135 0   209 1   134 0   209 1   134 0   209 1   132 0   209 1   132 0   209 1   131 0   207 1   131 0   207 1   132 0   205 1   132 0   205 1   134 0   205 1   134 0   205 1   135 0   
                                           205 1   135 0   205 1   136 0   207 1   7   255 129 0   207 1   138 0   207 1   7   255 134 0   203 1   134 0   211 1   7   255 48  0   207 1   48  0   209 1   48  0   209 1   46  0   209 1   46  0   209 1   45  0   209 1   45  0   209 1   44  0   207 1   
                                           44  0   207 1   45  0   205 1   45  0   205 1   46  0   205 1   46  0   205 1   48  0   205 1   48  0   205 1   48  0   207 1   7   255 42  0   207 1   51  0   207 1   7   255 46  0   203 1   46  0   211 1   7   255 50  2   120 1   49  2   121 1   49  2   
                                           121 1   47  2   122 1   47  2   122 1   46  2   121 1   46  2   121 1   45  2   120 1   45  2   120 1   46  2   118 1   46  2   118 1   47  2   118 1   47  2   118 1   49  2   118 1   49  2   118 1   50  2   120 1   7   255 43  2   120 1   52  2   120 1   
                                           7   255 47  2   115 1   47  2   124 1   7   255 93  0   36  1   93  0   49  1   93  0   49  1   105 0   52  1   105 0   52  1   162 0   52  1   162 0   52  1   174 0   49  1   174 0   49  1   174 0   36  1   174 0   36  1   162 0   32  1   162 0   32  1   
                                           105 0   32  1   105 0   32  1   93  0   36  1   7   255 93  0   191 1   93  0   203 1   93  0   203 1   105 0   207 1   105 0   207 1   162 0   207 1   162 0   207 1   174 0   203 1   174 0   203 1   174 0   191 1   174 0   191 1   162 0   187 1   162 0   
                                           187 1   105 0   187 1   105 0   187 1   93  0   191 1   0   252 65  117 116 111 67  65  68  32  83  108 105 100 101 13  10  26  0   86  2   106 6   234 2   99  219 79  1   2   0   52  18  7   255 7   255 136 0   53  1   48  1   53  1   48  1   53  1   48  
                                           1   96  1   48  1   96  1   246 1   96  1   246 1   96  1   246 1   154 1   246 1   154 1   48  1   154 1   48  1   154 1   48  1   198 1   48  1   198 1   136 0   198 1   136 0   198 1   136 0   53  1   7   255 136 0   53  1   136 0   53  1   7   255 136 
                                           0   53  1   136 0   53  1   7   255 225 1   140 1   220 1   144 1   220 1   144 1   213 1   146 1   213 1   146 1   207 1   146 1   207 1   146 1   201 1   144 1   201 1   144 1   196 1   140 1   196 1   140 1   192 1   135 1   192 1   135 1   190 1   129 
                                           1   190 1   129 1   190 1   122 1   190 1   122 1   192 1   116 1   192 1   116 1   196 1   111 1   196 1   111 1   201 1   107 1   201 1   107 1   207 1   105 1   207 1   105 1   213 1   105 1   213 1   105 1   220 1   107 1   220 1   107 1   225 1   111 
                                           1   7   255 225 1   111 1   225 1   140 1   7   255 143 1   84  1   143 1   94  1   143 1   94  1   152 1   96  1   152 1   96  1   197 1   96  1   197 1   96  1   206 1   94  1   206 1   94  1   206 1   84  1   206 1   84  1   197 1   81  1   197 1   81  
                                           1   152 1   81  1   152 1   81  1   143 1   84  1   7   255 143 1   56  1   143 1   65  1   143 1   65  1   152 1   68  1   152 1   68  1   197 1   68  1   197 1   68  1   206 1   65  1   206 1   65  1   206 1   56  1   206 1   56  1   197 1   53  1   197 
                                           1   53  1   152 1   53  1   152 1   53  1   143 1   56  1   7   255 143 1   157 1   143 1   167 1   143 1   167 1   152 1   170 1   152 1   170 1   197 1   170 1   197 1   170 1   206 1   167 1   206 1   167 1   206 1   157 1   206 1   157 1   197 1   154 
                                           1   197 1   154 1   152 1   154 1   152 1   154 1   143 1   157 1   7   255 143 1   185 1   143 1   195 1   143 1   195 1   152 1   198 1   152 1   198 1   197 1   198 1   197 1   198 1   206 1   195 1   206 1   195 1   206 1   185 1   206 1   185 1   197 
                                           1   182 1   197 1   182 1   152 1   182 1   152 1   182 1   143 1   185 1   7   255 214 1   84  1   214 1   94  1   214 1   94  1   223 1   96  1   223 1   96  1   12  2   96  1   12  2   96  1   21  2   94  1   21  2   94  1   21  2   84  1   21  2   84  
                                           1   12  2   81  1   12  2   81  1   223 1   81  1   223 1   81  1   214 1   84  1   7   255 214 1   56  1   214 1   65  1   214 1   65  1   223 1   68  1   223 1   68  1   12  2   68  1   12  2   68  1   21  2   65  1   21  2   65  1   21  2   56  1   21  
                                           )) "a")
 (_WriteStream FILE (vl-list->string (list 2   56  1   12  2   53  1   12  2   53  1   223 1   53  1   223 1   53  1   214 1   56  1   7   255 214 1   157 1   214 1   167 1   214 1   167 1   223 1   170 1   223 1   170 1   12  2   170 1   12  2   170 1   21  2   167 1   21  2   167 1   21  2   157 
                                           1   21  2   157 1   12  2   154 1   12  2   154 1   223 1   154 1   223 1   154 1   214 1   157 1   7   255 214 1   185 1   214 1   195 1   214 1   195 1   223 1   198 1   223 1   198 1   12  2   198 1   12  2   198 1   21  2   195 1   21  2   195 1   21  
                                           2   185 1   21  2   185 1   12  2   182 1   12  2   182 1   223 1   182 1   223 1   182 1   214 1   185 1   7   255 187 0   125 1   186 0   128 1   186 0   128 1   184 0   130 1   184 0   130 1   181 0   131 1   181 0   131 1   178 0   130 1   178 0   130 
                                           1   176 0   128 1   176 0   128 1   175 0   125 1   175 0   125 1   176 0   123 1   176 0   123 1   178 0   121 1   178 0   121 1   181 0   120 1   181 0   120 1   184 0   121 1   184 0   121 1   186 0   123 1   186 0   123 1   187 0   125 1   7   255 170 
                                           0   125 1   192 0   125 1   7   255 181 0   114 1   181 0   137 1   7   255 142 0   198 1   141 0   201 1   141 0   201 1   139 0   203 1   139 0   203 1   136 0   204 1   136 0   204 1   134 0   203 1   134 0   203 1   131 0   201 1   131 0   201 1   131 
                                           0   198 1   131 0   198 1   131 0   195 1   131 0   195 1   134 0   193 1   134 0   193 1   136 0   192 1   136 0   192 1   139 0   193 1   139 0   193 1   141 0   195 1   141 0   195 1   142 0   198 1   7   255 125 0   198 1   148 0   198 1   7   255 136 
                                           0   187 1   136 0   209 1   7   255 187 0   198 1   186 0   201 1   186 0   201 1   184 0   203 1   184 0   203 1   181 0   204 1   181 0   204 1   178 0   203 1   178 0   203 1   176 0   201 1   176 0   201 1   175 0   198 1   175 0   198 1   176 0   195 
                                           1   176 0   195 1   178 0   193 1   178 0   193 1   181 0   192 1   181 0   192 1   184 0   193 1   184 0   193 1   186 0   195 1   186 0   195 1   187 0   198 1   7   255 170 0   198 1   192 0   198 1   7   255 181 0   187 1   181 0   209 1   7   255 187 
                                           0   53  1   186 0   56  1   186 0   56  1   184 0   58  1   184 0   58  1   181 0   58  1   181 0   58  1   178 0   58  1   178 0   58  1   176 0   56  1   176 0   56  1   175 0   53  1   175 0   53  1   176 0   50  1   176 0   50  1   178 0   48  1   178 
                                           0   48  1   181 0   47  1   181 0   47  1   184 0   48  1   184 0   48  1   186 0   50  1   186 0   50  1   187 0   53  1   7   255 170 0   53  1   192 0   53  1   7   255 181 0   42  1   181 0   64  1   7   255 142 0   53  1   141 0   56  1   141 0   56  
                                           1   139 0   58  1   139 0   58  1   136 0   58  1   136 0   58  1   134 0   58  1   134 0   58  1   131 0   56  1   131 0   56  1   131 0   53  1   131 0   53  1   131 0   50  1   131 0   50  1   134 0   48  1   134 0   48  1   136 0   47  1   136 0   47  
                                           1   139 0   48  1   139 0   48  1   141 0   50  1   141 0   50  1   142 0   53  1   7   255 125 0   53  1   148 0   53  1   7   255 136 0   42  1   136 0   64  1   7   255 216 1   198 1   215 1   201 1   215 1   201 1   213 1   203 1   213 1   203 1   210 
                                           1   204 1   210 1   204 1   207 1   203 1   207 1   203 1   205 1   201 1   205 1   201 1   205 1   198 1   205 1   198 1   205 1   195 1   205 1   195 1   207 1   193 1   207 1   193 1   210 1   192 1   210 1   192 1   213 1   193 1   213 1   193 1   215 
                                           1   195 1   215 1   195 1   216 1   198 1   7   255 199 1   198 1   221 1   198 1   7   255 210 1   187 1   210 1   209 1   7   255 216 1   53  1   215 1   56  1   215 1   56  1   213 1   58  1   213 1   58  1   210 1   58  1   210 1   58  1   207 1   58  
                                           1   207 1   58  1   205 1   56  1   205 1   56  1   205 1   53  1   205 1   53  1   205 1   50  1   205 1   50  1   207 1   48  1   207 1   48  1   210 1   47  1   210 1   47  1   213 1   48  1   213 1   48  1   215 1   50  1   215 1   50  1   216 1   53  
                                           1   7   255 199 1   53  1   221 1   53  1   7   255 210 1   42  1   210 1   64  1   7   255 216 1   125 1   215 1   128 1   215 1   128 1   213 1   130 1   213 1   130 1   210 1   131 1   210 1   131 1   207 1   130 1   207 1   130 1   205 1   128 1   205 
                                           1   128 1   205 1   125 1   205 1   125 1   205 1   123 1   205 1   123 1   207 1   121 1   207 1   121 1   210 1   120 1   210 1   120 1   213 1   121 1   213 1   121 1   215 1   123 1   215 1   123 1   216 1   125 1   7   255 199 1   125 1   221 1   125 
                                           1   7   255 210 1   114 1   210 1   137 1   7   255 150 0   185 1   150 0   195 1   150 0   195 1   159 0   198 1   159 0   198 1   204 0   198 1   204 0   198 1   212 0   195 1   212 0   195 1   212 0   185 1   212 0   185 1   204 0   182 1   204 0   182 
                                           1   159 0   182 1   159 0   182 1   150 0   185 1   7   255 150 0   56  1   150 0   65  1   150 0   65  1   159 0   68  1   159 0   68  1   204 0   68  1   204 0   68  1   212 0   65  1   212 0   65  1   212 0   56  1   212 0   56  1   204 0   53  1   204 
                                           0   53  1   159 0   53  1   159 0   53  1   150 0   56  1   7   255 154 1   53  1   151 3   53  1   151 3   53  1   151 3   198 1   151 3   198 1   154 1   198 1   154 1   198 1   154 1   53  1   7   255 154 1   53  1   154 1   53  1   7   255 154 1   53  
                                           1   154 1   53  1   7   255 216 1   125 1   215 1   128 1   215 1   128 1   213 1   130 1   213 1   130 1   210 1   131 1   210 1   131 1   207 1   130 1   207 1   130 1   205 1   128 1   205 1   128 1   204 1   125 1   204 1   125 1   205 1   122 1   205 
                                           1   122 1   207 1   120 1   207 1   120 1   210 1   120 1   210 1   120 1   213 1   120 1   213 1   120 1   215 1   122 1   215 1   122 1   216 1   125 1   7   255 17  3   84  1   17  3   94  1   17  3   94  1   26  3   96  1   26  3   96  1   71  3   96  
                                           1   71  3   96  1   80  3   94  1   80  3   94  1   80  3   84  1   80  3   84  1   71  3   81  1   71  3   81  1   26  3   81  1   26  3   81  1   17  3   84  1   7   255 17  3   56  1   17  3   65  1   17  3   65  1   26  3   68  1   26  3   68  1   71  
                                           3   68  1   71  3   68  1   80  3   65  1   80  3   65  1   80  3   56  1   80  3   56  1   71  3   53  1   71  3   53  1   26  3   53  1   26  3   53  1   17  3   56  1   7   255 17  3   157 1   17  3   167 1   17  3   167 1   26  3   170 1   26  3   170 
                                           1   71  3   170 1   71  3   170 1   80  3   167 1   80  3   167 1   80  3   157 1   80  3   157 1   71  3   154 1   71  3   154 1   26  3   154 1   26  3   154 1   17  3   157 1   7   255 17  3   185 1   17  3   195 1   17  3   195 1   26  3   198 1   26  
                                           3   198 1   71  3   198 1   71  3   198 1   80  3   195 1   80  3   195 1   80  3   185 1   80  3   185 1   71  3   182 1   71  3   182 1   26  3   182 1   26  3   182 1   17  3   185 1   7   255 88  3   84  1   88  3   94  1   88  3   94  1   97  3   96  
                                           1   97  3   96  1   142 3   96  1   142 3   96  1   151 3   94  1   151 3   94  1   151 3   84  1   151 3   84  1   142 3   81  1   142 3   81  1   97  3   81  1   97  3   81  1   88  3   84  1   7   255 88  3   56  1   88  3   65  1   88  3   65  1   97  
                                           3   68  1   97  3   68  1   142 3   68  1   142 3   68  1   151 3   65  1   151 3   65  1   151 3   56  1   151 3   56  1   142 3   53  1   142 3   53  1   97  3   53  1   97  3   53  1   88  3   56  1   7   255 88  3   157 1   88  3   167 1   88  3   167 
                                           1   97  3   170 1   97  3   170 1   142 3   170 1   142 3   170 1   151 3   167 1   151 3   167 1   151 3   157 1   151 3   157 1   142 3   154 1   142 3   154 1   97  3   154 1   97  3   154 1   88  3   157 1   7   255 88  3   185 1   88  3   195 1   88  
                                           3   195 1   97  3   198 1   97  3   198 1   142 3   198 1   142 3   198 1   151 3   195 1   151 3   195 1   151 3   185 1   151 3   185 1   142 3   182 1   142 3   182 1   97  3   182 1   97  3   182 1   88  3   185 1   7   255 216 1   125 1   215 1   128 
                                           1   215 1   128 1   213 1   130 1   213 1   130 1   210 1   131 1   210 1   131 1   207 1   130 1   207 1   130 1   205 1   128 1   205 1   128 1   205 1   125 1   205 1   125 1   205 1   123 1   205 1   123 1   207 1   121 1   207 1   121 1   210 1   120 
                                           1   210 1   120 1   213 1   121 1   213 1   121 1   215 1   123 1   215 1   123 1   216 1   125 1   7   255 199 1   125 1   221 1   125 1   7   255 210 1   114 1   210 1   137 1   7   255 160 1   53  1   159 1   56  1   159 1   56  1   157 1   58  1   157 
                                           1   58  1   154 1   58  1   154 1   58  1   151 1   58  1   151 1   58  1   149 1   56  1   149 1   56  1   149 1   53  1   149 1   53  1   149 1   50  1   149 1   50  1   151 1   48  1   151 1   48  1   154 1   47  1   154 1   47  1   157 1   48  1   157 
                                           1   48  1   159 1   50  1   159 1   50  1   160 1   53  1   7   255 143 1   53  1   165 1   53  1   7   255 154 1   42  1   154 1   64  1   7   255 160 1   198 1   159 1   201 1   159 1   201 1   157 1   203 1   157 1   203 1   154 1   204 1   154 1   204 
                                           1   151 1   203 1   151 1   203 1   149 1   201 1   149 1   201 1   149 1   198 1   149 1   198 1   149 1   195 1   149 1   195 1   151 1   193 1   151 1   193 1   154 1   192 1   154 1   192 1   157 1   193 1   157 1   193 1   159 1   195 1   159 1   195 
                                           1   160 1   198 1   7   255 143 1   198 1   165 1   198 1   7   255 154 1   187 1   154 1   209 1   7   255 157 3   198 1   156 3   201 1   156 3   201 1   154 3   203 1   154 3   203 1   151 3   204 1   151 3   204 1   148 3   203 1   148 3   203 1   146 
                                           3   201 1   146 3   201 1   145 3   198 1   145 3   198 1   146 3   195 1   146 3   195 1   148 3   193 1   148 3   193 1   151 3   192 1   151 3   192 1   154 3   193 1   154 3   193 1   156 3   195 1   156 3   195 1   157 3   198 1   7   255 140 3   198 
                                           1   162 3   198 1   7   255 151 3   187 1   151 3   209 1   7   255 157 3   53  1   156 3   56  1   156 3   56  1   154 3   58  1   154 3   58  1   151 3   58  1   151 3   58  1   148 3   58  1   148 3   58  1   146 3   56  1   146 3   56  1   145 3   53  
                                           1   145 3   53  1   146 3   50  1   146 3   50  1   148 3   48  1   148 3   48  1   151 3   47  1   151 3   47  1   154 3   48  1   154 3   48  1   156 3   50  1   156 3   50  1   157 3   53  1   7   255 140 3   53  1   162 3   53  1   7   255 151 3   42  
                                           1   151 3   64  1   7   255 90  3   53  1   89  3   56  1   89  3   56  1   87  3   58  1   87  3   58  1   84  3   58  1   84  3   58  1   81  3   58  1   81  3   58  1   79  3   56  1   79  3   56  1   78  3   53  1   78  3   53  1   79  3   50  1   79  
                                           3   50  1   81  3   48  1   81  3   48  1   84  3   47  1   84  3   47  1   87  3   48  1   87  3   48  1   89  3   50  1   89  3   50  1   90  3   53  1   7   255 73  3   53  1   95  3   53  1   7   255 84  3   42  1   84  3   64  1   7   255 90  3   198 
                                           1   89  3   201 1   89  3   201 1   87  3   203 1   87  3   203 1   84  3   204 1   84  3   204 1   81  3   203 1   81  3   203 1   79  3   201 1   79  3   201 1   78  3   198 1   78  3   198 1   79  3   195 1   79  3   195 1   81  3   193 1   81  3   193 
                                           1   84  3   192 1   84  3   192 1   87  3   193 1   87  3   193 1   89  3   195 1   89  3   195 1   90  3   198 1   7   255 73  3   198 1   95  3   198 1   7   255 84  3   187 1   84  3   209 1   7   255 157 3   125 1   156 3   128 1   156 3   128 1   154 
                                           3   130 1   154 3   130 1   151 3   131 1   151 3   131 1   148 3   130 1   148 3   130 1   146 3   128 1   146 3   128 1   145 3   125 1   145 3   125 1   146 3   123 1   146 3   123 1   148 3   121 1   148 3   121 1   151 3   120 1   151 3   120 1   154 
                                           3   121 1   154 3   121 1   156 3   123 1   156 3   123 1   157 3   125 1   7   255 140 3   125 1   162 3   125 1   7   255 151 3   114 1   151 3   137 1   7   255 151 3   125 1   12  4   125 1   7   255 161 3   125 1   159 3   130 1   159 3   130 1   156 
                                           3   134 1   156 3   134 1   151 3   135 1   151 3   135 1   146 3   134 1   146 3   134 1   143 3   130 1   143 3   130 1   141 3   125 1   141 3   125 1   143 3   121 1   143 3   121 1   146 3   117 1   146 3   117 1   151 3   116 1   151 3   116 1   156 
                                           3   117 1   156 3   117 1   159 3   121 1   159 3   121 1   161 3   125 1   7   255 237 3   84  1   237 3   94  1   237 3   94  1   246 3   96  1   246 3   96  1   35  4   96  1   35  4   96  1   44  4   94  1   44  4   94  1   44  4   84  1   44  4   84  
                                           1   35  4   81  1   35  4   81  1   246 3   81  1   246 3   81  1   237 3   84  1   7   255 237 3   56  1   237 3   65  1   237 3   65  1   246 3   68  1   246 3   68  1   35  4   68  1   35  4   68  1   44  4   65  1   44  4   65  1   44  4   56  1   44  
                                           4   56  1   35  4   53  1   35  4   53  1   246 3   53  1   246 3   53  1   237 3   56  1   7   255 237 3   157 1   237 3   167 1   237 3   167 1   246 3   170 1   246 3   170 1   35  4   170 1   35  4   170 1   44  4   167 1   44  4   167 1   44  4   157 
                                           1   44  4   157 1   35  4   154 1   35  4   154 1   246 3   154 1   246 3   154 1   237 3   157 1   7   255 237 3   185 1   237 3   195 1   237 3   195 1   246 3   198 1   246 3   198 1   35  4   198 1   35  4   198 1   44  4   195 1   44  4   195 1   44  
                                           4   185 1   44  4   185 1   35  4   182 1   35  4   182 1   246 3   182 1   246 3   182 1   237 3   185 1   7   255 157 3   125 1   156 3   128 1   156 3   128 1   154 3   130 1   154 3   130 1   151 3   131 1   151 3   131 1   148 3   130 1   148 3   130 
                                           1   146 3   128 1   146 3   128 1   145 3   125 1   145 3   125 1   146 3   123 1   146 3   123 1   148 3   121 1   148 3   121 1   151 3   120 1   151 3   120 1   154 3   121 1   154 3   121 1   156 3   123 1   156 3   123 1   157 3   125 1   7   255 140 
                                           3   125 1   162 3   125 1   7   255 151 3   114 1   151 3   137 1   7   255 18  4   125 1   17  4   128 1   17  4   128 1   15  4   130 1   15  4   130 1   12  4   131 1   12  4   131 1   10  4   130 1   10  4   130 1   8   4   128 1   8   4   128 1   7   
                                           4   125 1   7   4   125 1   8   4   123 1   8   4   123 1   10  4   121 1   10  4   121 1   12  4   120 1   12  4   120 1   15  4   121 1   15  4   121 1   17  4   123 1   17  4   123 1   18  4   125 1   7   255 1   4   125 1   24  4   125 1   7   255 12  
                                           4   114 1   12  4   137 1   7   255 18  4   198 1   17  4   201 1   17  4   201 1   15  4   203 1   15  4   203 1   12  4   204 1   12  4   204 1   10  4   203 1   10  4   203 1   8   4   201 1   8   4   201 1   7   4   198 1   7   4   198 1   8   4   195 
                                           1   8   4   195 1   10  4   193 1   10  4   193 1   12  4   192 1   12  4   192 1   15  4   193 1   15  4   193 1   17  4   195 1   17  4   195 1   18  4   198 1   7   255 1   4   198 1   24  4   198 1   7   255 12  4   187 1   12  4   209 1   7   255 18  
                                           4   53  1   17  4   56  1   17  4   56  1   15  4   58  1   15  4   58  1   12  4   58  1   12  4   58  1   10  4   58  1   10  4   58  1   8   4   56  1   8   4   56  1   7   4   53  1   7   4   53  1   8   4   50  1   8   4   50  1   10  4   48  1   10  
                                           4   48  1   12  4   47  1   12  4   47  1   15  4   48  1   15  4   48  1   17  4   50  1   17  4   50  1   18  4   53  1   7   255 1   4   53  1   24  4   53  1   7   255 12  4   42  1   12  4   64  1   7   255 213 3   53  1   226 5   53  1   226 5   53  
                                           1   226 5   198 1   226 5   198 1   213 3   198 1   213 3   198 1   213 3   53  1   7   255 213 3   53  1   213 3   53  1   7   255 213 3   53  1   213 3   53  1   7   255 22  4   125 1   21  4   130 1   21  4   130 1   17  4   134 1   17  4   134 1   12  
                                           4   135 1   12  4   135 1   8   4   134 1   8   4   134 1   4   4   130 1   4   4   130 1   3   4   125 1   3   4   125 1   4   4   121 1   4   4   121 1   8   4   117 1   8   4   117 1   12  4   116 1   12  4   116 1   17  4   117 1   17  4   117 1   21  
                                           4   121 1   21  4   121 1   22  4   125 1   7   255 76  5   84  1   76  5   94  1   76  5   94  1   84  5   96  1   84  5   96  1   129 5   96  1   129 5   96  1   138 5   94  1   138 5   94  1   138 5   84  1   138 5   84  1   129 5   81  1   129 5   81  
                                           1   84  5   81  1   84  5   81  1   76  5   84  1   7   255 76  5   56  1   76  5   65  1   76  5   65  1   84  5   68  1   84  5   68  1   129 5   68  1   129 5   68  1   138 5   65  1   138 5   65  1   138 5   56  1   138 5   56  1   129 5   53  1   129 
                                           5   53  1   84  5   53  1   84  5   53  1   76  5   56  1   7   255 76  5   157 1   76  5   167 1   76  5   167 1   84  5   170 1   84  5   170 1   129 5   170 1   129 5   170 1   138 5   167 1   138 5   167 1   138 5   157 1   138 5   157 1   129 5   154 
                                           1   129 5   154 1   84  5   154 1   84  5   154 1   76  5   157 1   7   255 76  5   185 1   76  5   195 1   76  5   195 1   84  5   198 1   84  5   198 1   129 5   198 1   129 5   198 1   138 5   195 1   138 5   195 1   138 5   185 1   138 5   185 1   129 
                                           )) "a")
 (_WriteStream FILE (vl-list->string (list 5   182 1   129 5   182 1   84  5   182 1   84  5   182 1   76  5   185 1   7   255 147 5   84  1   147 5   94  1   147 5   94  1   155 5   96  1   155 5   96  1   200 5   96  1   200 5   96  1   209 5   94  1   209 5   94  1   209 5   84  1   209 5   84  
                                           1   200 5   81  1   200 5   81  1   155 5   81  1   155 5   81  1   147 5   84  1   7   255 147 5   56  1   147 5   65  1   147 5   65  1   155 5   68  1   155 5   68  1   200 5   68  1   200 5   68  1   209 5   65  1   209 5   65  1   209 5   56  1   209 
                                           5   56  1   200 5   53  1   200 5   53  1   155 5   53  1   155 5   53  1   147 5   56  1   7   255 147 5   157 1   147 5   167 1   147 5   167 1   155 5   170 1   155 5   170 1   200 5   170 1   200 5   170 1   209 5   167 1   209 5   167 1   209 5   157 
                                           1   209 5   157 1   200 5   154 1   200 5   154 1   155 5   154 1   155 5   154 1   147 5   157 1   7   255 147 5   185 1   147 5   195 1   147 5   195 1   155 5   198 1   155 5   198 1   200 5   198 1   200 5   198 1   209 5   195 1   209 5   195 1   209 
                                           5   185 1   209 5   185 1   200 5   182 1   200 5   182 1   155 5   182 1   155 5   182 1   147 5   185 1   7   255 218 3   53  1   217 3   56  1   217 3   56  1   215 3   58  1   215 3   58  1   213 3   58  1   213 3   58  1   210 3   58  1   210 3   58  
                                           1   208 3   56  1   208 3   56  1   207 3   53  1   207 3   53  1   208 3   50  1   208 3   50  1   210 3   48  1   210 3   48  1   213 3   47  1   213 3   47  1   215 3   48  1   215 3   48  1   217 3   50  1   217 3   50  1   218 3   53  1   7   255 201 
                                           3   53  1   224 3   53  1   7   255 213 3   42  1   213 3   64  1   7   255 232 5   53  1   231 5   56  1   231 5   56  1   229 5   58  1   229 5   58  1   226 5   58  1   226 5   58  1   223 5   58  1   223 5   58  1   221 5   56  1   221 5   56  1   221 
                                           5   53  1   221 5   53  1   221 5   50  1   221 5   50  1   223 5   48  1   223 5   48  1   226 5   47  1   226 5   47  1   229 5   48  1   229 5   48  1   231 5   50  1   231 5   50  1   232 5   53  1   7   255 215 5   53  1   237 5   53  1   7   255 226 
                                           5   42  1   226 5   64  1   7   255 232 5   198 1   231 5   201 1   231 5   201 1   229 5   203 1   229 5   203 1   226 5   204 1   226 5   204 1   223 5   203 1   223 5   203 1   221 5   201 1   221 5   201 1   221 5   198 1   221 5   198 1   221 5   195 
                                           1   221 5   195 1   223 5   193 1   223 5   193 1   226 5   192 1   226 5   192 1   229 5   193 1   229 5   193 1   231 5   195 1   231 5   195 1   232 5   198 1   7   255 215 5   198 1   237 5   198 1   7   255 226 5   187 1   226 5   209 1   7   255 218 
                                           3   198 1   217 3   201 1   217 3   201 1   215 3   203 1   215 3   203 1   213 3   204 1   213 3   204 1   210 3   203 1   210 3   203 1   208 3   201 1   208 3   201 1   207 3   198 1   207 3   198 1   208 3   195 1   208 3   195 1   210 3   193 1   210 
                                           3   193 1   213 3   192 1   213 3   192 1   215 3   193 1   215 3   193 1   217 3   195 1   217 3   195 1   218 3   198 1   7   255 201 3   198 1   224 3   198 1   7   255 213 3   187 1   213 3   209 1   7   255 18  4   125 1   17  4   128 1   17  4   128 
                                           1   15  4   130 1   15  4   130 1   12  4   131 1   12  4   131 1   10  4   130 1   10  4   130 1   8   4   128 1   8   4   128 1   7   4   125 1   7   4   125 1   8   4   123 1   8   4   123 1   10  4   121 1   10  4   121 1   12  4   120 1   12  4   120 
                                           1   15  4   121 1   15  4   121 1   17  4   123 1   17  4   123 1   18  4   125 1   7   255 1   4   125 1   24  4   125 1   7   255 12  4   114 1   12  4   137 1   7   255 148 5   125 1   147 5   128 1   147 5   128 1   145 5   130 1   145 5   130 1   142 
                                           5   131 1   142 5   131 1   139 5   130 1   139 5   130 1   137 5   128 1   137 5   128 1   137 5   125 1   137 5   125 1   137 5   123 1   137 5   123 1   139 5   121 1   139 5   121 1   142 5   120 1   142 5   120 1   145 5   121 1   145 5   121 1   147 
                                           5   123 1   147 5   123 1   148 5   125 1   7   255 131 5   125 1   153 5   125 1   7   255 142 5   114 1   142 5   137 1   7   255 148 5   198 1   147 5   201 1   147 5   201 1   145 5   203 1   145 5   203 1   142 5   204 1   142 5   204 1   139 5   203 
                                           1   139 5   203 1   137 5   201 1   137 5   201 1   137 5   198 1   137 5   198 1   137 5   195 1   137 5   195 1   139 5   193 1   139 5   193 1   142 5   192 1   142 5   192 1   145 5   193 1   145 5   193 1   147 5   195 1   147 5   195 1   148 5   198 
                                           1   7   255 131 5   198 1   153 5   198 1   7   255 142 5   187 1   142 5   209 1   7   255 148 5   53  1   147 5   56  1   147 5   56  1   145 5   58  1   145 5   58  1   142 5   58  1   142 5   58  1   139 5   58  1   139 5   58  1   137 5   56  1   137 
                                           5   56  1   137 5   53  1   137 5   53  1   137 5   50  1   137 5   50  1   139 5   48  1   139 5   48  1   142 5   47  1   142 5   47  1   145 5   48  1   145 5   48  1   147 5   50  1   147 5   50  1   148 5   53  1   7   255 131 5   53  1   153 5   53  
                                           1   7   255 142 5   42  1   142 5   64  1   0   252 65  117 116 111 67  65  68  32  83  108 105 100 101 13  10  26  0   86  2   73  6   247 2   97  120 67  1   2   0   52  18  7   255 7   255 197 1   22  1   29  6   22  1   29  6   22  1   29  6   224 1   
                                           29  6   224 1   197 1   224 1   197 1   224 1   197 1   22  1   7   255 197 1   22  1   197 1   22  1   7   255 197 1   22  1   197 1   22  1   7   255 197 1   22  1   197 1   22  1   7   255 76  5   66  1   76  5   79  1   76  5   79  1   88  5   83  1   
                                           88  5   83  1   151 5   83  1   151 5   83  1   163 5   79  1   163 5   79  1   163 5   66  1   163 5   66  1   151 5   61  1   151 5   61  1   88  5   61  1   88  5   61  1   76  5   66  1   7   255 76  5   26  1   76  5   40  1   76  5   40  1   88  5   
                                           44  1   88  5   44  1   151 5   44  1   151 5   44  1   163 5   40  1   163 5   40  1   163 5   26  1   163 5   26  1   151 5   22  1   151 5   22  1   88  5   22  1   88  5   22  1   76  5   26  1   7   255 76  5   168 1   76  5   181 1   76  5   181 1   
                                           88  5   185 1   88  5   185 1   151 5   185 1   151 5   185 1   163 5   181 1   163 5   181 1   163 5   168 1   163 5   168 1   151 5   164 1   151 5   164 1   88  5   164 1   88  5   164 1   76  5   168 1   7   255 76  5   207 1   76  5   220 1   76  5   
                                           220 1   88  5   224 1   88  5   224 1   151 5   224 1   151 5   224 1   163 5   220 1   163 5   220 1   163 5   207 1   163 5   207 1   151 5   203 1   151 5   203 1   88  5   203 1   88  5   203 1   76  5   207 1   7   255 175 5   66  1   175 5   79  1   
                                           175 5   79  1   187 5   83  1   187 5   83  1   249 5   83  1   249 5   83  1   6   6   79  1   6   6   79  1   6   6   66  1   6   6   66  1   249 5   61  1   249 5   61  1   187 5   61  1   187 5   61  1   175 5   66  1   7   255 175 5   26  1   175 5   
                                           40  1   175 5   40  1   187 5   44  1   187 5   44  1   249 5   44  1   249 5   44  1   6   6   40  1   6   6   40  1   6   6   26  1   6   6   26  1   249 5   22  1   249 5   22  1   187 5   22  1   187 5   22  1   175 5   26  1   7   255 175 5   168 1   
                                           175 5   181 1   175 5   181 1   187 5   185 1   187 5   185 1   249 5   185 1   249 5   185 1   6   6   181 1   6   6   181 1   6   6   168 1   6   6   168 1   249 5   164 1   249 5   164 1   187 5   164 1   187 5   164 1   175 5   168 1   7   255 175 5   
                                           207 1   175 5   220 1   175 5   220 1   187 5   224 1   187 5   224 1   249 5   224 1   249 5   224 1   6   6   220 1   6   6   220 1   6   6   207 1   6   6   207 1   249 5   203 1   249 5   203 1   187 5   203 1   187 5   203 1   175 5   207 1   7   255 
                                           50  2   123 1   49  2   127 1   49  2   127 1   46  2   130 1   46  2   130 1   42  2   131 1   42  2   131 1   38  2   130 1   38  2   130 1   36  2   127 1   36  2   127 1   35  2   123 1   35  2   123 1   36  2   120 1   36  2   120 1   38  2   117 1   
                                           38  2   117 1   42  2   116 1   42  2   116 1   46  2   117 1   46  2   117 1   49  2   120 1   49  2   120 1   50  2   123 1   7   255 27  2   123 1   58  2   123 1   7   255 42  2   108 1   42  2   139 1   7   255 205 1   224 1   204 1   228 1   204 1   
                                           228 1   201 1   231 1   201 1   231 1   197 1   232 1   197 1   232 1   193 1   231 1   193 1   231 1   190 1   228 1   190 1   228 1   189 1   224 1   189 1   224 1   190 1   221 1   190 1   221 1   193 1   218 1   193 1   218 1   197 1   217 1   197 1   
                                           217 1   201 1   218 1   201 1   218 1   204 1   221 1   204 1   221 1   205 1   224 1   7   255 182 1   224 1   213 1   224 1   7   255 197 1   209 1   197 1   240 1   7   255 205 1   22  1   204 1   26  1   204 1   26  1   201 1   29  1   201 1   29  1   
                                           197 1   30  1   197 1   30  1   193 1   29  1   193 1   29  1   190 1   26  1   190 1   26  1   189 1   22  1   189 1   22  1   190 1   19  1   190 1   19  1   193 1   16  1   193 1   16  1   197 1   15  1   197 1   15  1   201 1   16  1   201 1   16  1   
                                           204 1   19  1   204 1   19  1   205 1   22  1   7   255 182 1   22  1   213 1   22  1   7   255 197 1   7   1   197 1   38  1   7   255 37  6   22  1   36  6   26  1   36  6   26  1   33  6   29  1   33  6   29  1   29  6   30  1   29  6   30  1   25  6   
                                           29  1   25  6   29  1   23  6   26  1   23  6   26  1   22  6   22  1   22  6   22  1   23  6   19  1   23  6   19  1   25  6   16  1   25  6   16  1   29  6   15  1   29  6   15  1   33  6   16  1   33  6   16  1   36  6   19  1   36  6   19  1   37  6   
                                           22  1   7   255 14  6   22  1   45  6   22  1   7   255 29  6   7   1   29  6   38  1   7   255 37  6   224 1   36  6   228 1   36  6   228 1   33  6   231 1   33  6   231 1   29  6   232 1   29  6   232 1   25  6   231 1   25  6   231 1   23  6   228 1   
                                           23  6   228 1   22  6   224 1   22  6   224 1   23  6   221 1   23  6   221 1   25  6   218 1   25  6   218 1   29  6   217 1   29  6   217 1   33  6   218 1   33  6   218 1   36  6   221 1   36  6   221 1   37  6   224 1   7   255 14  6   224 1   45  6   
                                           224 1   7   255 29  6   209 1   29  6   240 1   7   255 176 5   224 1   175 5   228 1   175 5   228 1   173 5   231 1   173 5   231 1   169 5   232 1   169 5   232 1   165 5   231 1   165 5   231 1   162 5   228 1   162 5   228 1   161 5   224 1   161 5   
                                           224 1   162 5   221 1   162 5   221 1   165 5   218 1   165 5   218 1   169 5   217 1   169 5   217 1   173 5   218 1   173 5   218 1   175 5   221 1   175 5   221 1   176 5   224 1   7   255 153 5   224 1   184 5   224 1   7   255 169 5   209 1   169 5   
                                           240 1   7   255 176 5   22  1   175 5   26  1   175 5   26  1   173 5   29  1   173 5   29  1   169 5   30  1   169 5   30  1   165 5   29  1   165 5   29  1   162 5   26  1   162 5   26  1   161 5   22  1   161 5   22  1   162 5   19  1   162 5   19  1   
                                           165 5   16  1   165 5   16  1   169 5   15  1   169 5   15  1   173 5   16  1   173 5   16  1   175 5   19  1   175 5   19  1   176 5   22  1   7   255 153 5   22  1   184 5   22  1   7   255 169 5   7   1   169 5   38  1   7   255 49  0   22  1   119 1   
                                           22  1   119 1   22  1   119 1   83  1   119 1   83  1   92  2   83  1   92  2   83  1   92  2   164 1   92  2   164 1   119 1   164 1   119 1   164 1   119 1   224 1   119 1   224 1   49  0   224 1   49  0   224 1   49  0   22  1   7   255 49  0   22  1   
                                           49  0   22  1   7   255 49  0   22  1   49  0   22  1   7   255 49  0   22  1   49  0   22  1   7   255 63  2   144 1   60  2   146 1   60  2   146 1   57  2   148 1   57  2   148 1   53  2   150 1   53  2   150 1   50  2   151 1   50  2   151 1   46  2   
                                           152 1   46  2   152 1   42  2   152 1   42  2   152 1   39  2   152 1   39  2   152 1   35  2   151 1   35  2   151 1   31  2   150 1   31  2   150 1   28  2   148 1   28  2   148 1   25  2   146 1   25  2   146 1   22  2   144 1   22  2   144 1   19  2   
                                           141 1   19  2   141 1   17  2   138 1   17  2   138 1   16  2   134 1   16  2   134 1   14  2   131 1   14  2   131 1   14  2   127 1   14  2   127 1   13  2   123 1   13  2   123 1   14  2   120 1   14  2   120 1   14  2   116 1   14  2   116 1   16  2   
                                           112 1   16  2   112 1   17  2   109 1   17  2   109 1   19  2   106 1   19  2   106 1   22  2   103 1   22  2   103 1   25  2   101 1   25  2   101 1   28  2   98  1   28  2   98  1   31  2   97  1   31  2   97  1   35  2   96  1   35  2   96  1   39  2   
                                           95  1   39  2   95  1   42  2   95  1   42  2   95  1   46  2   95  1   46  2   95  1   50  2   96  1   50  2   96  1   53  2   97  1   53  2   97  1   57  2   98  1   57  2   98  1   60  2   101 1   60  2   101 1   63  2   103 1   7   255 63  2   103 1   
                                           63  2   144 1   7   255 205 1   66  1   205 1   79  1   205 1   79  1   218 1   83  1   218 1   83  1   24  2   83  1   24  2   83  1   36  2   79  1   36  2   79  1   36  2   66  1   36  2   66  1   24  2   61  1   24  2   61  1   218 1   61  1   218 1   
                                           61  1   205 1   66  1   7   255 205 1   26  1   205 1   40  1   205 1   40  1   218 1   44  1   218 1   44  1   24  2   44  1   24  2   44  1   36  2   40  1   36  2   40  1   36  2   26  1   36  2   26  1   24  2   22  1   24  2   22  1   218 1   22  1   
                                           218 1   22  1   205 1   26  1   7   255 205 1   168 1   205 1   181 1   205 1   181 1   218 1   185 1   218 1   185 1   24  2   185 1   24  2   185 1   36  2   181 1   36  2   181 1   36  2   168 1   36  2   168 1   24  2   164 1   24  2   164 1   218 1   
                                           164 1   218 1   164 1   205 1   168 1   7   255 205 1   207 1   205 1   220 1   205 1   220 1   218 1   224 1   218 1   224 1   24  2   224 1   24  2   224 1   36  2   220 1   36  2   220 1   36  2   207 1   36  2   207 1   24  2   203 1   24  2   203 1   
                                           218 1   203 1   218 1   203 1   205 1   207 1   7   255 48  2   66  1   48  2   79  1   48  2   79  1   60  2   83  1   60  2   83  1   123 2   83  1   123 2   83  1   135 2   79  1   135 2   79  1   135 2   66  1   135 2   66  1   123 2   61  1   123 2   
                                           61  1   60  2   61  1   60  2   61  1   48  2   66  1   7   255 48  2   26  1   48  2   40  1   48  2   40  1   60  2   44  1   60  2   44  1   123 2   44  1   123 2   44  1   135 2   40  1   135 2   40  1   135 2   26  1   135 2   26  1   123 2   22  1   
                                           123 2   22  1   60  2   22  1   60  2   22  1   48  2   26  1   7   255 48  2   168 1   48  2   181 1   48  2   181 1   60  2   185 1   60  2   185 1   123 2   185 1   123 2   185 1   135 2   181 1   135 2   181 1   135 2   168 1   135 2   168 1   123 2   
                                           164 1   123 2   164 1   60  2   164 1   60  2   164 1   48  2   168 1   7   255 48  2   207 1   48  2   220 1   48  2   220 1   60  2   224 1   60  2   224 1   123 2   224 1   123 2   224 1   135 2   220 1   135 2   220 1   135 2   207 1   135 2   207 1   
                                           123 2   203 1   123 2   203 1   60  2   203 1   60  2   203 1   48  2   207 1   7   255 83  0   26  1   83  0   40  1   83  0   40  1   95  0   44  1   95  0   44  1   158 0   44  1   158 0   44  1   170 0   40  1   170 0   40  1   170 0   26  1   170 0   
                                           26  1   158 0   22  1   158 0   22  1   95  0   22  1   95  0   22  1   83  0   26  1   7   255 83  0   207 1   83  0   220 1   83  0   220 1   95  0   224 1   95  0   224 1   158 0   224 1   158 0   224 1   170 0   220 1   170 0   220 1   170 0   207 1   
                                           170 0   207 1   158 0   203 1   158 0   203 1   95  0   203 1   95  0   203 1   83  0   207 1   7   255 134 0   123 1   134 0   125 1   134 0   125 1   133 0   127 1   133 0   127 1   132 0   129 1   132 0   129 1   130 0   130 1   130 0   130 1   129 0   
                                           131 1   129 0   131 1   127 0   131 1   127 0   131 1   125 0   131 1   125 0   131 1   123 0   130 1   123 0   130 1   121 0   129 1   121 0   129 1   120 0   127 1   120 0   127 1   119 0   125 1   119 0   125 1   119 0   123 1   119 0   123 1   119 0   
                                           121 1   119 0   121 1   120 0   120 1   120 0   120 1   121 0   118 1   121 0   118 1   123 0   117 1   123 0   117 1   125 0   116 1   125 0   116 1   127 0   116 1   127 0   116 1   129 0   116 1   129 0   116 1   130 0   117 1   130 0   117 1   132 0   
                                           118 1   132 0   118 1   133 0   120 1   133 0   120 1   134 0   121 1   134 0   121 1   134 0   123 1   7   255 111 0   123 1   142 0   123 1   7   255 127 0   108 1   127 0   139 1   7   255 57  0   224 1   56  0   226 1   56  0   226 1   56  0   228 1   
                                           56  0   228 1   54  0   230 1   54  0   230 1   53  0   231 1   53  0   231 1   51  0   232 1   51  0   232 1   49  0   232 1   49  0   232 1   47  0   232 1   47  0   232 1   45  0   231 1   45  0   231 1   43  0   230 1   43  0   230 1   42  0   228 1   
                                           42  0   228 1   41  0   226 1   41  0   226 1   41  0   224 1   41  0   224 1   41  0   222 1   41  0   222 1   42  0   221 1   42  0   221 1   43  0   219 1   43  0   219 1   45  0   218 1   45  0   218 1   47  0   217 1   47  0   217 1   49  0   217 1   
                                           )) "a")
 (_WriteStream FILE (vl-list->string (list 49  0   217 1   51  0   217 1   51  0   217 1   53  0   218 1   53  0   218 1   54  0   219 1   54  0   219 1   56  0   221 1   56  0   221 1   56  0   222 1   56  0   222 1   57  0   224 1   7   255 33  0   224 1   64  0   224 1   7   255 49  0   209 1   
                                           49  0   240 1   7   255 57  0   22  1   56  0   24  1   56  0   24  1   56  0   26  1   56  0   26  1   54  0   28  1   54  0   28  1   53  0   29  1   53  0   29  1   51  0   30  1   51  0   30  1   49  0   30  1   49  0   30  1   47  0   30  1   47  0   
                                           30  1   45  0   29  1   45  0   29  1   43  0   28  1   43  0   28  1   42  0   26  1   42  0   26  1   41  0   24  1   41  0   24  1   41  0   22  1   41  0   22  1   41  0   20  1   41  0   20  1   42  0   19  1   42  0   19  1   43  0   17  1   43  0   
                                           17  1   45  0   16  1   45  0   16  1   47  0   15  1   47  0   15  1   49  0   15  1   49  0   15  1   51  0   15  1   51  0   15  1   53  0   16  1   53  0   16  1   54  0   17  1   54  0   17  1   56  0   19  1   56  0   19  1   56  0   20  1   56  0   
                                           20  1   57  0   22  1   7   255 33  0   22  1   64  0   22  1   7   255 49  0   7   1   49  0   38  1   7   255 50  2   123 1   50  2   125 1   50  2   125 1   49  2   127 1   49  2   127 1   48  2   129 1   48  2   129 1   46  2   130 1   46  2   130 1   
                                           44  2   131 1   44  2   131 1   42  2   131 1   42  2   131 1   40  2   131 1   40  2   131 1   38  2   130 1   38  2   130 1   37  2   129 1   37  2   129 1   36  2   127 1   36  2   127 1   35  2   125 1   35  2   125 1   35  2   123 1   35  2   123 1   
                                           35  2   121 1   35  2   121 1   36  2   120 1   36  2   120 1   37  2   118 1   37  2   118 1   38  2   117 1   38  2   117 1   40  2   116 1   40  2   116 1   42  2   116 1   42  2   116 1   44  2   116 1   44  2   116 1   46  2   117 1   46  2   117 1   
                                           48  2   118 1   48  2   118 1   49  2   120 1   49  2   120 1   50  2   121 1   50  2   121 1   50  2   123 1   7   255 27  2   123 1   58  2   123 1   7   255 42  2   108 1   42  2   139 1   7   255 50  2   224 1   50  2   226 1   50  2   226 1   49  2   
                                           228 1   49  2   228 1   48  2   230 1   48  2   230 1   46  2   231 1   46  2   231 1   44  2   232 1   44  2   232 1   42  2   232 1   42  2   232 1   40  2   232 1   40  2   232 1   38  2   231 1   38  2   231 1   37  2   230 1   37  2   230 1   36  2   
                                           228 1   36  2   228 1   35  2   226 1   35  2   226 1   35  2   224 1   35  2   224 1   35  2   222 1   35  2   222 1   36  2   221 1   36  2   221 1   37  2   219 1   37  2   219 1   38  2   218 1   38  2   218 1   40  2   217 1   40  2   217 1   42  2   
                                           217 1   42  2   217 1   44  2   217 1   44  2   217 1   46  2   218 1   46  2   218 1   48  2   219 1   48  2   219 1   49  2   221 1   49  2   221 1   50  2   222 1   50  2   222 1   50  2   224 1   7   255 27  2   224 1   58  2   224 1   7   255 42  2   
                                           209 1   42  2   240 1   7   255 50  2   22  1   50  2   24  1   50  2   24  1   49  2   26  1   49  2   26  1   48  2   28  1   48  2   28  1   46  2   29  1   46  2   29  1   44  2   30  1   44  2   30  1   42  2   30  1   42  2   30  1   40  2   30  1   
                                           40  2   30  1   38  2   29  1   38  2   29  1   37  2   28  1   37  2   28  1   36  2   26  1   36  2   26  1   35  2   24  1   35  2   24  1   35  2   22  1   35  2   22  1   35  2   20  1   35  2   20  1   36  2   19  1   36  2   19  1   37  2   17  1   
                                           37  2   17  1   38  2   16  1   38  2   16  1   40  2   15  1   40  2   15  1   42  2   15  1   42  2   15  1   44  2   15  1   44  2   15  1   46  2   16  1   46  2   16  1   48  2   17  1   48  2   17  1   49  2   19  1   49  2   19  1   50  2   20  1   
                                           50  2   20  1   50  2   22  1   7   255 27  2   22  1   58  2   22  1   7   255 42  2   7   1   42  2   38  1   7   255 134 0   224 1   134 0   226 1   134 0   226 1   133 0   228 1   133 0   228 1   132 0   230 1   132 0   230 1   130 0   231 1   130 0   
                                           231 1   129 0   232 1   129 0   232 1   127 0   232 1   127 0   232 1   125 0   232 1   125 0   232 1   123 0   231 1   123 0   231 1   121 0   230 1   121 0   230 1   120 0   228 1   120 0   228 1   119 0   226 1   119 0   226 1   119 0   224 1   119 0   
                                           224 1   119 0   222 1   119 0   222 1   120 0   221 1   120 0   221 1   121 0   219 1   121 0   219 1   123 0   218 1   123 0   218 1   125 0   217 1   125 0   217 1   127 0   217 1   127 0   217 1   129 0   217 1   129 0   217 1   130 0   218 1   130 0   
                                           218 1   132 0   219 1   132 0   219 1   133 0   221 1   133 0   221 1   134 0   222 1   134 0   222 1   134 0   224 1   7   255 111 0   224 1   142 0   224 1   7   255 127 0   209 1   127 0   240 1   7   255 134 0   22  1   134 0   24  1   134 0   24  1   
                                           133 0   26  1   133 0   26  1   132 0   28  1   132 0   28  1   130 0   29  1   130 0   29  1   129 0   30  1   129 0   30  1   127 0   30  1   127 0   30  1   125 0   30  1   125 0   30  1   123 0   29  1   123 0   29  1   121 0   28  1   121 0   28  1   
                                           120 0   26  1   120 0   26  1   119 0   24  1   119 0   24  1   119 0   22  1   119 0   22  1   119 0   20  1   119 0   20  1   120 0   19  1   120 0   19  1   121 0   17  1   121 0   17  1   123 0   16  1   123 0   16  1   125 0   15  1   125 0   15  1   
                                           127 0   15  1   127 0   15  1   129 0   15  1   129 0   15  1   130 0   16  1   130 0   16  1   132 0   17  1   132 0   17  1   133 0   19  1   133 0   19  1   134 0   20  1   134 0   20  1   134 0   22  1   7   255 111 0   22  1   142 0   22  1   7   255 
                                           127 0   7   1   127 0   38  1   0   252 65  117 116 111 67  65  68  32  83  108 105 100 101 13  10  26  0   86  2   73  6   247 2   97  120 67  1   2   0   52  18  7   255 7   255 105 0   198 0   253 5   198 0   253 5   198 0   253 5   66  2   253 5   66  
                                           2   105 0   66  2   105 0   66  2   105 0   198 0   7   255 105 0   198 0   105 0   198 0   7   255 105 0   198 0   105 0   198 0   7   255 105 0   198 0   105 0   198 0   7   255 144 4   21  1   144 4   45  1   144 4   45  1   166 4   53  1   166 4   53  
                                           1   25  5   53  1   25  5   53  1   47  5   45  1   47  5   45  1   47  5   21  1   47  5   21  1   25  5   13  1   25  5   13  1   166 4   13  1   166 4   13  1   144 4   21  1   7   255 144 4   205 0   144 4   230 0   144 4   230 0   166 4   237 0   166 
                                           4   237 0   25  5   237 0   25  5   237 0   47  5   230 0   47  5   230 0   47  5   205 0   47  5   205 0   25  5   198 0   25  5   198 0   166 4   198 0   166 4   198 0   144 4   205 0   7   255 144 4   219 1   144 4   244 1   144 4   244 1   166 4   251 
                                           1   166 4   251 1   25  5   251 1   25  5   251 1   47  5   244 1   47  5   244 1   47  5   219 1   47  5   219 1   25  5   211 1   25  5   211 1   166 4   211 1   166 4   211 1   144 4   219 1   7   255 144 4   34  2   144 4   59  2   144 4   59  2   166 
                                           4   66  2   166 4   66  2   25  5   66  2   25  5   66  2   47  5   59  2   47  5   59  2   47  5   34  2   47  5   34  2   25  5   27  2   25  5   27  2   166 4   27  2   166 4   27  2   144 4   34  2   7   255 44  1   132 1   43  1   135 1   43  1   135 
                                           1   39  1   137 1   39  1   137 1   36  1   135 1   36  1   135 1   34  1   132 1   34  1   132 1   36  1   129 1   36  1   129 1   39  1   127 1   39  1   127 1   43  1   129 1   43  1   129 1   44  1   132 1   7   255 30  1   132 1   49  1   132 1   7   
                                           255 39  1   123 1   39  1   142 1   7   255 109 0   198 0   108 0   201 0   108 0   201 0   105 0   203 0   105 0   203 0   101 0   201 0   101 0   201 0   100 0   198 0   100 0   198 0   101 0   194 0   101 0   194 0   105 0   193 0   105 0   193 0   108 
                                           0   194 0   108 0   194 0   109 0   198 0   7   255 95  0   198 0   114 0   198 0   7   255 105 0   188 0   105 0   207 0   7   255 44  1   198 0   43  1   201 0   43  1   201 0   39  1   203 0   39  1   203 0   36  1   201 0   36  1   201 0   34  1   198 
                                           0   34  1   198 0   36  1   194 0   36  1   194 0   39  1   193 0   39  1   193 0   43  1   194 0   43  1   194 0   44  1   198 0   7   255 30  1   198 0   49  1   198 0   7   255 39  1   188 0   39  1   207 0   7   255 228 4   198 0   227 4   201 0   227 
                                           4   201 0   223 4   203 0   223 4   203 0   220 4   201 0   220 4   201 0   219 4   198 0   219 4   198 0   220 4   194 0   220 4   194 0   223 4   193 0   223 4   193 0   227 4   194 0   227 4   194 0   228 4   198 0   7   255 214 4   198 0   233 4   198 
                                           0   7   255 223 4   188 0   223 4   207 0   7   255 2   6   198 0   1   6   201 0   1   6   201 0   253 5   203 0   253 5   203 0   250 5   201 0   250 5   201 0   248 5   198 0   248 5   198 0   250 5   194 0   250 5   194 0   253 5   193 0   253 5   193 
                                           0   1   6   194 0   1   6   194 0   2   6   198 0   7   255 244 5   198 0   7   6   198 0   7   255 253 5   188 0   253 5   207 0   7   255 2   6   66  2   1   6   70  2   1   6   70  2   253 5   71  2   253 5   71  2   250 5   70  2   250 5   70  2   248 
                                           5   66  2   248 5   66  2   250 5   63  2   250 5   63  2   253 5   62  2   253 5   62  2   1   6   63  2   1   6   63  2   2   6   66  2   7   255 244 5   66  2   7   6   66  2   7   255 253 5   57  2   253 5   76  2   7   255 228 4   66  2   227 4   70  
                                           2   227 4   70  2   223 4   71  2   223 4   71  2   220 4   70  2   220 4   70  2   219 4   66  2   219 4   66  2   220 4   63  2   220 4   63  2   223 4   62  2   223 4   62  2   227 4   63  2   227 4   63  2   228 4   66  2   7   255 214 4   66  2   233 
                                           4   66  2   7   255 223 4   57  2   223 4   76  2   7   255 44  1   66  2   43  1   70  2   43  1   70  2   39  1   71  2   39  1   71  2   36  1   70  2   36  1   70  2   34  1   66  2   34  1   66  2   36  1   63  2   36  1   63  2   39  1   62  2   39  
                                           1   62  2   43  1   63  2   43  1   63  2   44  1   66  2   7   255 30  1   66  2   49  1   66  2   7   255 39  1   57  2   39  1   76  2   7   255 109 0   66  2   108 0   70  2   108 0   70  2   105 0   71  2   105 0   71  2   101 0   70  2   101 0   70  
                                           2   100 0   66  2   100 0   66  2   101 0   63  2   101 0   63  2   105 0   62  2   105 0   62  2   108 0   63  2   108 0   63  2   109 0   66  2   7   255 95  0   66  2   114 0   66  2   7   255 105 0   57  2   105 0   76  2   51  255 51  255 105 0   198 
                                           0   253 5   198 0   253 5   198 0   253 5   66  2   253 5   66  2   105 0   66  2   105 0   66  2   105 0   198 0   7   255 7   255 216 0   34  2   216 0   59  2   216 0   59  2   238 0   66  2   238 0   66  2   96  1   66  2   96  1   66  2   119 1   59  
                                           2   119 1   59  2   119 1   34  2   119 1   34  2   96  1   27  2   96  1   27  2   238 0   27  2   238 0   27  2   216 0   34  2   7   255 216 0   205 0   216 0   230 0   216 0   230 0   238 0   237 0   238 0   237 0   96  1   237 0   96  1   237 0   119 
                                           1   230 0   119 1   230 0   119 1   205 0   119 1   205 0   96  1   198 0   96  1   198 0   238 0   198 0   238 0   198 0   216 0   205 0   0   252 65  117 116 111 67  65  68  32  83  108 105 100 101 13  10  26  0   86  2   106 6   234 2   99  219 79  1   
                                           2   0   52  18  7   255 7   255 82  0   181 0   255 5   181 0   255 5   181 0   255 5   46  2   255 5   46  2   82  0   46  2   82  0   46  2   82  0   181 0   7   255 82  0   181 0   82  0   181 0   7   255 82  0   181 0   82  0   181 0   7   255 45  4   
                                           254 0   45  4   21  1   45  4   21  1   66  4   28  1   66  4   28  1   172 4   28  1   172 4   28  1   193 4   21  1   193 4   21  1   193 4   254 0   193 4   254 0   172 4   247 0   172 4   247 0   66  4   247 0   66  4   247 0   45  4   254 0   7   255 
                                           45  4   188 0   45  4   211 0   45  4   211 0   66  4   218 0   66  4   218 0   172 4   218 0   172 4   218 0   193 4   211 0   193 4   211 0   193 4   188 0   193 4   188 0   172 4   181 0   172 4   181 0   66  4   181 0   66  4   181 0   45  4   188 0   
                                           7   255 45  4   206 1   45  4   229 1   45  4   229 1   66  4   236 1   66  4   236 1   172 4   236 1   172 4   236 1   193 4   229 1   193 4   229 1   193 4   206 1   193 4   206 1   172 4   199 1   172 4   199 1   66  4   199 1   66  4   199 1   45  4   
                                           206 1   7   255 45  4   17  2   45  4   40  2   45  4   40  2   66  4   46  2   66  4   46  2   172 4   46  2   172 4   46  2   193 4   40  2   193 4   40  2   193 4   17  2   193 4   17  2   172 4   10  2   172 4   10  2   66  4   10  2   66  4   10  2   
                                           45  4   17  2   7   255 96  0   181 0   94  0   188 0   94  0   188 0   89  0   193 0   89  0   193 0   82  0   195 0   82  0   195 0   74  0   193 0   74  0   193 0   69  0   188 0   69  0   188 0   67  0   181 0   67  0   181 0   69  0   174 0   69  0   
                                           174 0   74  0   168 0   74  0   168 0   82  0   166 0   82  0   166 0   89  0   168 0   89  0   168 0   94  0   174 0   94  0   174 0   96  0   181 0   7   255 53  0   181 0   111 0   181 0   7   255 82  0   152 0   82  0   210 0   7   255 212 0   181 0   
                                           211 0   188 0   211 0   188 0   205 0   193 0   205 0   193 0   198 0   195 0   198 0   195 0   191 0   193 0   191 0   193 0   185 0   188 0   185 0   188 0   183 0   181 0   183 0   181 0   185 0   174 0   185 0   174 0   191 0   168 0   191 0   168 0   
                                           198 0   166 0   198 0   166 0   205 0   168 0   205 0   168 0   211 0   174 0   211 0   174 0   212 0   181 0   7   255 169 0   181 0   227 0   181 0   7   255 198 0   152 0   198 0   210 0   7   255 133 4   181 0   131 4   188 0   131 4   188 0   126 4   
                                           193 0   126 4   193 0   119 4   195 0   119 4   195 0   112 4   193 0   112 4   193 0   106 4   188 0   106 4   188 0   104 4   181 0   104 4   181 0   106 4   174 0   106 4   174 0   112 4   168 0   112 4   168 0   119 4   166 0   119 4   166 0   126 4   
                                           168 0   126 4   168 0   131 4   174 0   131 4   174 0   133 4   181 0   7   255 90  4   181 0   148 4   181 0   7   255 119 4   152 0   119 4   210 0   7   255 14  6   181 0   12  6   188 0   12  6   188 0   7   6   193 0   7   6   193 0   255 5   195 0   
                                           255 5   195 0   248 5   193 0   248 5   193 0   243 5   188 0   243 5   188 0   241 5   181 0   241 5   181 0   243 5   174 0   243 5   174 0   248 5   168 0   248 5   168 0   255 5   166 0   255 5   166 0   7   6   168 0   7   6   168 0   12  6   174 0   
                                           12  6   174 0   14  6   181 0   7   255 226 5   181 0   28  6   181 0   7   255 255 5   152 0   255 5   210 0   7   255 14  6   46  2   12  6   54  2   12  6   54  2   7   6   59  2   7   6   59  2   255 5   61  2   255 5   61  2   248 5   59  2   248 5   
                                           59  2   243 5   54  2   243 5   54  2   241 5   46  2   241 5   46  2   243 5   39  2   243 5   39  2   248 5   34  2   248 5   34  2   255 5   32  2   255 5   32  2   7   6   34  2   7   6   34  2   12  6   39  2   12  6   39  2   14  6   46  2   7   255 
                                           226 5   46  2   28  6   46  2   7   255 255 5   17  2   255 5   76  2   7   255 133 4   46  2   131 4   54  2   131 4   54  2   126 4   59  2   126 4   59  2   119 4   61  2   119 4   61  2   112 4   59  2   112 4   59  2   106 4   54  2   106 4   54  2   
                                           104 4   46  2   104 4   46  2   106 4   39  2   106 4   39  2   112 4   34  2   112 4   34  2   119 4   32  2   119 4   32  2   126 4   34  2   126 4   34  2   131 4   39  2   131 4   39  2   133 4   46  2   7   255 90  4   46  2   148 4   46  2   7   255 
                                           119 4   17  2   119 4   76  2   7   255 212 0   46  2   211 0   54  2   211 0   54  2   205 0   59  2   205 0   59  2   198 0   61  2   198 0   61  2   191 0   59  2   191 0   59  2   185 0   54  2   185 0   54  2   183 0   46  2   183 0   46  2   185 0   
                                           39  2   185 0   39  2   191 0   34  2   191 0   34  2   198 0   32  2   198 0   32  2   205 0   34  2   205 0   34  2   211 0   39  2   211 0   39  2   212 0   46  2   7   255 169 0   46  2   227 0   46  2   7   255 198 0   17  2   198 0   76  2   7   255 
                                           96  0   46  2   94  0   54  2   94  0   54  2   89  0   59  2   89  0   59  2   82  0   61  2   82  0   61  2   74  0   59  2   74  0   59  2   69  0   54  2   69  0   54  2   67  0   46  2   67  0   46  2   69  0   39  2   69  0   39  2   74  0   34  2   
                                           74  0   34  2   82  0   32  2   82  0   32  2   89  0   34  2   89  0   34  2   94  0   39  2   94  0   39  2   96  0   46  2   7   255 53  0   46  2   111 0   46  2   7   255 82  0   17  2   82  0   76  2   7   255 212 0   114 1   211 0   121 1   211 0   
                                           121 1   205 0   126 1   205 0   126 1   198 0   128 1   198 0   128 1   191 0   126 1   191 0   126 1   185 0   121 1   185 0   121 1   183 0   114 1   183 0   114 1   185 0   106 1   185 0   106 1   191 0   101 1   191 0   101 1   198 0   99  1   198 0   
                                           99  1   205 0   101 1   205 0   101 1   211 0   106 1   211 0   106 1   212 0   114 1   7   255 169 0   114 1   227 0   114 1   7   255 198 0   85  1   198 0   143 1   7   255 124 0   17  2   124 0   40  2   124 0   40  2   145 0   46  2   145 0   46  2   
                                           )) "a")
 (_WriteStream FILE (vl-list->string (list 251 0   46  2   251 0   46  2   16  1   40  2   16  1   40  2   16  1   17  2   16  1   17  2   251 0   10  2   251 0   10  2   145 0   10  2   145 0   10  2   124 0   17  2   7   255 124 0   188 0   124 0   211 0   124 0   211 0   145 0   218 0   145 0   
                                           218 0   251 0   218 0   251 0   218 0   16  1   211 0   16  1   211 0   16  1   188 0   16  1   188 0   251 0   181 0   251 0   181 0   145 0   181 0   145 0   181 0   124 0   188 0   0   252 65  117 116 111 67  65  68  32  83  108 105 100 101 13  10  26  
                                           0   86  2   73  6   247 2   97  120 67  1   2   0   52  18  7   255 7   255 142 3   45  1   38  6   45  1   38  6   45  1   38  6   204 1   38  6   204 1   142 3   204 1   142 3   204 1   142 3   45  1   7   255 142 3   45  1   142 3   45  1   7   255 142 
                                           3   45  1   142 3   45  1   7   255 142 3   45  1   142 3   45  1   7   255 129 5   79  1   129 5   89  1   129 5   89  1   138 5   93  1   138 5   93  1   188 5   93  1   188 5   93  1   197 5   89  1   197 5   89  1   197 5   79  1   197 5   79  1   188 
                                           5   76  1   188 5   76  1   138 5   76  1   138 5   76  1   129 5   79  1   7   255 129 5   48  1   129 5   59  1   129 5   59  1   138 5   62  1   138 5   62  1   188 5   62  1   188 5   62  1   197 5   59  1   197 5   59  1   197 5   48  1   197 5   48  
                                           1   188 5   45  1   188 5   45  1   138 5   45  1   138 5   45  1   129 5   48  1   7   255 129 5   160 1   129 5   170 1   129 5   170 1   138 5   174 1   138 5   174 1   188 5   174 1   188 5   174 1   197 5   170 1   197 5   170 1   197 5   160 1   197 
                                           5   160 1   188 5   156 1   188 5   156 1   138 5   156 1   138 5   156 1   129 5   160 1   7   255 129 5   190 1   129 5   201 1   129 5   201 1   138 5   204 1   138 5   204 1   188 5   204 1   188 5   204 1   197 5   201 1   197 5   201 1   197 5   190 
                                           1   197 5   190 1   188 5   187 1   188 5   187 1   138 5   187 1   138 5   187 1   129 5   190 1   7   255 207 5   79  1   207 5   89  1   207 5   89  1   216 5   93  1   216 5   93  1   10  6   93  1   10  6   93  1   20  6   89  1   20  6   89  1   20  
                                           6   79  1   20  6   79  1   10  6   76  1   10  6   76  1   216 5   76  1   216 5   76  1   207 5   79  1   7   255 207 5   48  1   207 5   59  1   207 5   59  1   216 5   62  1   216 5   62  1   10  6   62  1   10  6   62  1   20  6   59  1   20  6   59  
                                           1   20  6   48  1   20  6   48  1   10  6   45  1   10  6   45  1   216 5   45  1   216 5   45  1   207 5   48  1   7   255 207 5   160 1   207 5   170 1   207 5   170 1   216 5   174 1   216 5   174 1   10  6   174 1   10  6   174 1   20  6   170 1   20  
                                           6   170 1   20  6   160 1   20  6   160 1   10  6   156 1   10  6   156 1   216 5   156 1   216 5   156 1   207 5   160 1   7   255 207 5   190 1   207 5   201 1   207 5   201 1   216 5   204 1   216 5   204 1   10  6   204 1   10  6   204 1   20  6   201 
                                           1   20  6   201 1   20  6   190 1   20  6   190 1   10  6   187 1   10  6   187 1   216 5   187 1   216 5   187 1   207 5   190 1   7   255 228 3   125 1   227 3   128 1   227 3   128 1   225 3   130 1   225 3   130 1   222 3   131 1   222 3   131 1   219 
                                           3   130 1   219 3   130 1   217 3   128 1   217 3   128 1   216 3   125 1   216 3   125 1   217 3   121 1   217 3   121 1   219 3   119 1   219 3   119 1   222 3   118 1   222 3   118 1   225 3   119 1   225 3   119 1   227 3   121 1   227 3   121 1   228 
                                           3   125 1   7   255 210 3   125 1   234 3   125 1   7   255 222 3   112 1   222 3   137 1   7   255 208 5   204 1   207 5   208 1   207 5   208 1   205 5   210 1   205 5   210 1   202 5   211 1   202 5   211 1   199 5   210 1   199 5   210 1   197 5   208 
                                           1   197 5   208 1   196 5   204 1   196 5   204 1   197 5   201 1   197 5   201 1   199 5   199 1   199 5   199 1   202 5   198 1   202 5   198 1   205 5   199 1   205 5   199 1   207 5   201 1   207 5   201 1   208 5   204 1   7   255 190 5   204 1   214 
                                           5   204 1   7   255 202 5   192 1   202 5   217 1   7   255 208 5   45  1   207 5   48  1   207 5   48  1   205 5   50  1   205 5   50  1   202 5   51  1   202 5   51  1   199 5   50  1   199 5   50  1   197 5   48  1   197 5   48  1   196 5   45  1   196 
                                           5   45  1   197 5   42  1   197 5   42  1   199 5   39  1   199 5   39  1   202 5   38  1   202 5   38  1   205 5   39  1   205 5   39  1   207 5   42  1   207 5   42  1   208 5   45  1   7   255 190 5   45  1   214 5   45  1   7   255 202 5   32  1   202 
                                           5   57  1   7   255 148 3   45  1   147 3   48  1   147 3   48  1   145 3   50  1   145 3   50  1   142 3   51  1   142 3   51  1   139 3   50  1   139 3   50  1   137 3   48  1   137 3   48  1   136 3   45  1   136 3   45  1   137 3   42  1   137 3   42  
                                           1   139 3   39  1   139 3   39  1   142 3   38  1   142 3   38  1   145 3   39  1   145 3   39  1   147 3   42  1   147 3   42  1   148 3   45  1   7   255 130 3   45  1   154 3   45  1   7   255 142 3   32  1   142 3   57  1   7   255 45  6   45  1   44  
                                           6   48  1   44  6   48  1   41  6   50  1   41  6   50  1   38  6   51  1   38  6   51  1   35  6   50  1   35  6   50  1   33  6   48  1   33  6   48  1   32  6   45  1   32  6   45  1   33  6   42  1   33  6   42  1   35  6   39  1   35  6   39  1   38  
                                           6   38  1   38  6   38  1   41  6   39  1   41  6   39  1   44  6   42  1   44  6   42  1   45  6   45  1   7   255 26  6   45  1   51  6   45  1   7   255 38  6   32  1   38  6   57  1   7   255 148 3   204 1   147 3   208 1   147 3   208 1   145 3   210 
                                           1   145 3   210 1   142 3   211 1   142 3   211 1   139 3   210 1   139 3   210 1   137 3   208 1   137 3   208 1   136 3   204 1   136 3   204 1   137 3   201 1   137 3   201 1   139 3   199 1   139 3   199 1   142 3   198 1   142 3   198 1   145 3   199 
                                           1   145 3   199 1   147 3   201 1   147 3   201 1   148 3   204 1   7   255 130 3   204 1   154 3   204 1   7   255 142 3   192 1   142 3   217 1   7   255 45  6   204 1   44  6   208 1   44  6   208 1   41  6   210 1   41  6   210 1   38  6   211 1   38  
                                           6   211 1   35  6   210 1   35  6   210 1   33  6   208 1   33  6   208 1   32  6   204 1   32  6   204 1   33  6   201 1   33  6   201 1   35  6   199 1   35  6   199 1   38  6   198 1   38  6   198 1   41  6   199 1   41  6   199 1   44  6   201 1   44  
                                           6   201 1   45  6   204 1   7   255 26  6   204 1   51  6   204 1   7   255 38  6   192 1   38  6   217 1   7   255 70  1   45  1   87  3   45  1   87  3   45  1   87  3   93  1   87  3   93  1   208 3   93  1   208 3   93  1   208 3   156 1   7   255 208 
                                           3   156 1   87  3   156 1   7   255 87  3   156 1   87  3   204 1   87  3   204 1   70  1   204 1   70  1   204 1   70  1   45  1   7   255 70  1   45  1   70  1   45  1   7   255 70  1   45  1   70  1   45  1   7   255 70  1   45  1   70  1   45  1   7   
                                           255 208 3   125 1   222 3   125 1   7   255 238 3   141 1   236 3   142 1   236 3   142 1   234 3   144 1   234 3   144 1   232 3   145 1   232 3   145 1   230 3   146 1   230 3   146 1   228 3   147 1   228 3   147 1   226 3   147 1   226 3   147 1   223 
                                           3   147 1   223 3   147 1   221 3   147 1   221 3   147 1   218 3   147 1   218 3   147 1   216 3   147 1   216 3   147 1   214 3   146 1   214 3   146 1   212 3   145 1   212 3   145 1   210 3   144 1   210 3   144 1   208 3   142 1   208 3   142 1   206 
                                           3   141 1   206 3   141 1   204 3   139 1   204 3   139 1   203 3   137 1   203 3   137 1   202 3   135 1   202 3   135 1   201 3   133 1   201 3   133 1   200 3   130 1   200 3   130 1   199 3   128 1   199 3   128 1   199 3   126 1   199 3   126 1   199 
                                           3   123 1   199 3   123 1   199 3   121 1   199 3   121 1   200 3   119 1   200 3   119 1   201 3   116 1   201 3   116 1   202 3   114 1   202 3   114 1   203 3   112 1   203 3   112 1   204 3   110 1   204 3   110 1   206 3   108 1   206 3   108 1   208 
                                           3   107 1   208 3   107 1   210 3   105 1   210 3   105 1   212 3   104 1   212 3   104 1   214 3   103 1   214 3   103 1   216 3   102 1   216 3   102 1   218 3   102 1   218 3   102 1   221 3   102 1   221 3   102 1   223 3   102 1   223 3   102 1   226 
                                           3   102 1   226 3   102 1   228 3   102 1   228 3   102 1   230 3   103 1   230 3   103 1   232 3   104 1   232 3   104 1   234 3   105 1   234 3   105 1   236 3   107 1   236 3   107 1   238 3   108 1   7   255 238 3   108 1   238 3   141 1   7   255 17  
                                           3   79  1   17  3   89  1   17  3   89  1   27  3   93  1   27  3   93  1   76  3   93  1   76  3   93  1   86  3   89  1   86  3   89  1   86  3   79  1   86  3   79  1   76  3   76  1   76  3   76  1   27  3   76  1   27  3   76  1   17  3   79  1   7   
                                           255 17  3   48  1   17  3   59  1   17  3   59  1   27  3   62  1   27  3   62  1   76  3   62  1   76  3   62  1   86  3   59  1   86  3   59  1   86  3   48  1   86  3   48  1   76  3   45  1   76  3   45  1   27  3   45  1   27  3   45  1   17  3   48  
                                           1   7   255 17  3   160 1   17  3   170 1   17  3   170 1   27  3   174 1   27  3   174 1   76  3   174 1   76  3   174 1   86  3   170 1   86  3   170 1   86  3   160 1   86  3   160 1   76  3   156 1   76  3   156 1   27  3   156 1   27  3   156 1   17  
                                           3   160 1   7   255 17  3   190 1   17  3   201 1   17  3   201 1   27  3   204 1   27  3   204 1   76  3   204 1   76  3   204 1   86  3   201 1   86  3   201 1   86  3   190 1   86  3   190 1   76  3   187 1   76  3   187 1   27  3   187 1   27  3   187 
                                           1   17  3   190 1   7   255 95  3   79  1   95  3   89  1   95  3   89  1   105 3   93  1   105 3   93  1   154 3   93  1   154 3   93  1   164 3   89  1   164 3   89  1   164 3   79  1   164 3   79  1   154 3   76  1   154 3   76  1   105 3   76  1   105 
                                           3   76  1   95  3   79  1   7   255 95  3   48  1   95  3   59  1   95  3   59  1   105 3   62  1   105 3   62  1   154 3   62  1   154 3   62  1   164 3   59  1   164 3   59  1   164 3   48  1   164 3   48  1   154 3   45  1   154 3   45  1   105 3   45  
                                           1   105 3   45  1   95  3   48  1   7   255 95  3   160 1   95  3   170 1   95  3   170 1   105 3   174 1   105 3   174 1   154 3   174 1   154 3   174 1   164 3   170 1   164 3   170 1   164 3   160 1   164 3   160 1   154 3   156 1   154 3   156 1   105 
                                           3   156 1   105 3   156 1   95  3   160 1   7   255 95  3   190 1   95  3   201 1   95  3   201 1   105 3   204 1   105 3   204 1   154 3   204 1   154 3   204 1   164 3   201 1   164 3   201 1   164 3   190 1   164 3   190 1   154 3   187 1   154 3   187 
                                           1   105 3   187 1   105 3   187 1   95  3   190 1   7   255 173 3   79  1   173 3   89  1   173 3   89  1   183 3   93  1   183 3   93  1   233 3   93  1   233 3   93  1   242 3   89  1   242 3   89  1   242 3   79  1   242 3   79  1   233 3   76  1   233 
                                           3   76  1   183 3   76  1   183 3   76  1   173 3   79  1   7   255 173 3   48  1   173 3   59  1   173 3   59  1   183 3   62  1   183 3   62  1   233 3   62  1   233 3   62  1   242 3   59  1   242 3   59  1   242 3   48  1   242 3   48  1   233 3   45  
                                           1   233 3   45  1   183 3   45  1   183 3   45  1   173 3   48  1   7   255 173 3   160 1   173 3   170 1   173 3   170 1   183 3   174 1   183 3   174 1   233 3   174 1   233 3   174 1   242 3   170 1   242 3   170 1   242 3   160 1   242 3   160 1   233 
                                           3   156 1   233 3   156 1   183 3   156 1   183 3   156 1   173 3   160 1   7   255 173 3   190 1   173 3   201 1   173 3   201 1   183 3   204 1   183 3   204 1   233 3   204 1   233 3   204 1   242 3   201 1   242 3   201 1   242 3   190 1   242 3   190 
                                           1   233 3   187 1   233 3   187 1   183 3   187 1   183 3   187 1   173 3   190 1   7   255 136 3   204 1   136 3   206 1   136 3   206 1   135 3   207 1   135 3   207 1   135 3   208 1   135 3   208 1   134 3   209 1   134 3   209 1   133 3   210 1   133 
                                           3   210 1   132 3   210 1   132 3   210 1   131 3   210 1   131 3   210 1   130 3   211 1   130 3   211 1   129 3   210 1   129 3   210 1   127 3   210 1   127 3   210 1   126 3   210 1   126 3   210 1   125 3   209 1   125 3   209 1   125 3   208 1   125 
                                           3   208 1   124 3   207 1   124 3   207 1   124 3   206 1   124 3   206 1   124 3   204 1   124 3   204 1   124 3   203 1   124 3   203 1   124 3   202 1   124 3   202 1   125 3   201 1   125 3   201 1   125 3   200 1   125 3   200 1   126 3   199 1   126 
                                           3   199 1   127 3   199 1   127 3   199 1   129 3   198 1   129 3   198 1   130 3   198 1   130 3   198 1   131 3   198 1   131 3   198 1   132 3   199 1   132 3   199 1   133 3   199 1   133 3   199 1   134 3   200 1   134 3   200 1   135 3   201 1   135 
                                           3   201 1   135 3   202 1   135 3   202 1   136 3   203 1   136 3   203 1   136 3   204 1   7   255 117 3   204 1   142 3   204 1   7   255 130 3   192 1   130 3   217 1   7   255 136 3   45  1   136 3   46  1   136 3   46  1   135 3   47  1   135 3   47  
                                           1   135 3   48  1   135 3   48  1   134 3   49  1   134 3   49  1   133 3   50  1   133 3   50  1   132 3   50  1   132 3   50  1   131 3   51  1   131 3   51  1   130 3   51  1   130 3   51  1   129 3   51  1   129 3   51  1   127 3   50  1   127 3   50  
                                           1   126 3   50  1   126 3   50  1   125 3   49  1   125 3   49  1   125 3   48  1   125 3   48  1   124 3   47  1   124 3   47  1   124 3   46  1   124 3   46  1   124 3   45  1   124 3   45  1   124 3   43  1   124 3   43  1   124 3   42  1   124 3   42  
                                           1   125 3   41  1   125 3   41  1   125 3   40  1   125 3   40  1   126 3   39  1   126 3   39  1   127 3   39  1   127 3   39  1   129 3   39  1   129 3   39  1   130 3   38  1   130 3   38  1   131 3   39  1   131 3   39  1   132 3   39  1   132 3   39  
                                           1   133 3   39  1   133 3   39  1   134 3   40  1   134 3   40  1   135 3   41  1   135 3   41  1   135 3   42  1   135 3   42  1   136 3   43  1   136 3   43  1   136 3   45  1   7   255 117 3   45  1   142 3   45  1   7   255 130 3   32  1   130 3   57  
                                           1   7   255 156 1   125 1   156 1   126 1   156 1   126 1   155 1   127 1   155 1   127 1   155 1   128 1   155 1   128 1   154 1   129 1   154 1   129 1   153 1   130 1   153 1   130 1   152 1   130 1   152 1   130 1   151 1   131 1   151 1   131 1   150 
                                           1   131 1   150 1   131 1   148 1   131 1   148 1   131 1   147 1   130 1   147 1   130 1   146 1   130 1   146 1   130 1   145 1   129 1   145 1   129 1   145 1   128 1   145 1   128 1   144 1   127 1   144 1   127 1   144 1   126 1   144 1   126 1   143 
                                           1   125 1   143 1   125 1   144 1   123 1   144 1   123 1   144 1   122 1   144 1   122 1   145 1   121 1   145 1   121 1   145 1   120 1   145 1   120 1   146 1   119 1   146 1   119 1   147 1   119 1   147 1   119 1   148 1   118 1   148 1   118 1   150 
                                           1   118 1   150 1   118 1   151 1   118 1   151 1   118 1   152 1   119 1   152 1   119 1   153 1   119 1   153 1   119 1   154 1   120 1   154 1   120 1   155 1   121 1   155 1   121 1   155 1   122 1   155 1   122 1   156 1   123 1   156 1   123 1   156 
                                           1   125 1   7   255 137 1   125 1   162 1   125 1   7   255 150 1   112 1   150 1   137 1   7   255 76  1   45  1   76  1   46  1   76  1   46  1   75  1   47  1   75  1   47  1   75  1   48  1   75  1   48  1   74  1   49  1   74  1   49  1   73  1   50  
                                           1   73  1   50  1   72  1   50  1   72  1   50  1   71  1   51  1   71  1   51  1   70  1   51  1   70  1   51  1   68  1   51  1   68  1   51  1   67  1   50  1   67  1   50  1   66  1   50  1   66  1   50  1   65  1   49  1   65  1   49  1   65  1   48  
                                           1   65  1   48  1   64  1   47  1   64  1   47  1   64  1   46  1   64  1   46  1   64  1   45  1   64  1   45  1   64  1   43  1   64  1   43  1   64  1   42  1   64  1   42  1   65  1   41  1   65  1   41  1   65  1   40  1   65  1   40  1   66  1   39  
                                           1   66  1   39  1   67  1   39  1   67  1   39  1   68  1   39  1   68  1   39  1   70  1   38  1   70  1   38  1   71  1   39  1   71  1   39  1   72  1   39  1   72  1   39  1   73  1   39  1   73  1   39  1   74  1   40  1   74  1   40  1   75  1   41  
                                           1   75  1   41  1   75  1   42  1   75  1   42  1   76  1   43  1   76  1   43  1   76  1   45  1   7   255 57  1   45  1   82  1   45  1   7   255 70  1   32  1   70  1   57  1   7   255 76  1   204 1   76  1   206 1   76  1   206 1   75  1   207 1   75  
                                           1   207 1   75  1   208 1   75  1   208 1   74  1   209 1   74  1   209 1   73  1   210 1   73  1   210 1   72  1   210 1   72  1   210 1   71  1   210 1   71  1   210 1   70  1   211 1   70  1   211 1   68  1   210 1   68  1   210 1   67  1   210 1   67  
                                           1   210 1   66  1   210 1   66  1   210 1   65  1   209 1   65  1   209 1   65  1   208 1   65  1   208 1   64  1   207 1   64  1   207 1   64  1   206 1   64  1   206 1   64  1   204 1   64  1   204 1   64  1   203 1   64  1   203 1   64  1   202 1   64  
                                           )) "a")
 (_WriteStream FILE (vl-list->string (list 1   202 1   65  1   201 1   65  1   201 1   65  1   200 1   65  1   200 1   66  1   199 1   66  1   199 1   67  1   199 1   67  1   199 1   68  1   198 1   68  1   198 1   70  1   198 1   70  1   198 1   71  1   198 1   71  1   198 1   72  1   199 1   72  
                                           1   199 1   73  1   199 1   73  1   199 1   74  1   200 1   74  1   200 1   75  1   201 1   75  1   201 1   75  1   202 1   75  1   202 1   76  1   203 1   76  1   203 1   76  1   204 1   7   255 57  1   204 1   82  1   204 1   7   255 70  1   192 1   70  
                                           1   217 1   7   255 228 3   125 1   228 3   126 1   228 3   126 1   228 3   127 1   228 3   127 1   227 3   128 1   227 3   128 1   226 3   129 1   226 3   129 1   225 3   130 1   225 3   130 1   224 3   130 1   224 3   130 1   223 3   131 1   223 3   131 
                                           1   222 3   131 1   222 3   131 1   221 3   131 1   221 3   131 1   220 3   130 1   220 3   130 1   219 3   130 1   219 3   130 1   218 3   129 1   218 3   129 1   217 3   128 1   217 3   128 1   216 3   127 1   216 3   127 1   216 3   126 1   216 3   126 
                                           1   216 3   125 1   216 3   125 1   216 3   123 1   216 3   123 1   216 3   122 1   216 3   122 1   217 3   121 1   217 3   121 1   218 3   120 1   218 3   120 1   219 3   119 1   219 3   119 1   220 3   119 1   220 3   119 1   221 3   118 1   221 3   118 
                                           1   222 3   118 1   222 3   118 1   223 3   118 1   223 3   118 1   224 3   119 1   224 3   119 1   225 3   119 1   225 3   119 1   226 3   120 1   226 3   120 1   227 3   121 1   227 3   121 1   228 3   122 1   228 3   122 1   228 3   123 1   228 3   123 
                                           1   228 3   125 1   7   255 210 3   125 1   234 3   125 1   7   255 222 3   112 1   222 3   137 1   7   255 37  0   45  1   221 0   45  1   221 0   45  1   221 0   93  1   221 0   93  1   189 1   93  1   189 1   93  1   189 1   156 1   189 1   156 1   221 
                                           0   156 1   221 0   156 1   221 0   204 1   221 0   204 1   37  0   204 1   37  0   204 1   37  0   45  1   7   255 37  0   45  1   37  0   45  1   7   255 37  0   45  1   37  0   45  1   7   255 37  0   45  1   37  0   45  1   7   255 166 1   141 1   163 
                                           1   143 1   163 1   143 1   160 1   145 1   160 1   145 1   157 1   146 1   157 1   146 1   153 1   147 1   153 1   147 1   150 1   147 1   150 1   147 1   146 1   147 1   146 1   147 1   143 1   146 1   143 1   146 1   139 1   145 1   139 1   145 1   136 
                                           1   143 1   136 1   143 1   133 1   141 1   133 1   141 1   131 1   138 1   131 1   138 1   129 1   135 1   129 1   135 1   128 1   132 1   128 1   132 1   127 1   128 1   127 1   128 1   127 1   125 1   127 1   125 1   127 1   121 1   127 1   121 1   128 
                                           1   117 1   128 1   117 1   129 1   114 1   129 1   114 1   131 1   111 1   131 1   111 1   133 1   108 1   133 1   108 1   136 1   106 1   136 1   106 1   139 1   104 1   139 1   104 1   143 1   103 1   143 1   103 1   146 1   102 1   146 1   102 1   150 
                                           1   102 1   150 1   102 1   153 1   102 1   153 1   102 1   157 1   103 1   157 1   103 1   160 1   104 1   160 1   104 1   163 1   106 1   163 1   106 1   166 1   108 1   7   255 166 1   108 1   166 1   141 1   7   255 76  1   79  1   76  1   89  1   76  
                                           1   89  1   86  1   93  1   86  1   93  1   135 1   93  1   135 1   93  1   145 1   89  1   145 1   89  1   145 1   79  1   145 1   79  1   135 1   76  1   135 1   76  1   86  1   76  1   86  1   76  1   76  1   79  1   7   255 76  1   48  1   76  1   59  
                                           1   76  1   59  1   86  1   62  1   86  1   62  1   135 1   62  1   135 1   62  1   145 1   59  1   145 1   59  1   145 1   48  1   145 1   48  1   135 1   45  1   135 1   45  1   86  1   45  1   86  1   45  1   76  1   48  1   7   255 76  1   160 1   76  
                                           1   170 1   76  1   170 1   86  1   174 1   86  1   174 1   135 1   174 1   135 1   174 1   145 1   170 1   145 1   170 1   145 1   160 1   145 1   160 1   135 1   156 1   135 1   156 1   86  1   156 1   86  1   156 1   76  1   160 1   7   255 76  1   190 
                                           1   76  1   201 1   76  1   201 1   86  1   204 1   86  1   204 1   135 1   204 1   135 1   204 1   145 1   201 1   145 1   201 1   145 1   190 1   145 1   190 1   135 1   187 1   135 1   187 1   86  1   187 1   86  1   187 1   76  1   190 1   7   255 154 
                                           1   79  1   154 1   89  1   154 1   89  1   164 1   93  1   164 1   93  1   213 1   93  1   213 1   93  1   223 1   89  1   223 1   89  1   223 1   79  1   223 1   79  1   213 1   76  1   213 1   76  1   164 1   76  1   164 1   76  1   154 1   79  1   7   
                                           255 154 1   48  1   154 1   59  1   154 1   59  1   164 1   62  1   164 1   62  1   213 1   62  1   213 1   62  1   223 1   59  1   223 1   59  1   223 1   48  1   223 1   48  1   213 1   45  1   213 1   45  1   164 1   45  1   164 1   45  1   154 1   48  
                                           1   7   255 154 1   160 1   154 1   170 1   154 1   170 1   164 1   174 1   164 1   174 1   213 1   174 1   213 1   174 1   223 1   170 1   223 1   170 1   223 1   160 1   223 1   160 1   213 1   156 1   213 1   156 1   164 1   156 1   164 1   156 1   154 
                                           1   160 1   7   255 154 1   190 1   154 1   201 1   154 1   201 1   164 1   204 1   164 1   204 1   213 1   204 1   213 1   204 1   223 1   201 1   223 1   201 1   223 1   190 1   223 1   190 1   213 1   187 1   213 1   187 1   164 1   187 1   164 1   187 
                                           1   154 1   190 1   7   255 45  0   48  1   45  0   59  1   45  0   59  1   55  0   62  1   55  0   62  1   104 0   62  1   104 0   62  1   114 0   59  1   114 0   59  1   114 0   48  1   114 0   48  1   104 0   45  1   104 0   45  1   55  0   45  1   55  
                                           0   45  1   45  0   48  1   7   255 45  0   190 1   45  0   201 1   45  0   201 1   55  0   204 1   55  0   204 1   104 0   204 1   104 0   204 1   114 0   201 1   114 0   201 1   114 0   190 1   114 0   190 1   104 0   187 1   104 0   187 1   55  0   187 
                                           1   55  0   187 1   45  0   190 1   7   255 86  0   204 1   85  0   206 1   85  0   206 1   85  0   208 1   85  0   208 1   83  0   209 1   83  0   209 1   82  0   210 1   82  0   210 1   80  0   211 1   80  0   211 1   78  0   210 1   78  0   210 1   76  
                                           0   209 1   76  0   209 1   75  0   208 1   75  0   208 1   74  0   206 1   74  0   206 1   73  0   204 1   73  0   204 1   74  0   203 1   74  0   203 1   75  0   201 1   75  0   201 1   76  0   199 1   76  0   199 1   78  0   199 1   78  0   199 1   80  
                                           0   198 1   80  0   198 1   82  0   199 1   82  0   199 1   83  0   199 1   83  0   199 1   85  0   201 1   85  0   201 1   85  0   203 1   85  0   203 1   86  0   204 1   7   255 67  0   204 1   92  0   204 1   7   255 80  0   192 1   80  0   217 1   7   
                                           255 86  0   45  1   85  0   47  1   85  0   47  1   85  0   48  1   85  0   48  1   83  0   50  1   83  0   50  1   82  0   50  1   82  0   50  1   80  0   51  1   80  0   51  1   78  0   50  1   78  0   50  1   76  0   50  1   76  0   50  1   75  0   48  
                                           1   75  0   48  1   74  0   47  1   74  0   47  1   73  0   45  1   73  0   45  1   74  0   43  1   74  0   43  1   75  0   41  1   75  0   41  1   76  0   40  1   76  0   40  1   78  0   39  1   78  0   39  1   80  0   38  1   80  0   38  1   82  0   39  
                                           1   82  0   39  1   83  0   40  1   83  0   40  1   85  0   41  1   85  0   41  1   85  0   43  1   85  0   43  1   86  0   45  1   7   255 67  0   45  1   92  0   45  1   7   255 80  0   32  1   80  0   57  1   7   255 86  0   125 1   85  0   126 1   85  
                                           0   126 1   85  0   128 1   85  0   128 1   83  0   129 1   83  0   129 1   82  0   130 1   82  0   130 1   80  0   131 1   80  0   131 1   78  0   130 1   78  0   130 1   76  0   129 1   76  0   129 1   75  0   128 1   75  0   128 1   74  0   126 1   74  
                                           0   126 1   73  0   125 1   73  0   125 1   74  0   123 1   74  0   123 1   75  0   121 1   75  0   121 1   76  0   120 1   76  0   120 1   78  0   119 1   78  0   119 1   80  0   118 1   80  0   118 1   82  0   119 1   82  0   119 1   83  0   120 1   83  
                                           0   120 1   85  0   121 1   85  0   121 1   85  0   123 1   85  0   123 1   86  0   125 1   7   255 67  0   125 1   92  0   125 1   7   255 80  0   112 1   80  0   137 1   7   255 43  0   204 1   42  0   206 1   42  0   206 1   42  0   208 1   42  0   208 
                                           1   40  0   209 1   40  0   209 1   38  0   210 1   38  0   210 1   37  0   211 1   37  0   211 1   35  0   210 1   35  0   210 1   33  0   209 1   33  0   209 1   32  0   208 1   32  0   208 1   31  0   206 1   31  0   206 1   30  0   204 1   30  0   204 
                                           1   31  0   203 1   31  0   203 1   32  0   201 1   32  0   201 1   33  0   199 1   33  0   199 1   35  0   199 1   35  0   199 1   37  0   198 1   37  0   198 1   38  0   199 1   38  0   199 1   40  0   199 1   40  0   199 1   42  0   201 1   42  0   201 
                                           1   42  0   203 1   42  0   203 1   43  0   204 1   7   255 24  0   204 1   49  0   204 1   7   255 37  0   192 1   37  0   217 1   7   255 43  0   45  1   42  0   47  1   42  0   47  1   42  0   48  1   42  0   48  1   40  0   50  1   40  0   50  1   38  
                                           0   50  1   38  0   50  1   37  0   51  1   37  0   51  1   35  0   50  1   35  0   50  1   33  0   50  1   33  0   50  1   32  0   48  1   32  0   48  1   31  0   47  1   31  0   47  1   30  0   45  1   30  0   45  1   31  0   43  1   31  0   43  1   32  
                                           0   41  1   32  0   41  1   33  0   40  1   33  0   40  1   35  0   39  1   35  0   39  1   37  0   38  1   37  0   38  1   38  0   39  1   38  0   39  1   40  0   40  1   40  0   40  1   42  0   41  1   42  0   41  1   42  0   43  1   42  0   43  1   43  
                                           0   45  1   7   255 24  0   45  1   49  0   45  1   7   255 37  0   32  1   37  0   57  1   7   255 156 1   125 1   155 1   126 1   155 1   126 1   155 1   128 1   155 1   128 1   153 1   129 1   153 1   129 1   152 1   130 1   152 1   130 1   150 1   131 
                                           1   150 1   131 1   148 1   130 1   148 1   130 1   146 1   129 1   146 1   129 1   145 1   128 1   145 1   128 1   144 1   126 1   144 1   126 1   143 1   125 1   143 1   125 1   144 1   123 1   144 1   123 1   145 1   121 1   145 1   121 1   146 1   120 
                                           1   146 1   120 1   148 1   119 1   148 1   119 1   150 1   118 1   150 1   118 1   152 1   119 1   152 1   119 1   153 1   120 1   153 1   120 1   155 1   121 1   155 1   121 1   155 1   123 1   155 1   123 1   156 1   125 1   7   255 137 1   125 1   162 
                                           1   125 1   7   255 150 1   112 1   150 1   137 1   7   255 156 1   204 1   155 1   206 1   155 1   206 1   155 1   208 1   155 1   208 1   153 1   209 1   153 1   209 1   152 1   210 1   152 1   210 1   150 1   211 1   150 1   211 1   148 1   210 1   148 
                                           1   210 1   146 1   209 1   146 1   209 1   145 1   208 1   145 1   208 1   144 1   206 1   144 1   206 1   143 1   204 1   143 1   204 1   144 1   203 1   144 1   203 1   145 1   201 1   145 1   201 1   146 1   199 1   146 1   199 1   148 1   199 1   148 
                                           1   199 1   150 1   198 1   150 1   198 1   152 1   199 1   152 1   199 1   153 1   199 1   153 1   199 1   155 1   201 1   155 1   201 1   155 1   203 1   155 1   203 1   156 1   204 1   7   255 137 1   204 1   162 1   204 1   7   255 150 1   192 1   150 
                                           1   217 1   7   255 156 1   45  1   155 1   47  1   155 1   47  1   155 1   48  1   155 1   48  1   153 1   50  1   153 1   50  1   152 1   50  1   152 1   50  1   150 1   51  1   150 1   51  1   148 1   50  1   148 1   50  1   146 1   50  1   146 1   50  
                                           1   145 1   48  1   145 1   48  1   144 1   47  1   144 1   47  1   143 1   45  1   143 1   45  1   144 1   43  1   144 1   43  1   145 1   41  1   145 1   41  1   146 1   40  1   146 1   40  1   148 1   39  1   148 1   39  1   150 1   38  1   150 1   38  
                                           1   152 1   39  1   152 1   39  1   153 1   40  1   153 1   40  1   155 1   41  1   155 1   41  1   155 1   43  1   155 1   43  1   156 1   45  1   7   255 137 1   45  1   162 1   45  1   7   255 150 1   32  1   150 1   57  1   0   252 65  117 116 111 67  
                                           65  68  32  83  108 105 100 101 13  10  26  0   86  2   73  6   247 2   97  120 67  1   2   0   52  18  51  255 51  255 63  0   22  1   35  3   22  1   35  3   22  1   35  3   219 1   35  3   219 1   63  0   219 1   63  0   219 1   63  0   22  1   7   255 
                                           7   255 63  0   22  1   35  3   22  1   35  3   22  1   35  3   219 1   35  3   219 1   63  0   219 1   63  0   219 1   63  0   22  1   7   255 63  0   22  1   63  0   22  1   7   255 63  0   22  1   63  0   22  1   7   255 63  0   22  1   63  0   22  1   
                                           7   255 102 2   26  1   102 2   39  1   102 2   39  1   114 2   43  1   114 2   43  1   173 2   43  1   173 2   43  1   184 2   39  1   184 2   39  1   184 2   26  1   184 2   26  1   173 2   22  1   173 2   22  1   114 2   22  1   114 2   22  1   102 2   
                                           26  1   7   255 102 2   203 1   102 2   216 1   102 2   216 1   114 2   219 1   114 2   219 1   173 2   219 1   173 2   219 1   184 2   216 1   184 2   216 1   184 2   203 1   184 2   203 1   173 2   199 1   173 2   199 1   114 2   199 1   114 2   199 1   
                                           102 2   203 1   7   255 65  0   22  1   65  0   24  1   65  0   24  1   63  0   25  1   63  0   25  1   61  0   24  1   61  0   24  1   60  0   22  1   60  0   22  1   61  0   20  1   61  0   20  1   63  0   20  1   63  0   20  1   65  0   20  1   65  0   
                                           20  1   65  0   22  1   7   255 58  0   22  1   68  0   22  1   7   255 63  0   17  1   63  0   27  1   7   255 164 0   22  1   163 0   24  1   163 0   24  1   162 0   25  1   162 0   25  1   160 0   24  1   160 0   24  1   159 0   22  1   159 0   22  1   
                                           160 0   20  1   160 0   20  1   162 0   20  1   162 0   20  1   163 0   20  1   163 0   20  1   164 0   22  1   7   255 157 0   22  1   167 0   22  1   7   255 162 0   17  1   162 0   27  1   7   255 146 2   22  1   145 2   24  1   145 2   24  1   143 2   
                                           25  1   143 2   25  1   142 2   24  1   142 2   24  1   141 2   22  1   141 2   22  1   142 2   20  1   142 2   20  1   143 2   20  1   143 2   20  1   145 2   20  1   145 2   20  1   146 2   22  1   7   255 138 2   22  1   148 2   22  1   7   255 143 2   
                                           17  1   143 2   27  1   7   255 38  3   22  1   37  3   24  1   37  3   24  1   35  3   25  1   35  3   25  1   34  3   24  1   34  3   24  1   33  3   22  1   33  3   22  1   34  3   20  1   34  3   20  1   35  3   20  1   35  3   20  1   37  3   20  1   
                                           37  3   20  1   38  3   22  1   7   255 30  3   22  1   40  3   22  1   7   255 35  3   17  1   35  3   27  1   7   255 38  3   219 1   37  3   221 1   37  3   221 1   35  3   222 1   35  3   222 1   34  3   221 1   34  3   221 1   33  3   219 1   33  3   
                                           219 1   34  3   218 1   34  3   218 1   35  3   217 1   35  3   217 1   37  3   218 1   37  3   218 1   38  3   219 1   7   255 30  3   219 1   40  3   219 1   7   255 35  3   214 1   35  3   224 1   7   255 146 2   219 1   145 2   221 1   145 2   221 1   
                                           143 2   222 1   143 2   222 1   142 2   221 1   142 2   221 1   141 2   219 1   141 2   219 1   142 2   218 1   142 2   218 1   143 2   217 1   143 2   217 1   145 2   218 1   145 2   218 1   146 2   219 1   7   255 138 2   219 1   148 2   219 1   7   255 
                                           143 2   214 1   143 2   224 1   7   255 164 0   219 1   163 0   221 1   163 0   221 1   162 0   222 1   162 0   222 1   160 0   221 1   160 0   221 1   159 0   219 1   159 0   219 1   160 0   218 1   160 0   218 1   162 0   217 1   162 0   217 1   163 0   
                                           218 1   163 0   218 1   164 0   219 1   7   255 157 0   219 1   167 0   219 1   7   255 162 0   214 1   162 0   224 1   7   255 65  0   219 1   65  0   221 1   65  0   221 1   63  0   222 1   63  0   222 1   61  0   221 1   61  0   221 1   60  0   219 1   
                                           60  0   219 1   61  0   218 1   61  0   218 1   63  0   217 1   63  0   217 1   65  0   218 1   65  0   218 1   65  0   219 1   7   255 58  0   219 1   68  0   219 1   7   255 63  0   214 1   63  0   224 1   7   255 164 0   121 1   163 0   122 1   163 0   
                                           122 1   162 0   123 1   162 0   123 1   160 0   122 1   160 0   122 1   159 0   121 1   159 0   121 1   160 0   119 1   160 0   119 1   162 0   118 1   162 0   118 1   163 0   119 1   163 0   119 1   164 0   121 1   7   255 157 0   121 1   167 0   121 1   
                                           7   255 162 0   116 1   162 0   126 1   7   255 38  3   121 1   37  3   122 1   37  3   122 1   35  3   123 1   35  3   123 1   33  3   122 1   33  3   122 1   33  3   121 1   33  3   121 1   33  3   119 1   33  3   119 1   35  3   118 1   35  3   118 1   
                                           37  3   119 1   37  3   119 1   38  3   121 1   7   255 30  3   121 1   40  3   121 1   7   255 35  3   116 1   35  3   126 1   7   255 121 0   203 1   121 0   216 1   121 0   216 1   132 0   219 1   132 0   219 1   191 0   219 1   191 0   219 1   203 0   
                                           216 1   203 0   216 1   203 0   203 1   203 0   203 1   191 0   199 1   191 0   199 1   132 0   199 1   132 0   199 1   121 0   203 1   7   255 121 0   26  1   121 0   39  1   121 0   39  1   132 0   43  1   132 0   43  1   191 0   43  1   191 0   43  1   
                                           )) "a")
 (_WriteStream FILE (vl-list->string (list 203 0   39  1   203 0   39  1   203 0   26  1   203 0   26  1   191 0   22  1   191 0   22  1   132 0   22  1   132 0   22  1   121 0   26  1   51  255 51  255 35  3   121 1   109 3   219 1   109 3   219 1   0   6   219 1   0   6   219 1   0   6   22  1   
                                           0   6   22  1   109 3   22  1   109 3   22  1   35  3   121 1   7   255 7   255 109 3   22  1   0   6   22  1   0   6   22  1   0   6   219 1   0   6   219 1   109 3   219 1   109 3   219 1   109 3   22  1   7   255 109 3   22  1   109 3   22  1   7   255 
                                           109 3   22  1   109 3   22  1   7   255 109 3   22  1   109 3   22  1   7   255 35  3   121 1   109 3   121 1   7   255 48  3   121 1   47  3   126 1   47  3   126 1   44  3   130 1   44  3   130 1   40  3   133 1   40  3   133 1   35  3   134 1   35  3   
                                           134 1   30  3   133 1   30  3   133 1   26  3   130 1   26  3   130 1   23  3   126 1   23  3   126 1   22  3   121 1   22  3   121 1   23  3   116 1   23  3   116 1   26  3   111 1   26  3   111 1   30  3   109 1   30  3   109 1   35  3   108 1   35  3   
                                           108 1   40  3   109 1   40  3   109 1   44  3   111 1   44  3   111 1   47  3   116 1   47  3   116 1   48  3   121 1   7   255 136 4   24  1   136 4   32  1   136 4   32  1   144 4   35  1   144 4   35  1   185 4   35  1   185 4   35  1   193 4   32  1   
                                           193 4   32  1   193 4   24  1   193 4   24  1   185 4   22  1   185 4   22  1   144 4   22  1   144 4   22  1   136 4   24  1   7   255 136 4   209 1   136 4   217 1   136 4   217 1   144 4   219 1   144 4   219 1   185 4   219 1   185 4   219 1   193 4   
                                           217 1   193 4   217 1   193 4   209 1   193 4   209 1   185 4   207 1   185 4   207 1   144 4   207 1   144 4   207 1   136 4   209 1   7   255 239 4   24  1   239 4   32  1   239 4   32  1   247 4   35  1   247 4   35  1   32  5   35  1   32  5   35  1   
                                           40  5   32  1   40  5   32  1   40  5   24  1   40  5   24  1   32  5   22  1   32  5   22  1   247 4   22  1   247 4   22  1   239 4   24  1   7   255 239 4   209 1   239 4   217 1   239 4   217 1   247 4   219 1   247 4   219 1   32  5   219 1   32  5   
                                           219 1   40  5   217 1   40  5   217 1   40  5   209 1   40  5   209 1   32  5   207 1   32  5   207 1   247 4   207 1   247 4   207 1   239 4   209 1   7   255 38  3   121 1   37  3   122 1   37  3   122 1   35  3   123 1   35  3   123 1   33  3   122 1   
                                           33  3   122 1   33  3   121 1   33  3   121 1   33  3   119 1   33  3   119 1   35  3   118 1   35  3   118 1   37  3   119 1   37  3   119 1   38  3   121 1   7   255 30  3   121 1   40  3   121 1   7   255 35  3   116 1   35  3   126 1   7   255 112 3   
                                           22  1   111 3   24  1   111 3   24  1   109 3   25  1   109 3   25  1   107 3   24  1   107 3   24  1   107 3   22  1   107 3   22  1   107 3   20  1   107 3   20  1   109 3   20  1   109 3   20  1   111 3   20  1   111 3   20  1   112 3   22  1   7   255 
                                           104 3   22  1   114 3   22  1   7   255 109 3   17  1   109 3   27  1   7   255 112 3   219 1   111 3   221 1   111 3   221 1   109 3   222 1   109 3   222 1   107 3   221 1   107 3   221 1   107 3   219 1   107 3   219 1   107 3   218 1   107 3   218 1   
                                           109 3   217 1   109 3   217 1   111 3   218 1   111 3   218 1   112 3   219 1   7   255 104 3   219 1   114 3   219 1   7   255 109 3   214 1   109 3   224 1   7   255 3   6   219 1   2   6   221 1   2   6   221 1   0   6   222 1   0   6   222 1   254 5   
                                           221 1   254 5   221 1   254 5   219 1   254 5   219 1   254 5   218 1   254 5   218 1   0   6   217 1   0   6   217 1   2   6   218 1   2   6   218 1   3   6   219 1   7   255 251 5   219 1   5   6   219 1   7   255 0   6   214 1   0   6   224 1   7   255 
                                           3   6   22  1   2   6   24  1   2   6   24  1   0   6   25  1   0   6   25  1   254 5   24  1   254 5   24  1   254 5   22  1   254 5   22  1   254 5   20  1   254 5   20  1   0   6   20  1   0   6   20  1   2   6   20  1   2   6   20  1   3   6   22  1   
                                           7   255 251 5   22  1   5   6   22  1   7   255 0   6   17  1   0   6   27  1   7   255 218 4   22  1   218 4   24  1   218 4   24  1   216 4   25  1   216 4   25  1   214 4   24  1   214 4   24  1   213 4   22  1   213 4   22  1   214 4   20  1   214 4   
                                           20  1   216 4   20  1   216 4   20  1   218 4   20  1   218 4   20  1   218 4   22  1   7   255 211 4   22  1   221 4   22  1   7   255 216 4   17  1   216 4   27  1   7   255 218 4   219 1   218 4   221 1   218 4   221 1   216 4   222 1   216 4   222 1   
                                           214 4   221 1   214 4   221 1   213 4   219 1   213 4   219 1   214 4   218 1   214 4   218 1   216 4   217 1   216 4   217 1   218 4   218 1   218 4   218 1   218 4   219 1   7   255 211 4   219 1   221 4   219 1   7   255 216 4   214 1   216 4   224 1   
                                           0   252 65  117 116 111 67  65  68  32  83  108 105 100 101 13  10  26  0   86  2   73  6   247 2   97  120 67  1   2   0   52  18  7   255 7   255 134 1   101 1   69  3   101 1   69  3   101 1   69  3   150 1   69  3   150 1   134 1   150 1   134 1   150 
                                           1   134 1   101 1   7   255 134 1   101 1   134 1   101 1   7   255 134 1   101 1   134 1   101 1   7   255 134 1   101 1   134 1   101 1   7   255 158 1   125 1   158 1   127 1   158 1   127 1   158 1   128 1   158 1   128 1   156 1   129 1   156 1   129 
                                           1   155 1   130 1   155 1   130 1   153 1   130 1   153 1   130 1   152 1   130 1   152 1   130 1   150 1   129 1   150 1   129 1   149 1   128 1   149 1   128 1   149 1   127 1   149 1   127 1   148 1   125 1   148 1   125 1   149 1   124 1   149 1   124 
                                           1   149 1   122 1   149 1   122 1   150 1   121 1   150 1   121 1   152 1   120 1   152 1   120 1   153 1   120 1   153 1   120 1   155 1   120 1   155 1   120 1   156 1   121 1   156 1   121 1   158 1   122 1   158 1   122 1   158 1   124 1   158 1   124 
                                           1   158 1   125 1   7   255 172 2   153 1   172 2   161 1   172 2   161 1   179 2   164 1   179 2   164 1   218 2   164 1   218 2   164 1   226 2   161 1   226 2   161 1   226 2   153 1   226 2   153 1   218 2   150 1   218 2   150 1   179 2   150 1   179 
                                           2   150 1   172 2   153 1   7   255 172 2   177 1   172 2   186 1   172 2   186 1   179 2   188 1   179 2   188 1   218 2   188 1   218 2   188 1   226 2   186 1   226 2   186 1   226 2   177 1   226 2   177 1   218 2   175 1   218 2   175 1   179 2   175 
                                           1   179 2   175 1   172 2   177 1   7   255 172 2   89  1   172 2   98  1   172 2   98  1   179 2   100 1   179 2   100 1   218 2   100 1   218 2   100 1   226 2   98  1   226 2   98  1   226 2   89  1   226 2   89  1   218 2   87  1   218 2   87  1   179 
                                           2   87  1   179 2   87  1   172 2   89  1   7   255 172 2   65  1   172 2   73  1   172 2   73  1   179 2   76  1   179 2   76  1   218 2   76  1   218 2   76  1   226 2   73  1   226 2   73  1   226 2   65  1   226 2   65  1   218 2   62  1   218 2   62  
                                           1   179 2   62  1   179 2   62  1   172 2   65  1   7   255 240 2   65  1   240 2   73  1   240 2   73  1   247 2   76  1   247 2   76  1   31  3   76  1   31  3   76  1   38  3   73  1   38  3   73  1   38  3   65  1   38  3   65  1   31  3   62  1   31  
                                           3   62  1   247 2   62  1   247 2   62  1   240 2   65  1   7   255 240 2   89  1   240 2   98  1   240 2   98  1   247 2   100 1   247 2   100 1   31  3   100 1   31  3   100 1   38  3   98  1   38  3   98  1   38  3   89  1   38  3   89  1   31  3   87  
                                           1   31  3   87  1   247 2   87  1   247 2   87  1   240 2   89  1   7   255 240 2   153 1   240 2   161 1   240 2   161 1   247 2   164 1   247 2   164 1   31  3   164 1   31  3   164 1   38  3   161 1   38  3   161 1   38  3   153 1   38  3   153 1   31  
                                           3   150 1   31  3   150 1   247 2   150 1   247 2   150 1   240 2   153 1   7   255 240 2   177 1   240 2   186 1   240 2   186 1   247 2   188 1   247 2   188 1   31  3   188 1   31  3   188 1   38  3   186 1   38  3   186 1   38  3   177 1   38  3   177 
                                           1   31  3   175 1   31  3   175 1   247 2   175 1   247 2   175 1   240 2   177 1   7   255 78  3   125 1   78  3   127 1   78  3   127 1   77  3   129 1   77  3   129 1   76  3   130 1   76  3   130 1   75  3   132 1   75  3   132 1   73  3   133 1   73  
                                           3   133 1   71  3   133 1   71  3   133 1   69  3   134 1   69  3   134 1   67  3   133 1   67  3   133 1   66  3   133 1   66  3   133 1   64  3   132 1   64  3   132 1   63  3   130 1   63  3   130 1   62  3   129 1   62  3   129 1   61  3   127 1   61  
                                           3   127 1   61  3   125 1   61  3   125 1   61  3   123 1   61  3   123 1   62  3   122 1   62  3   122 1   63  3   120 1   63  3   120 1   64  3   119 1   64  3   119 1   66  3   118 1   66  3   118 1   67  3   117 1   67  3   117 1   69  3   117 1   69  
                                           3   117 1   71  3   117 1   71  3   117 1   73  3   118 1   73  3   118 1   75  3   119 1   75  3   119 1   76  3   120 1   76  3   120 1   77  3   122 1   77  3   122 1   78  3   123 1   78  3   123 1   78  3   125 1   7   255 56  2   125 1   55  2   127 
                                           1   55  2   127 1   55  2   129 1   55  2   129 1   53  2   130 1   53  2   130 1   52  2   132 1   52  2   132 1   50  2   132 1   50  2   132 1   48  2   133 1   48  2   133 1   46  2   132 1   46  2   132 1   44  2   132 1   44  2   132 1   43  2   130 
                                           1   43  2   130 1   42  2   129 1   42  2   129 1   41  2   127 1   41  2   127 1   41  2   125 1   41  2   125 1   41  2   123 1   41  2   123 1   42  2   122 1   42  2   122 1   43  2   120 1   43  2   120 1   44  2   119 1   44  2   119 1   46  2   118 
                                           1   46  2   118 1   48  2   118 1   48  2   118 1   50  2   118 1   50  2   118 1   52  2   119 1   52  2   119 1   53  2   120 1   53  2   120 1   55  2   122 1   55  2   122 1   55  2   123 1   55  2   123 1   56  2   125 1   7   255 74  3   125 1   74  
                                           3   127 1   74  3   127 1   73  3   128 1   73  3   128 1   72  3   129 1   72  3   129 1   71  3   130 1   71  3   130 1   69  3   130 1   69  3   130 1   68  3   130 1   68  3   130 1   66  3   129 1   66  3   129 1   65  3   128 1   65  3   128 1   65  
                                           3   127 1   65  3   127 1   64  3   125 1   64  3   125 1   65  3   124 1   65  3   124 1   65  3   122 1   65  3   122 1   66  3   121 1   66  3   121 1   68  3   121 1   68  3   121 1   69  3   120 1   69  3   120 1   71  3   121 1   71  3   121 1   72  
                                           3   121 1   72  3   121 1   73  3   122 1   73  3   122 1   74  3   124 1   74  3   124 1   74  3   125 1   7   255 60  3   125 1   79  3   125 1   7   255 69  3   116 1   69  3   135 1   7   255 158 1   125 1   158 1   127 1   158 1   127 1   157 1   128 
                                           1   157 1   128 1   156 1   129 1   156 1   129 1   155 1   130 1   155 1   130 1   153 1   130 1   153 1   130 1   152 1   130 1   152 1   130 1   151 1   129 1   151 1   129 1   149 1   128 1   149 1   128 1   149 1   127 1   149 1   127 1   149 1   125 
                                           1   149 1   125 1   149 1   124 1   149 1   124 1   149 1   122 1   149 1   122 1   151 1   121 1   151 1   121 1   152 1   121 1   152 1   121 1   153 1   120 1   153 1   120 1   155 1   121 1   155 1   121 1   156 1   121 1   156 1   121 1   157 1   122 
                                           1   157 1   122 1   158 1   124 1   158 1   124 1   158 1   125 1   7   255 144 1   125 1   163 1   125 1   7   255 153 1   116 1   153 1   135 1   7   255 238 2   188 1   238 2   190 1   238 2   190 1   237 2   191 1   237 2   191 1   236 2   192 1   236 
                                           2   192 1   234 2   193 1   234 2   193 1   233 2   193 1   233 2   193 1   231 2   193 1   231 2   193 1   230 2   192 1   230 2   192 1   229 2   191 1   229 2   191 1   228 2   190 1   228 2   190 1   228 2   188 1   228 2   188 1   228 2   187 1   228 
                                           2   187 1   229 2   186 1   229 2   186 1   230 2   184 1   230 2   184 1   231 2   184 1   231 2   184 1   233 2   184 1   233 2   184 1   234 2   184 1   234 2   184 1   236 2   184 1   236 2   184 1   237 2   186 1   237 2   186 1   238 2   187 1   238 
                                           2   187 1   238 2   188 1   7   255 223 2   188 1   243 2   188 1   7   255 233 2   179 1   233 2   198 1   7   255 238 2   62  1   238 2   64  1   238 2   64  1   237 2   65  1   237 2   65  1   236 2   66  1   236 2   66  1   234 2   67  1   234 2   67  
                                           1   233 2   67  1   233 2   67  1   231 2   67  1   231 2   67  1   230 2   66  1   230 2   66  1   229 2   65  1   229 2   65  1   228 2   64  1   228 2   64  1   228 2   62  1   228 2   62  1   228 2   61  1   228 2   61  1   229 2   59  1   229 2   59  
                                           1   230 2   58  1   230 2   58  1   231 2   57  1   231 2   57  1   233 2   57  1   233 2   57  1   234 2   57  1   234 2   57  1   236 2   58  1   236 2   58  1   237 2   59  1   237 2   59  1   238 2   61  1   238 2   61  1   238 2   62  1   7   255 223 
                                           2   62  1   243 2   62  1   7   255 233 2   52  1   233 2   72  1   1   255 1   255 53  2   125 1   53  2   127 1   53  2   127 1   52  2   128 1   52  2   128 1   51  2   129 1   51  2   129 1   50  2   130 1   50  2   130 1   48  2   130 1   48  2   130 
                                           1   47  2   130 1   47  2   130 1   45  2   129 1   45  2   129 1   44  2   128 1   44  2   128 1   44  2   127 1   44  2   127 1   43  2   125 1   43  2   125 1   44  2   124 1   44  2   124 1   44  2   122 1   44  2   122 1   45  2   121 1   45  2   121 
                                           1   47  2   121 1   47  2   121 1   48  2   120 1   48  2   120 1   50  2   121 1   50  2   121 1   51  2   121 1   51  2   121 1   52  2   122 1   52  2   122 1   53  2   124 1   53  2   124 1   53  2   125 1   1   255 38  2   125 1   58  2   125 1   1   
                                           255 48  2   116 1   48  2   135 1   7   255 7   255 195 1   132 1   195 1   133 1   195 1   133 1   196 1   135 1   196 1   135 1   197 1   136 1   197 1   136 1   200 1   137 1   200 1   137 1   204 1   137 1   204 1   137 1   207 1   136 1   207 1   136 
                                           1   208 1   135 1   208 1   135 1   209 1   133 1   209 1   133 1   209 1   130 1   209 1   130 1   208 1   128 1   208 1   128 1   206 1   125 1   206 1   125 1   194 1   113 1   194 1   113 1   210 1   113 1   7   255 62  0   62  1   10  1   62  1   10  
                                           1   62  1   10  1   100 1   10  1   100 1   187 1   100 1   187 1   100 1   187 1   150 1   187 1   150 1   10  1   150 1   10  1   150 1   10  1   188 1   10  1   188 1   62  0   188 1   62  0   188 1   62  0   62  1   7   255 62  0   62  1   62  0   62  
                                           1   7   255 62  0   62  1   62  0   62  1   7   255 62  0   62  1   62  0   62  1   7   255 92  1   65  1   92  1   73  1   92  1   73  1   100 1   76  1   100 1   76  1   139 1   76  1   139 1   76  1   147 1   73  1   147 1   73  1   147 1   65  1   147 
                                           1   65  1   139 1   62  1   139 1   62  1   100 1   62  1   100 1   62  1   92  1   65  1   7   255 92  1   89  1   92  1   98  1   92  1   98  1   100 1   100 1   100 1   100 1   139 1   100 1   139 1   100 1   147 1   98  1   147 1   98  1   147 1   89  
                                           1   147 1   89  1   139 1   87  1   139 1   87  1   100 1   87  1   100 1   87  1   92  1   89  1   7   255 160 1   65  1   160 1   73  1   160 1   73  1   168 1   76  1   168 1   76  1   207 1   76  1   207 1   76  1   215 1   73  1   215 1   73  1   215 
                                           1   65  1   215 1   65  1   207 1   62  1   207 1   62  1   168 1   62  1   168 1   62  1   160 1   65  1   7   255 160 1   89  1   160 1   98  1   160 1   98  1   168 1   100 1   168 1   100 1   207 1   100 1   207 1   100 1   215 1   98  1   215 1   98  
                                           1   215 1   89  1   215 1   89  1   207 1   87  1   207 1   87  1   168 1   87  1   168 1   87  1   160 1   89  1   7   255 92  1   153 1   92  1   161 1   92  1   161 1   100 1   164 1   100 1   164 1   139 1   164 1   139 1   164 1   147 1   161 1   147 
                                           1   161 1   147 1   153 1   147 1   153 1   139 1   150 1   139 1   150 1   100 1   150 1   100 1   150 1   92  1   153 1   7   255 92  1   177 1   92  1   186 1   92  1   186 1   100 1   188 1   100 1   188 1   139 1   188 1   139 1   188 1   147 1   186 
                                           1   147 1   186 1   147 1   177 1   147 1   177 1   139 1   175 1   139 1   175 1   100 1   175 1   100 1   175 1   92  1   177 1   7   255 160 1   153 1   160 1   161 1   160 1   161 1   168 1   164 1   168 1   164 1   207 1   164 1   207 1   164 1   215 
                                           1   161 1   215 1   161 1   215 1   153 1   215 1   153 1   207 1   150 1   207 1   150 1   168 1   150 1   168 1   150 1   160 1   153 1   7   255 160 1   177 1   160 1   186 1   160 1   186 1   168 1   188 1   168 1   188 1   207 1   188 1   207 1   188 
                                           1   215 1   186 1   215 1   186 1   215 1   177 1   215 1   177 1   207 1   175 1   207 1   175 1   168 1   175 1   168 1   175 1   160 1   177 1   7   255 166 1   138 1   164 1   140 1   164 1   140 1   162 1   141 1   162 1   141 1   159 1   142 1   159 
                                           1   142 1   156 1   143 1   156 1   143 1   153 1   143 1   153 1   143 1   151 1   143 1   151 1   143 1   148 1   142 1   148 1   142 1   145 1   141 1   145 1   141 1   143 1   140 1   143 1   140 1   141 1   138 1   141 1   138 1   139 1   136 1   139 
                                           )) "a")
 (_WriteStream FILE (vl-list->string (list 1   136 1   137 1   133 1   137 1   133 1   136 1   131 1   136 1   131 1   136 1   128 1   136 1   128 1   135 1   125 1   135 1   125 1   136 1   122 1   136 1   122 1   136 1   120 1   136 1   120 1   137 1   117 1   137 1   117 1   139 1   115 1   139 
                                           1   115 1   141 1   112 1   141 1   112 1   143 1   111 1   143 1   111 1   145 1   109 1   145 1   109 1   148 1   108 1   148 1   108 1   151 1   107 1   151 1   107 1   153 1   107 1   153 1   107 1   156 1   107 1   156 1   107 1   159 1   108 1   159 
                                           1   108 1   162 1   109 1   162 1   109 1   164 1   111 1   164 1   111 1   166 1   112 1   7   255 166 1   112 1   166 1   138 1   7   255 158 1   125 1   158 1   127 1   158 1   127 1   157 1   128 1   157 1   128 1   156 1   129 1   156 1   129 1   155 
                                           1   130 1   155 1   130 1   153 1   130 1   153 1   130 1   152 1   130 1   152 1   130 1   151 1   129 1   151 1   129 1   149 1   128 1   149 1   128 1   149 1   127 1   149 1   127 1   149 1   125 1   149 1   125 1   149 1   124 1   149 1   124 1   149 
                                           1   122 1   149 1   122 1   151 1   121 1   151 1   121 1   152 1   121 1   152 1   121 1   153 1   120 1   153 1   120 1   155 1   121 1   155 1   121 1   156 1   121 1   156 1   121 1   157 1   122 1   157 1   122 1   158 1   124 1   158 1   124 1   158 
                                           1   125 1   7   255 144 1   125 1   163 1   125 1   7   255 153 1   116 1   153 1   135 1   7   255 83  0   177 1   83  0   186 1   83  0   186 1   91  0   188 1   91  0   188 1   130 0   188 1   130 0   188 1   138 0   186 1   138 0   186 1   138 0   177 
                                           1   138 0   177 1   130 0   175 1   130 0   175 1   91  0   175 1   91  0   175 1   83  0   177 1   7   255 83  0   65  1   83  0   73  1   83  0   73  1   91  0   76  1   91  0   76  1   130 0   76  1   130 0   76  1   138 0   73  1   138 0   73  1   138 
                                           0   65  1   138 0   65  1   130 0   62  1   130 0   62  1   91  0   62  1   91  0   62  1   83  0   65  1   7   255 115 0   125 1   115 0   127 1   115 0   127 1   114 0   128 1   114 0   128 1   113 0   129 1   113 0   129 1   112 0   130 1   112 0   130 
                                           1   110 0   130 1   110 0   130 1   109 0   130 1   109 0   130 1   108 0   129 1   108 0   129 1   106 0   128 1   106 0   128 1   106 0   127 1   106 0   127 1   106 0   125 1   106 0   125 1   106 0   124 1   106 0   124 1   106 0   122 1   106 0   122 
                                           1   108 0   121 1   108 0   121 1   109 0   121 1   109 0   121 1   110 0   120 1   110 0   120 1   112 0   121 1   112 0   121 1   113 0   121 1   113 0   121 1   114 0   122 1   114 0   122 1   115 0   124 1   115 0   124 1   115 0   125 1   7   255 101 
                                           0   125 1   120 0   125 1   7   255 110 0   116 1   110 0   135 1   7   255 115 0   188 1   115 0   190 1   115 0   190 1   114 0   191 1   114 0   191 1   113 0   192 1   113 0   192 1   112 0   193 1   112 0   193 1   110 0   193 1   110 0   193 1   109 
                                           0   193 1   109 0   193 1   108 0   192 1   108 0   192 1   106 0   191 1   106 0   191 1   106 0   190 1   106 0   190 1   106 0   188 1   106 0   188 1   106 0   187 1   106 0   187 1   106 0   186 1   106 0   186 1   108 0   184 1   108 0   184 1   109 
                                           0   184 1   109 0   184 1   110 0   184 1   110 0   184 1   112 0   184 1   112 0   184 1   113 0   184 1   113 0   184 1   114 0   186 1   114 0   186 1   115 0   187 1   115 0   187 1   115 0   188 1   7   255 101 0   188 1   120 0   188 1   7   255 110 
                                           0   179 1   110 0   198 1   7   255 115 0   62  1   115 0   64  1   115 0   64  1   114 0   65  1   114 0   65  1   113 0   66  1   113 0   66  1   112 0   67  1   112 0   67  1   110 0   67  1   110 0   67  1   109 0   67  1   109 0   67  1   108 0   66  
                                           1   108 0   66  1   106 0   65  1   106 0   65  1   106 0   64  1   106 0   64  1   106 0   62  1   106 0   62  1   106 0   61  1   106 0   61  1   106 0   59  1   106 0   59  1   108 0   58  1   108 0   58  1   109 0   57  1   109 0   57  1   110 0   57  
                                           1   110 0   57  1   112 0   57  1   112 0   57  1   113 0   58  1   113 0   58  1   114 0   59  1   114 0   59  1   115 0   61  1   115 0   61  1   115 0   62  1   7   255 101 0   62  1   120 0   62  1   7   255 110 0   52  1   110 0   72  1   7   255 158 
                                           1   188 1   158 1   190 1   158 1   190 1   157 1   191 1   157 1   191 1   156 1   192 1   156 1   192 1   155 1   193 1   155 1   193 1   153 1   193 1   153 1   193 1   152 1   193 1   152 1   193 1   151 1   192 1   151 1   192 1   149 1   191 1   149 
                                           1   191 1   149 1   190 1   149 1   190 1   149 1   188 1   149 1   188 1   149 1   187 1   149 1   187 1   149 1   186 1   149 1   186 1   151 1   184 1   151 1   184 1   152 1   184 1   152 1   184 1   153 1   184 1   153 1   184 1   155 1   184 1   155 
                                           1   184 1   156 1   184 1   156 1   184 1   157 1   186 1   157 1   186 1   158 1   187 1   158 1   187 1   158 1   188 1   7   255 144 1   188 1   163 1   188 1   7   255 153 1   179 1   153 1   198 1   7   255 158 1   62  1   158 1   64  1   158 1   64  
                                           1   157 1   65  1   157 1   65  1   156 1   66  1   156 1   66  1   155 1   67  1   155 1   67  1   153 1   67  1   153 1   67  1   152 1   67  1   152 1   67  1   151 1   66  1   151 1   66  1   149 1   65  1   149 1   65  1   149 1   64  1   149 1   64  
                                           1   149 1   62  1   149 1   62  1   149 1   61  1   149 1   61  1   149 1   59  1   149 1   59  1   151 1   58  1   151 1   58  1   152 1   57  1   152 1   57  1   153 1   57  1   153 1   57  1   155 1   57  1   155 1   57  1   156 1   58  1   156 1   58  
                                           1   157 1   59  1   157 1   59  1   158 1   61  1   158 1   61  1   158 1   62  1   7   255 144 1   62  1   163 1   62  1   7   255 153 1   52  1   153 1   72  1   7   255 67  0   62  1   66  0   64  1   66  0   64  1   66  0   65  1   66  0   65  1   65  
                                           0   66  1   65  0   66  1   63  0   67  1   63  0   67  1   62  0   67  1   62  0   67  1   60  0   67  1   60  0   67  1   59  0   66  1   59  0   66  1   58  0   65  1   58  0   65  1   57  0   64  1   57  0   64  1   57  0   62  1   57  0   62  1   57  
                                           0   61  1   57  0   61  1   58  0   59  1   58  0   59  1   59  0   58  1   59  0   58  1   60  0   57  1   60  0   57  1   62  0   57  1   62  0   57  1   63  0   57  1   63  0   57  1   65  0   58  1   65  0   58  1   66  0   59  1   66  0   59  1   66  
                                           0   61  1   66  0   61  1   67  0   62  1   7   255 52  0   62  1   71  0   62  1   7   255 62  0   52  1   62  0   72  1   7   255 67  0   188 1   66  0   190 1   66  0   190 1   66  0   191 1   66  0   191 1   65  0   192 1   65  0   192 1   63  0   193 
                                           1   63  0   193 1   62  0   193 1   62  0   193 1   60  0   193 1   60  0   193 1   59  0   192 1   59  0   192 1   58  0   191 1   58  0   191 1   57  0   190 1   57  0   190 1   57  0   188 1   57  0   188 1   57  0   187 1   57  0   187 1   58  0   186 
                                           1   58  0   186 1   59  0   184 1   59  0   184 1   60  0   184 1   60  0   184 1   62  0   184 1   62  0   184 1   63  0   184 1   63  0   184 1   65  0   184 1   65  0   184 1   66  0   186 1   66  0   186 1   66  0   187 1   66  0   187 1   67  0   188 
                                           1   7   255 52  0   188 1   71  0   188 1   7   255 62  0   179 1   62  0   198 1   7   255 156 0   133 1   158 0   134 1   158 0   134 1   162 0   137 1   162 0   137 1   162 0   113 1   7   255 69  3   101 1   132 4   101 1   132 4   101 1   132 4   150 
                                           1   132 4   150 1   69  3   150 1   69  3   150 1   69  3   101 1   7   255 69  3   101 1   69  3   101 1   7   255 69  3   101 1   69  3   101 1   7   255 69  3   101 1   69  3   101 1   7   255 74  3   125 1   74  3   127 1   74  3   127 1   73  3   128 
                                           1   73  3   128 1   72  3   129 1   72  3   129 1   71  3   130 1   71  3   130 1   69  3   130 1   69  3   130 1   68  3   130 1   68  3   130 1   66  3   129 1   66  3   129 1   65  3   128 1   65  3   128 1   65  3   127 1   65  3   127 1   64  3   125 
                                           1   64  3   125 1   65  3   124 1   65  3   124 1   65  3   122 1   65  3   122 1   66  3   121 1   66  3   121 1   68  3   121 1   68  3   121 1   69  3   120 1   69  3   120 1   71  3   121 1   71  3   121 1   72  3   121 1   72  3   121 1   73  3   122 
                                           1   73  3   122 1   74  3   124 1   74  3   124 1   74  3   125 1   7   255 244 3   153 1   244 3   161 1   244 3   161 1   252 3   164 1   252 3   164 1   35  4   164 1   35  4   164 1   42  4   161 1   42  4   161 1   42  4   153 1   42  4   153 1   35  
                                           4   150 1   35  4   150 1   252 3   150 1   252 3   150 1   244 3   153 1   7   255 244 3   177 1   244 3   186 1   244 3   186 1   252 3   188 1   252 3   188 1   35  4   188 1   35  4   188 1   42  4   186 1   42  4   186 1   42  4   177 1   42  4   177 
                                           1   35  4   175 1   35  4   175 1   252 3   175 1   252 3   175 1   244 3   177 1   7   255 56  4   177 1   56  4   186 1   56  4   186 1   64  4   188 1   64  4   188 1   103 4   188 1   103 4   188 1   110 4   186 1   110 4   186 1   110 4   177 1   110 
                                           4   177 1   103 4   175 1   103 4   175 1   64  4   175 1   64  4   175 1   56  4   177 1   7   255 56  4   65  1   56  4   73  1   56  4   73  1   64  4   76  1   64  4   76  1   103 4   76  1   103 4   76  1   110 4   73  1   110 4   73  1   110 4   65  
                                           1   110 4   65  1   103 4   62  1   103 4   62  1   64  4   62  1   64  4   62  1   56  4   65  1   7   255 56  4   89  1   56  4   98  1   56  4   98  1   64  4   100 1   64  4   100 1   103 4   100 1   103 4   100 1   110 4   98  1   110 4   98  1   110 
                                           4   89  1   110 4   89  1   103 4   87  1   103 4   87  1   64  4   87  1   64  4   87  1   56  4   89  1   7   255 244 3   65  1   244 3   73  1   244 3   73  1   252 3   76  1   252 3   76  1   35  4   76  1   35  4   76  1   42  4   73  1   42  4   73  
                                           1   42  4   65  1   42  4   65  1   35  4   62  1   35  4   62  1   252 3   62  1   252 3   62  1   244 3   65  1   7   255 244 3   89  1   244 3   98  1   244 3   98  1   252 3   100 1   252 3   100 1   35  4   100 1   35  4   100 1   42  4   98  1   42  
                                           4   98  1   42  4   89  1   42  4   89  1   35  4   87  1   35  4   87  1   252 3   87  1   252 3   87  1   244 3   89  1   7   255 56  4   153 1   56  4   161 1   56  4   161 1   64  4   164 1   64  4   164 1   103 4   164 1   103 4   164 1   110 4   161 
                                           1   110 4   161 1   110 4   153 1   110 4   153 1   103 4   150 1   103 4   150 1   64  4   150 1   64  4   150 1   56  4   153 1   1   255 1   255 54  4   125 1   54  4   127 1   54  4   127 1   53  4   128 1   53  4   128 1   52  4   129 1   52  4   129 
                                           1   51  4   130 1   51  4   130 1   49  4   130 1   49  4   130 1   48  4   130 1   48  4   130 1   46  4   129 1   46  4   129 1   45  4   128 1   45  4   128 1   44  4   127 1   44  4   127 1   44  4   125 1   44  4   125 1   44  4   124 1   44  4   124 
                                           1   45  4   122 1   45  4   122 1   46  4   121 1   46  4   121 1   48  4   121 1   48  4   121 1   49  4   120 1   49  4   120 1   51  4   121 1   51  4   121 1   52  4   121 1   52  4   121 1   53  4   122 1   53  4   122 1   54  4   124 1   54  4   124 
                                           1   54  4   125 1   1   255 39  4   125 1   59  4   125 1   1   255 49  4   116 1   49  4   135 1   7   255 7   255 57  4   125 1   56  4   127 1   56  4   127 1   56  4   129 1   56  4   129 1   54  4   130 1   54  4   130 1   53  4   132 1   53  4   132 
                                           1   51  4   132 1   51  4   132 1   49  4   133 1   49  4   133 1   47  4   132 1   47  4   132 1   45  4   132 1   45  4   132 1   44  4   130 1   44  4   130 1   43  4   129 1   43  4   129 1   42  4   127 1   42  4   127 1   42  4   125 1   42  4   125 
                                           1   42  4   123 1   42  4   123 1   43  4   122 1   43  4   122 1   44  4   120 1   44  4   120 1   45  4   119 1   45  4   119 1   47  4   118 1   47  4   118 1   49  4   118 1   49  4   118 1   51  4   118 1   51  4   118 1   53  4   119 1   53  4   119 
                                           1   54  4   120 1   54  4   120 1   56  4   122 1   56  4   122 1   56  4   123 1   56  4   123 1   57  4   125 1   7   255 74  3   125 1   74  3   127 1   74  3   127 1   73  3   128 1   73  3   128 1   72  3   129 1   72  3   129 1   71  3   130 1   71  
                                           3   130 1   69  3   130 1   69  3   130 1   68  3   130 1   68  3   130 1   66  3   129 1   66  3   129 1   65  3   128 1   65  3   128 1   65  3   127 1   65  3   127 1   64  3   125 1   64  3   125 1   65  3   124 1   65  3   124 1   65  3   122 1   65  
                                           3   122 1   66  3   121 1   66  3   121 1   68  3   121 1   68  3   121 1   69  3   120 1   69  3   120 1   71  3   121 1   71  3   121 1   72  3   121 1   72  3   121 1   73  3   122 1   73  3   122 1   74  3   124 1   74  3   124 1   74  3   125 1   7   
                                           255 60  3   125 1   79  3   125 1   7   255 69  3   116 1   69  3   135 1   7   255 54  4   188 1   54  4   190 1   54  4   190 1   53  4   191 1   53  4   191 1   52  4   192 1   52  4   192 1   51  4   193 1   51  4   193 1   49  4   193 1   49  4   193 
                                           1   48  4   193 1   48  4   193 1   46  4   192 1   46  4   192 1   45  4   191 1   45  4   191 1   44  4   190 1   44  4   190 1   44  4   188 1   44  4   188 1   44  4   187 1   44  4   187 1   45  4   186 1   45  4   186 1   46  4   184 1   46  4   184 
                                           1   48  4   184 1   48  4   184 1   49  4   184 1   49  4   184 1   51  4   184 1   51  4   184 1   52  4   184 1   52  4   184 1   53  4   186 1   53  4   186 1   54  4   187 1   54  4   187 1   54  4   188 1   7   255 39  4   188 1   59  4   188 1   7   
                                           255 49  4   179 1   49  4   198 1   7   255 54  4   62  1   54  4   64  1   54  4   64  1   53  4   65  1   53  4   65  1   52  4   66  1   52  4   66  1   51  4   67  1   51  4   67  1   49  4   67  1   49  4   67  1   48  4   67  1   48  4   67  1   46  
                                           4   66  1   46  4   66  1   45  4   65  1   45  4   65  1   44  4   64  1   44  4   64  1   44  4   62  1   44  4   62  1   44  4   61  1   44  4   61  1   45  4   59  1   45  4   59  1   46  4   58  1   46  4   58  1   48  4   57  1   48  4   57  1   49  
                                           4   57  1   49  4   57  1   51  4   57  1   51  4   57  1   52  4   58  1   52  4   58  1   53  4   59  1   53  4   59  1   54  4   61  1   54  4   61  1   54  4   62  1   7   255 39  4   62  1   59  4   62  1   7   255 49  4   52  1   49  4   72  1   7   
                                           255 112 3   137 1   125 3   137 1   125 3   137 1   118 3   128 1   118 3   128 1   121 3   128 1   121 3   128 1   124 3   127 1   124 3   127 1   125 3   126 1   125 3   126 1   126 3   122 1   126 3   122 1   126 3   120 1   126 3   120 1   125 3   117 
                                           1   125 3   117 1   123 3   114 1   123 3   114 1   119 3   113 1   119 3   113 1   116 3   113 1   116 3   113 1   112 3   114 1   112 3   114 1   111 3   115 1   111 3   115 1   110 3   118 1   7   255 57  4   125 1   56  4   127 1   56  4   127 1   56  
                                           4   129 1   56  4   129 1   54  4   130 1   54  4   130 1   53  4   132 1   53  4   132 1   51  4   132 1   51  4   132 1   49  4   133 1   49  4   133 1   47  4   132 1   47  4   132 1   45  4   132 1   45  4   132 1   44  4   130 1   44  4   130 1   43  
                                           4   129 1   43  4   129 1   42  4   127 1   42  4   127 1   42  4   125 1   42  4   125 1   42  4   123 1   42  4   123 1   43  4   122 1   43  4   122 1   44  4   120 1   44  4   120 1   45  4   119 1   45  4   119 1   47  4   118 1   47  4   118 1   49  
                                           4   118 1   49  4   118 1   51  4   118 1   51  4   118 1   53  4   119 1   53  4   119 1   54  4   120 1   54  4   120 1   56  4   122 1   56  4   122 1   56  4   123 1   56  4   123 1   57  4   125 1   7   255 153 1   48  1   9   6   48  1   9   6   48  
                                           1   9   6   203 1   9   6   203 1   153 1   203 1   153 1   203 1   153 1   48  1   7   255 153 1   48  1   153 1   48  1   7   255 153 1   48  1   153 1   48  1   7   255 56  2   125 1   55  2   127 1   55  2   127 1   55  2   129 1   55  2   129 1   53  
                                           2   130 1   53  2   130 1   52  2   132 1   52  2   132 1   50  2   132 1   50  2   132 1   48  2   133 1   48  2   133 1   46  2   132 1   46  2   132 1   44  2   132 1   44  2   132 1   43  2   130 1   43  2   130 1   42  2   129 1   42  2   129 1   41  
                                           2   127 1   41  2   127 1   41  2   125 1   41  2   125 1   41  2   123 1   41  2   123 1   42  2   122 1   42  2   122 1   43  2   120 1   43  2   120 1   44  2   119 1   44  2   119 1   46  2   118 1   46  2   118 1   48  2   118 1   48  2   118 1   50  
                                           2   118 1   50  2   118 1   52  2   119 1   52  2   119 1   53  2   120 1   53  2   120 1   55  2   122 1   55  2   122 1   55  2   123 1   55  2   123 1   56  2   125 1   3   255 3   255 53  2   125 1   53  2   127 1   53  2   127 1   52  2   128 1   52  
                                           2   128 1   51  2   129 1   51  2   129 1   50  2   130 1   50  2   130 1   48  2   130 1   48  2   130 1   47  2   130 1   47  2   130 1   45  2   129 1   45  2   129 1   44  2   128 1   44  2   128 1   44  2   127 1   44  2   127 1   43  2   125 1   43  
                                           )) "a")
 (_WriteStream FILE (vl-list->string (list 2   125 1   44  2   124 1   44  2   124 1   44  2   122 1   44  2   122 1   45  2   121 1   45  2   121 1   47  2   121 1   47  2   121 1   48  2   120 1   48  2   120 1   50  2   121 1   50  2   121 1   51  2   121 1   51  2   121 1   52  2   122 1   52  
                                           2   122 1   53  2   124 1   53  2   124 1   53  2   125 1   3   255 38  2   125 1   58  2   125 1   3   255 48  2   116 1   48  2   135 1   3   255 54  4   125 1   54  4   127 1   54  4   127 1   53  4   128 1   53  4   128 1   52  4   129 1   52  4   129 
                                           1   51  4   130 1   51  4   130 1   49  4   130 1   49  4   130 1   48  4   130 1   48  4   130 1   46  4   129 1   46  4   129 1   45  4   128 1   45  4   128 1   44  4   127 1   44  4   127 1   44  4   125 1   44  4   125 1   44  4   124 1   44  4   124 
                                           1   45  4   122 1   45  4   122 1   46  4   121 1   46  4   121 1   48  4   121 1   48  4   121 1   49  4   120 1   49  4   120 1   51  4   121 1   51  4   121 1   52  4   121 1   52  4   121 1   53  4   122 1   53  4   122 1   54  4   124 1   54  4   124 
                                           1   54  4   125 1   3   255 39  4   125 1   59  4   125 1   3   255 49  4   116 1   49  4   135 1   7   255 7   255 158 1   203 1   158 1   204 1   158 1   204 1   157 1   206 1   157 1   206 1   156 1   207 1   156 1   207 1   155 1   208 1   155 1   208 
                                           1   153 1   208 1   153 1   208 1   152 1   208 1   152 1   208 1   151 1   207 1   151 1   207 1   149 1   206 1   149 1   206 1   149 1   204 1   149 1   204 1   149 1   203 1   149 1   203 1   149 1   201 1   149 1   201 1   149 1   200 1   149 1   200 
                                           1   151 1   199 1   151 1   199 1   152 1   198 1   152 1   198 1   153 1   198 1   153 1   198 1   155 1   198 1   155 1   198 1   156 1   199 1   156 1   199 1   157 1   200 1   157 1   200 1   158 1   201 1   158 1   201 1   158 1   203 1   7   255 144 
                                           1   203 1   163 1   203 1   7   255 153 1   193 1   153 1   213 1   7   255 158 1   48  1   158 1   49  1   158 1   49  1   157 1   50  1   157 1   50  1   156 1   51  1   156 1   51  1   155 1   52  1   155 1   52  1   153 1   52  1   153 1   52  1   152 
                                           1   52  1   152 1   52  1   151 1   51  1   151 1   51  1   149 1   50  1   149 1   50  1   149 1   49  1   149 1   49  1   149 1   48  1   149 1   48  1   149 1   46  1   149 1   46  1   149 1   45  1   149 1   45  1   151 1   44  1   151 1   44  1   152 
                                           1   43  1   152 1   43  1   153 1   43  1   153 1   43  1   155 1   43  1   155 1   43  1   156 1   44  1   156 1   44  1   157 1   45  1   157 1   45  1   158 1   46  1   158 1   46  1   158 1   48  1   7   255 144 1   48  1   163 1   48  1   7   255 153 
                                           1   38  1   153 1   57  1   7   255 14  6   48  1   13  6   49  1   13  6   49  1   13  6   50  1   13  6   50  1   12  6   51  1   12  6   51  1   10  6   52  1   10  6   52  1   9   6   52  1   9   6   52  1   7   6   52  1   7   6   52  1   6   6   51  
                                           1   6   6   51  1   5   6   50  1   5   6   50  1   4   6   49  1   4   6   49  1   4   6   48  1   4   6   48  1   4   6   46  1   4   6   46  1   5   6   45  1   5   6   45  1   6   6   44  1   6   6   44  1   7   6   43  1   7   6   43  1   9   6   43  
                                           1   9   6   43  1   10  6   43  1   10  6   43  1   12  6   44  1   12  6   44  1   13  6   45  1   13  6   45  1   13  6   46  1   13  6   46  1   14  6   48  1   7   255 255 5   48  1   18  6   48  1   7   255 9   6   38  1   9   6   57  1   7   255 14  
                                           6   203 1   13  6   204 1   13  6   204 1   13  6   206 1   13  6   206 1   12  6   207 1   12  6   207 1   10  6   208 1   10  6   208 1   9   6   208 1   9   6   208 1   7   6   208 1   7   6   208 1   6   6   207 1   6   6   207 1   5   6   206 1   5   
                                           6   206 1   4   6   204 1   4   6   204 1   4   6   203 1   4   6   203 1   4   6   201 1   4   6   201 1   5   6   200 1   5   6   200 1   6   6   199 1   6   6   199 1   7   6   198 1   7   6   198 1   9   6   198 1   9   6   198 1   10  6   198 1   10  
                                           6   198 1   12  6   199 1   12  6   199 1   13  6   200 1   13  6   200 1   13  6   201 1   13  6   201 1   14  6   203 1   7   255 255 5   203 1   18  6   203 1   7   255 9   6   193 1   9   6   213 1   7   255 100 2   137 1   88  2   121 1   88  2   121 
                                           1   105 2   121 1   7   255 100 2   137 1   100 2   113 1   0   252 65  117 116 111 67  65  68  32  83  108 105 100 101 13  10  26  0   86  2   106 6   234 2   99  219 79  1   2   0   52  18  7   255 7   255 69  0   242 0   43  6   242 0   43  6   242 0   
                                           43  6   245 1   43  6   245 1   69  0   245 1   69  0   245 1   69  0   242 0   7   255 69  0   242 0   69  0   242 0   7   255 69  0   242 0   69  0   242 0   7   255 69  4   247 0   69  4   8   1   69  4   8   1   84  4   13  1   84  4   13  1   163 4   
                                           13  1   163 4   13  1   178 4   8   1   178 4   8   1   178 4   247 0   178 4   247 0   163 4   242 0   163 4   242 0   84  4   242 0   84  4   242 0   69  4   247 0   7   255 69  4   222 1   69  4   239 1   69  4   239 1   84  4   245 1   84  4   245 1   
                                           163 4   245 1   163 4   245 1   178 4   239 1   178 4   239 1   178 4   222 1   178 4   222 1   163 4   217 1   163 4   217 1   84  4   217 1   84  4   217 1   69  4   222 1   7   255 80  0   242 0   79  0   247 0   79  0   247 0   75  0   251 0   75  0   
                                           251 0   69  0   253 0   69  0   253 0   64  0   251 0   64  0   251 0   60  0   247 0   60  0   247 0   59  0   242 0   59  0   242 0   60  0   237 0   60  0   237 0   64  0   233 0   64  0   233 0   69  0   231 0   69  0   231 0   75  0   233 0   75  0   
                                           233 0   79  0   237 0   79  0   237 0   80  0   242 0   7   255 48  0   242 0   91  0   242 0   7   255 69  0   220 0   69  0   8   1   7   255 80  0   245 1   79  0   250 1   79  0   250 1   75  0   254 1   75  0   254 1   69  0   255 1   69  0   255 1   
                                           64  0   254 1   64  0   254 1   60  0   250 1   60  0   250 1   59  0   245 1   59  0   245 1   60  0   239 1   60  0   239 1   64  0   235 1   64  0   235 1   69  0   234 1   69  0   234 1   75  0   235 1   75  0   235 1   79  0   239 1   79  0   239 1   
                                           80  0   245 1   7   255 48  0   245 1   91  0   245 1   7   255 69  0   223 1   69  0   10  2   7   255 53  6   245 1   52  6   250 1   52  6   250 1   48  6   254 1   48  6   254 1   43  6   255 1   43  6   255 1   37  6   254 1   37  6   254 1   33  6   
                                           250 1   33  6   250 1   32  6   245 1   32  6   245 1   33  6   239 1   33  6   239 1   37  6   235 1   37  6   235 1   43  6   234 1   43  6   234 1   48  6   235 1   48  6   235 1   52  6   239 1   52  6   239 1   53  6   245 1   7   255 21  6   245 1   
                                           64  6   245 1   7   255 43  6   223 1   43  6   10  2   7   255 53  6   242 0   52  6   247 0   52  6   247 0   48  6   251 0   48  6   251 0   43  6   253 0   43  6   253 0   37  6   251 0   37  6   251 0   33  6   247 0   33  6   247 0   32  6   242 0   
                                           32  6   242 0   33  6   237 0   33  6   237 0   37  6   233 0   37  6   233 0   43  6   231 0   43  6   231 0   48  6   233 0   48  6   233 0   52  6   237 0   52  6   237 0   53  6   242 0   7   255 21  6   242 0   64  6   242 0   7   255 43  6   220 0   
                                           43  6   8   1   7   255 18  1   242 0   17  1   247 0   17  1   247 0   13  1   251 0   13  1   251 0   7   1   253 0   7   1   253 0   2   1   251 0   2   1   251 0   254 0   247 0   254 0   247 0   253 0   242 0   253 0   242 0   254 0   237 0   254 0   
                                           237 0   2   1   233 0   2   1   233 0   7   1   231 0   7   1   231 0   13  1   233 0   13  1   233 0   17  1   237 0   17  1   237 0   18  1   242 0   7   255 242 0   242 0   29  1   242 0   7   255 7   1   220 0   7   1   8   1   7   255 18  1   245 1   
                                           17  1   250 1   17  1   250 1   13  1   254 1   13  1   254 1   7   1   255 1   7   1   255 1   2   1   254 1   2   1   254 1   254 0   250 1   254 0   250 1   253 0   245 1   253 0   245 1   254 0   239 1   254 0   239 1   2   1   235 1   2   1   235 1   
                                           7   1   234 1   7   1   234 1   13  1   235 1   13  1   235 1   17  1   239 1   17  1   239 1   18  1   245 1   7   255 242 0   245 1   29  1   245 1   7   255 7   1   223 1   7   1   10  2   7   255 134 4   245 1   133 4   250 1   133 4   250 1   129 4   
                                           254 1   129 4   254 1   123 4   255 1   123 4   255 1   118 4   254 1   118 4   254 1   114 4   250 1   114 4   250 1   113 4   245 1   113 4   245 1   114 4   239 1   114 4   239 1   118 4   235 1   118 4   235 1   123 4   234 1   123 4   234 1   129 4   
                                           235 1   129 4   235 1   133 4   239 1   133 4   239 1   134 4   245 1   7   255 102 4   245 1   145 4   245 1   7   255 123 4   223 1   123 4   10  2   7   255 134 4   242 0   133 4   247 0   133 4   247 0   129 4   251 0   129 4   251 0   123 4   253 0   
                                           123 4   253 0   118 4   251 0   118 4   251 0   114 4   247 0   114 4   247 0   113 4   242 0   113 4   242 0   114 4   237 0   114 4   237 0   118 4   233 0   118 4   233 0   123 4   231 0   123 4   231 0   129 4   233 0   129 4   233 0   133 4   237 0   
                                           133 4   237 0   134 4   242 0   7   255 102 4   242 0   145 4   242 0   7   255 123 4   220 0   123 4   8   1   7   255 18  1   115 1   17  1   121 1   17  1   121 1   13  1   125 1   13  1   125 1   7   1   126 1   7   1   126 1   2   1   125 1   2   1   
                                           125 1   254 0   121 1   254 0   121 1   253 0   115 1   253 0   115 1   254 0   110 1   254 0   110 1   2   1   106 1   2   1   106 1   7   1   105 1   7   1   105 1   13  1   106 1   13  1   106 1   17  1   110 1   17  1   110 1   18  1   115 1   7   255 
                                           242 0   115 1   29  1   115 1   7   255 7   1   94  1   7   1   137 1   7   255 209 0   222 1   209 0   239 1   209 0   239 1   224 0   245 1   224 0   245 1   47  1   245 1   47  1   245 1   62  1   239 1   62  1   239 1   62  1   222 1   62  1   222 1   
                                           47  1   217 1   47  1   217 1   224 0   217 1   224 0   217 1   209 0   222 1   7   255 209 0   247 0   209 0   8   1   209 0   8   1   224 0   13  1   224 0   13  1   47  1   13  1   47  1   13  1   62  1   8   1   62  1   8   1   62  1   247 0   62  1   
                                           247 0   47  1   242 0   47  1   242 0   224 0   242 0   224 0   242 0   209 0   247 0   0   252 65  117 116 111 67  65  68  32  83  108 105 100 101 13  10  26  0   86  2   73  6   31  3   200 70  51  1   2   0   52  18  7   255 7   255 64  0   246 1   64  
                                           0   248 1   64  0   248 1   63  0   251 1   63  0   251 1   61  0   252 1   61  0   252 1   59  0   253 1   59  0   253 1   56  0   254 1   56  0   254 1   54  0   253 1   54  0   253 1   52  0   252 1   52  0   252 1   50  0   251 1   50  0   251 1   49  
                                           0   248 1   49  0   248 1   49  0   246 1   49  0   246 1   49  0   244 1   49  0   244 1   50  0   242 1   50  0   242 1   52  0   240 1   52  0   240 1   54  0   239 1   54  0   239 1   56  0   239 1   56  0   239 1   59  0   239 1   59  0   239 1   61  
                                           0   240 1   61  0   240 1   63  0   242 1   63  0   242 1   64  0   244 1   64  0   244 1   64  0   246 1   7   255 42  0   246 1   71  0   246 1   7   255 56  0   231 1   56  0   5   2   7   255 64  0   52  1   64  0   54  1   64  0   54  1   63  0   56  
                                           1   63  0   56  1   61  0   58  1   61  0   58  1   59  0   59  1   59  0   59  1   56  0   59  1   56  0   59  1   54  0   59  1   54  0   59  1   52  0   58  1   52  0   58  1   50  0   56  1   50  0   56  1   49  0   54  1   49  0   54  1   49  0   52  
                                           1   49  0   52  1   49  0   49  1   49  0   49  1   50  0   47  1   50  0   47  1   52  0   45  1   52  0   45  1   54  0   44  1   54  0   44  1   56  0   44  1   56  0   44  1   59  0   44  1   59  0   44  1   61  0   45  1   61  0   45  1   63  0   47  
                                           1   63  0   47  1   64  0   49  1   64  0   49  1   64  0   52  1   7   255 42  0   52  1   71  0   52  1   7   255 56  0   37  1   56  0   67  1   7   255 31  2   52  1   31  2   54  1   31  2   54  1   30  2   56  1   30  2   56  1   28  2   58  1   28  
                                           2   58  1   26  2   59  1   26  2   59  1   24  2   59  1   24  2   59  1   21  2   59  1   21  2   59  1   19  2   58  1   19  2   58  1   18  2   56  1   18  2   56  1   17  2   54  1   17  2   54  1   16  2   52  1   16  2   52  1   17  2   49  1   17  
                                           2   49  1   18  2   47  1   18  2   47  1   19  2   45  1   19  2   45  1   21  2   44  1   21  2   44  1   24  2   44  1   24  2   44  1   26  2   44  1   26  2   44  1   28  2   45  1   28  2   45  1   30  2   47  1   30  2   47  1   31  2   49  1   31  
                                           2   49  1   31  2   52  1   7   255 9   2   52  1   39  2   52  1   7   255 24  2   37  1   24  2   67  1   7   255 31  2   246 1   31  2   248 1   31  2   248 1   30  2   251 1   30  2   251 1   28  2   252 1   28  2   252 1   26  2   253 1   26  2   253 
                                           1   24  2   254 1   24  2   254 1   21  2   253 1   21  2   253 1   19  2   252 1   19  2   252 1   18  2   251 1   18  2   251 1   17  2   248 1   17  2   248 1   16  2   246 1   16  2   246 1   17  2   244 1   17  2   244 1   18  2   242 1   18  2   242 
                                           1   19  2   240 1   19  2   240 1   21  2   239 1   21  2   239 1   24  2   239 1   24  2   239 1   26  2   239 1   26  2   239 1   28  2   240 1   28  2   240 1   30  2   242 1   30  2   242 1   31  2   244 1   31  2   244 1   31  2   246 1   7   255 9   
                                           2   246 1   39  2   246 1   7   255 24  2   231 1   24  2   5   2   7   255 131 0   52  1   131 0   54  1   131 0   54  1   130 0   56  1   130 0   56  1   128 0   58  1   128 0   58  1   126 0   59  1   126 0   59  1   124 0   59  1   124 0   59  1   122 
                                           0   59  1   122 0   59  1   119 0   58  1   119 0   58  1   118 0   56  1   118 0   56  1   117 0   54  1   117 0   54  1   116 0   52  1   116 0   52  1   117 0   49  1   117 0   49  1   118 0   47  1   118 0   47  1   119 0   45  1   119 0   45  1   122 
                                           0   44  1   122 0   44  1   124 0   44  1   124 0   44  1   126 0   44  1   126 0   44  1   128 0   45  1   128 0   45  1   130 0   47  1   130 0   47  1   131 0   49  1   131 0   49  1   131 0   52  1   7   255 109 0   52  1   139 0   52  1   7   255 124 
                                           0   37  1   124 0   67  1   7   255 131 0   246 1   131 0   248 1   131 0   248 1   130 0   251 1   130 0   251 1   128 0   252 1   128 0   252 1   126 0   253 1   126 0   253 1   124 0   254 1   124 0   254 1   122 0   253 1   122 0   253 1   119 0   252 
                                           1   119 0   252 1   118 0   251 1   118 0   251 1   117 0   248 1   117 0   248 1   116 0   246 1   116 0   246 1   117 0   244 1   117 0   244 1   118 0   242 1   118 0   242 1   119 0   240 1   119 0   240 1   122 0   239 1   122 0   239 1   124 0   239 
                                           1   124 0   239 1   126 0   239 1   126 0   239 1   128 0   240 1   128 0   240 1   130 0   242 1   130 0   242 1   131 0   244 1   131 0   244 1   131 0   246 1   7   255 109 0   246 1   139 0   246 1   7   255 124 0   231 1   124 0   5   2   7   255 131 
                                           0   149 1   131 0   151 1   131 0   151 1   130 0   153 1   130 0   153 1   128 0   155 1   128 0   155 1   126 0   156 1   126 0   156 1   124 0   156 1   124 0   156 1   122 0   156 1   122 0   156 1   119 0   155 1   119 0   155 1   118 0   153 1   118 
                                           0   153 1   117 0   151 1   117 0   151 1   116 0   149 1   116 0   149 1   117 0   147 1   117 0   147 1   118 0   144 1   118 0   144 1   119 0   143 1   119 0   143 1   122 0   142 1   122 0   142 1   124 0   141 1   124 0   141 1   126 0   142 1   126 
                                           0   142 1   128 0   143 1   128 0   143 1   130 0   144 1   130 0   144 1   131 0   147 1   131 0   147 1   131 0   149 1   7   255 109 0   149 1   139 0   149 1   7   255 124 0   134 1   124 0   164 1   7   255 82  0   55  1   82  0   69  1   82  0   69  
                                           1   94  0   72  1   94  0   72  1   154 0   72  1   154 0   72  1   166 0   69  1   166 0   69  1   166 0   55  1   166 0   55  1   154 0   52  1   154 0   52  1   94  0   52  1   94  0   52  1   82  0   55  1   7   255 82  0   229 1   82  0   242 1   82  
                                           0   242 1   94  0   246 1   94  0   246 1   154 0   246 1   154 0   246 1   166 0   242 1   166 0   242 1   166 0   229 1   166 0   229 1   154 0   225 1   154 0   225 1   94  0   225 1   94  0   225 1   82  0   229 1   7   255 238 1   229 1   238 1   242 
                                           1   238 1   242 1   250 1   246 1   250 1   246 1   54  2   246 1   54  2   246 1   66  2   242 1   66  2   242 1   66  2   229 1   66  2   229 1   54  2   225 1   54  2   225 1   250 1   225 1   250 1   225 1   238 1   229 1   7   255 238 1   192 1   238 
                                           1   205 1   238 1   205 1   250 1   208 1   250 1   208 1   54  2   208 1   54  2   208 1   66  2   205 1   66  2   205 1   66  2   192 1   66  2   192 1   54  2   188 1   54  2   188 1   250 1   188 1   250 1   188 1   238 1   192 1   7   255 238 1   93  
                                           1   238 1   106 1   238 1   106 1   250 1   110 1   250 1   110 1   54  2   110 1   54  2   110 1   66  2   106 1   66  2   106 1   66  2   93  1   66  2   93  1   54  2   89  1   54  2   89  1   250 1   89  1   250 1   89  1   238 1   93  1   7   255 238 
                                           )) "a")
 (_WriteStream FILE (vl-list->string (list 1   55  1   238 1   68  1   238 1   68  1   250 1   72  1   250 1   72  1   54  2   72  1   54  2   72  1   66  2   68  1   66  2   68  1   66  2   55  1   66  2   55  1   54  2   52  1   54  2   52  1   250 1   52  1   250 1   52  1   238 1   55  1   7   
                                           255 56  0   52  1   220 0   52  1   220 0   52  1   220 0   110 1   220 0   110 1   114 2   110 1   114 2   110 1   114 2   188 1   114 2   188 1   220 0   188 1   220 0   188 1   220 0   246 1   220 0   246 1   56  0   246 1   56  0   246 1   56  0   52  
                                           1   7   255 56  0   52  1   56  0   52  1   7   255 56  0   52  1   56  0   52  1   7   255 31  2   149 1   31  2   151 1   31  2   151 1   30  2   153 1   30  2   153 1   28  2   155 1   28  2   155 1   26  2   156 1   26  2   156 1   24  2   156 1   24  
                                           2   156 1   21  2   156 1   21  2   156 1   19  2   155 1   19  2   155 1   18  2   153 1   18  2   153 1   17  2   151 1   17  2   151 1   16  2   149 1   16  2   149 1   17  2   147 1   17  2   147 1   18  2   144 1   18  2   144 1   19  2   143 1   19  
                                           2   143 1   21  2   142 1   21  2   142 1   24  2   141 1   24  2   141 1   26  2   142 1   26  2   142 1   28  2   143 1   28  2   143 1   30  2   144 1   30  2   144 1   31  2   147 1   31  2   147 1   31  2   149 1   7   255 9   2   149 1   39  2   149 
                                           1   7   255 24  2   134 1   24  2   164 1   7   255 37  2   149 1   36  2   152 1   36  2   152 1   35  2   154 1   35  2   154 1   34  2   157 1   34  2   157 1   32  2   159 1   32  2   159 1   29  2   161 1   29  2   161 1   27  2   161 1   27  2   161 
                                           1   24  2   162 1   24  2   162 1   21  2   161 1   21  2   161 1   18  2   161 1   18  2   161 1   16  2   159 1   16  2   159 1   14  2   157 1   14  2   157 1   12  2   154 1   12  2   154 1   11  2   152 1   11  2   152 1   11  2   149 1   11  2   149 
                                           1   11  2   146 1   11  2   146 1   12  2   143 1   12  2   143 1   14  2   141 1   14  2   141 1   16  2   139 1   16  2   139 1   18  2   137 1   18  2   137 1   21  2   136 1   21  2   136 1   24  2   136 1   24  2   136 1   27  2   136 1   27  2   136 
                                           1   29  2   137 1   29  2   137 1   32  2   139 1   32  2   139 1   34  2   141 1   34  2   141 1   35  2   143 1   35  2   143 1   36  2   146 1   36  2   146 1   37  2   149 1   7   255 164 1   52  1   240 5   52  1   240 5   52  1   240 5   246 1   7   
                                           255 240 5   246 1   164 1   246 1   7   255 164 1   246 1   164 1   52  1   7   255 164 1   52  1   164 1   52  1   7   255 164 1   52  1   164 1   52  1   7   255 38  5   93  1   38  5   106 1   38  5   106 1   49  5   110 1   49  5   110 1   110 5   110 
                                           1   110 5   110 1   121 5   106 1   121 5   106 1   121 5   93  1   121 5   93  1   110 5   89  1   110 5   89  1   49  5   89  1   49  5   89  1   38  5   93  1   7   255 38  5   55  1   38  5   69  1   38  5   69  1   49  5   72  1   49  5   72  1   110 
                                           5   72  1   110 5   72  1   121 5   69  1   121 5   69  1   121 5   55  1   121 5   55  1   110 5   52  1   110 5   52  1   49  5   52  1   49  5   52  1   38  5   55  1   7   255 38  5   191 1   38  5   205 1   38  5   205 1   49  5   208 1   49  5   208 
                                           1   110 5   208 1   110 5   208 1   121 5   205 1   121 5   205 1   121 5   191 1   121 5   191 1   110 5   188 1   110 5   188 1   49  5   188 1   49  5   188 1   38  5   191 1   7   255 38  5   229 1   38  5   242 1   38  5   242 1   49  5   246 1   49  
                                           5   246 1   110 5   246 1   110 5   246 1   121 5   242 1   121 5   242 1   121 5   229 1   121 5   229 1   110 5   225 1   110 5   225 1   49  5   225 1   49  5   225 1   38  5   229 1   7   255 31  2   149 1   31  2   151 1   31  2   151 1   30  2   153 
                                           1   30  2   153 1   28  2   155 1   28  2   155 1   26  2   156 1   26  2   156 1   24  2   156 1   24  2   156 1   21  2   156 1   21  2   156 1   19  2   155 1   19  2   155 1   18  2   153 1   18  2   153 1   17  2   151 1   17  2   151 1   16  2   149 
                                           1   16  2   149 1   17  2   147 1   17  2   147 1   18  2   144 1   18  2   144 1   19  2   143 1   19  2   143 1   21  2   142 1   21  2   142 1   24  2   141 1   24  2   141 1   26  2   142 1   26  2   142 1   28  2   143 1   28  2   143 1   30  2   144 
                                           1   30  2   144 1   31  2   147 1   31  2   147 1   31  2   149 1   7   255 9   2   149 1   39  2   149 1   7   255 24  2   134 1   24  2   164 1   7   255 171 1   246 1   171 1   248 1   171 1   248 1   170 1   251 1   170 1   251 1   168 1   252 1   168 
                                           1   252 1   166 1   253 1   166 1   253 1   164 1   254 1   164 1   254 1   161 1   253 1   161 1   253 1   159 1   252 1   159 1   252 1   158 1   251 1   158 1   251 1   157 1   248 1   157 1   248 1   156 1   246 1   156 1   246 1   157 1   244 1   157 
                                           1   244 1   158 1   242 1   158 1   242 1   159 1   240 1   159 1   240 1   161 1   239 1   161 1   239 1   164 1   239 1   164 1   239 1   166 1   239 1   166 1   239 1   168 1   240 1   168 1   240 1   170 1   242 1   170 1   242 1   171 1   244 1   171 
                                           1   244 1   171 1   246 1   7   255 149 1   246 1   179 1   246 1   7   255 164 1   231 1   164 1   5   2   7   255 171 1   52  1   171 1   54  1   171 1   54  1   170 1   56  1   170 1   56  1   168 1   58  1   168 1   58  1   166 1   59  1   166 1   59  
                                           1   164 1   59  1   164 1   59  1   161 1   59  1   161 1   59  1   159 1   58  1   159 1   58  1   158 1   56  1   158 1   56  1   157 1   54  1   157 1   54  1   156 1   52  1   156 1   52  1   157 1   49  1   157 1   49  1   158 1   47  1   158 1   47  
                                           1   159 1   45  1   159 1   45  1   161 1   44  1   161 1   44  1   164 1   44  1   164 1   44  1   166 1   44  1   166 1   44  1   168 1   45  1   168 1   45  1   170 1   47  1   170 1   47  1   171 1   49  1   171 1   49  1   171 1   52  1   7   255 149 
                                           1   52  1   179 1   52  1   7   255 164 1   37  1   164 1   67  1   7   255 248 5   52  1   248 5   54  1   248 5   54  1   246 5   56  1   246 5   56  1   245 5   58  1   245 5   58  1   243 5   59  1   243 5   59  1   240 5   59  1   240 5   59  1   238 
                                           5   59  1   238 5   59  1   236 5   58  1   236 5   58  1   234 5   56  1   234 5   56  1   233 5   54  1   233 5   54  1   233 5   52  1   233 5   52  1   233 5   49  1   233 5   49  1   234 5   47  1   234 5   47  1   236 5   45  1   236 5   45  1   238 
                                           5   44  1   238 5   44  1   240 5   44  1   240 5   44  1   243 5   44  1   243 5   44  1   245 5   45  1   245 5   45  1   246 5   47  1   246 5   47  1   248 5   49  1   248 5   49  1   248 5   52  1   7   255 225 5   52  1   255 5   52  1   7   255 240 
                                           5   37  1   240 5   67  1   7   255 248 5   246 1   248 5   248 1   248 5   248 1   246 5   251 1   246 5   251 1   245 5   252 1   245 5   252 1   243 5   253 1   243 5   253 1   240 5   254 1   240 5   254 1   238 5   253 1   238 5   253 1   236 5   252 
                                           1   236 5   252 1   234 5   251 1   234 5   251 1   233 5   248 1   233 5   248 1   233 5   246 1   233 5   246 1   233 5   244 1   233 5   244 1   234 5   242 1   234 5   242 1   236 5   240 1   236 5   240 1   238 5   239 1   238 5   239 1   240 5   239 
                                           1   240 5   239 1   243 5   239 1   243 5   239 1   245 5   240 1   245 5   240 1   246 5   242 1   246 5   242 1   248 5   244 1   248 5   244 1   248 5   246 1   7   255 225 5   246 1   255 5   246 1   7   255 240 5   231 1   240 5   5   2   7   255 87  
                                           5   246 1   87  5   248 1   87  5   248 1   85  5   251 1   85  5   251 1   84  5   252 1   84  5   252 1   82  5   253 1   82  5   253 1   79  5   254 1   79  5   254 1   77  5   253 1   77  5   253 1   75  5   252 1   75  5   252 1   73  5   251 1   73  
                                           5   251 1   72  5   248 1   72  5   248 1   72  5   246 1   72  5   246 1   72  5   244 1   72  5   244 1   73  5   242 1   73  5   242 1   75  5   240 1   75  5   240 1   77  5   239 1   77  5   239 1   79  5   239 1   79  5   239 1   82  5   239 1   82  
                                           5   239 1   84  5   240 1   84  5   240 1   85  5   242 1   85  5   242 1   87  5   244 1   87  5   244 1   87  5   246 1   7   255 64  5   246 1   94  5   246 1   7   255 79  5   231 1   79  5   5   2   7   255 87  5   52  1   87  5   54  1   87  5   54  
                                           1   85  5   56  1   85  5   56  1   84  5   58  1   84  5   58  1   82  5   59  1   82  5   59  1   79  5   59  1   79  5   59  1   77  5   59  1   77  5   59  1   75  5   58  1   75  5   58  1   73  5   56  1   73  5   56  1   72  5   54  1   72  5   54  
                                           1   72  5   52  1   72  5   52  1   72  5   49  1   72  5   49  1   73  5   47  1   73  5   47  1   75  5   45  1   75  5   45  1   77  5   44  1   77  5   44  1   79  5   44  1   79  5   44  1   82  5   44  1   82  5   44  1   84  5   45  1   84  5   45  
                                           1   85  5   47  1   85  5   47  1   87  5   49  1   87  5   49  1   87  5   52  1   7   255 64  5   52  1   94  5   52  1   7   255 79  5   37  1   79  5   67  1   0   252 65  117 116 111 67  65  68  32  83  108 105 100 101 13  10  26  0   86  2   106 6   
                                           234 2   99  219 79  1   2   0   52  18  7   255 7   255 38  0   22  1   8   1   22  1   8   1   22  1   8   1   81  1   8   1   81  1   101 2   81  1   101 2   81  1   101 2   159 1   101 2   159 1   8   1   159 1   8   1   159 1   8   1   217 1   8   1   
                                           217 1   38  0   217 1   38  0   217 1   38  0   22  1   7   255 38  0   22  1   38  0   22  1   7   255 38  0   22  1   38  0   22  1   7   255 73  2   139 1   68  2   143 1   68  2   143 1   62  2   146 1   62  2   146 1   56  2   147 1   56  2   147 1   
                                           50  2   147 1   50  2   147 1   44  2   146 1   44  2   146 1   38  2   143 1   38  2   143 1   33  2   139 1   33  2   139 1   29  2   135 1   29  2   135 1   27  2   129 1   27  2   129 1   25  2   123 1   25  2   123 1   25  2   117 1   25  2   117 1   
                                           27  2   110 1   27  2   110 1   29  2   105 1   29  2   105 1   33  2   100 1   33  2   100 1   38  2   96  1   38  2   96  1   44  2   93  1   44  2   93  1   50  2   92  1   50  2   92  1   56  2   92  1   56  2   92  1   62  2   93  1   62  2   93  1   
                                           68  2   96  1   68  2   96  1   73  2   100 1   7   255 73  2   100 1   73  2   139 1   7   255 219 1   64  1   219 1   77  1   219 1   77  1   231 1   81  1   231 1   81  1   35  2   81  1   35  2   81  1   47  2   77  1   47  2   77  1   47  2   64  1   
                                           47  2   64  1   35  2   60  1   35  2   60  1   231 1   60  1   231 1   60  1   219 1   64  1   7   255 219 1   26  1   219 1   39  1   219 1   39  1   231 1   43  1   231 1   43  1   35  2   43  1   35  2   43  1   47  2   39  1   47  2   39  1   47  2   
                                           26  1   47  2   26  1   35  2   22  1   35  2   22  1   231 1   22  1   231 1   22  1   219 1   26  1   7   255 219 1   163 1   219 1   176 1   219 1   176 1   231 1   180 1   231 1   180 1   35  2   180 1   35  2   180 1   47  2   176 1   47  2   176 1   
                                           47  2   163 1   47  2   163 1   35  2   159 1   35  2   159 1   231 1   159 1   231 1   159 1   219 1   163 1   7   255 219 1   200 1   219 1   214 1   219 1   214 1   231 1   217 1   231 1   217 1   35  2   217 1   35  2   217 1   47  2   214 1   47  2   
                                           214 1   47  2   200 1   47  2   200 1   35  2   196 1   35  2   196 1   231 1   196 1   231 1   196 1   219 1   200 1   7   255 59  2   64  1   59  2   77  1   59  2   77  1   71  2   81  1   71  2   81  1   131 2   81  1   131 2   81  1   143 2   77  1   
                                           143 2   77  1   143 2   64  1   143 2   64  1   131 2   60  1   131 2   60  1   71  2   60  1   71  2   60  1   59  2   64  1   7   255 59  2   26  1   59  2   39  1   59  2   39  1   71  2   43  1   71  2   43  1   131 2   43  1   131 2   43  1   143 2   
                                           39  1   143 2   39  1   143 2   26  1   143 2   26  1   131 2   22  1   131 2   22  1   71  2   22  1   71  2   22  1   59  2   26  1   7   255 59  2   163 1   59  2   176 1   59  2   176 1   71  2   180 1   71  2   180 1   131 2   180 1   131 2   180 1   
                                           143 2   176 1   143 2   176 1   143 2   163 1   143 2   163 1   131 2   159 1   131 2   159 1   71  2   159 1   71  2   159 1   59  2   163 1   7   255 59  2   200 1   59  2   214 1   59  2   214 1   71  2   217 1   71  2   217 1   131 2   217 1   131 2   
                                           217 1   143 2   214 1   143 2   214 1   143 2   200 1   143 2   200 1   131 2   196 1   131 2   196 1   71  2   196 1   71  2   196 1   59  2   200 1   7   255 61  2   120 1   60  2   123 1   60  2   123 1   58  2   125 1   58  2   125 1   56  2   127 1   
                                           56  2   127 1   53  2   127 1   53  2   127 1   50  2   127 1   50  2   127 1   48  2   125 1   48  2   125 1   46  2   123 1   46  2   123 1   45  2   120 1   45  2   120 1   46  2   117 1   46  2   117 1   48  2   114 1   48  2   114 1   50  2   113 1   
                                           50  2   113 1   53  2   112 1   53  2   112 1   56  2   113 1   56  2   113 1   58  2   114 1   58  2   114 1   60  2   117 1   60  2   117 1   61  2   120 1   7   255 38  2   120 1   68  2   120 1   7   255 53  2   105 1   53  2   135 1   7   255 106 0   
                                           22  1   105 0   25  1   105 0   25  1   103 0   27  1   103 0   27  1   101 0   29  1   101 0   29  1   98  0   29  1   98  0   29  1   95  0   29  1   95  0   29  1   93  0   27  1   93  0   27  1   91  0   25  1   91  0   25  1   91  0   22  1   91  0   
                                           22  1   91  0   19  1   91  0   19  1   93  0   17  1   93  0   17  1   95  0   15  1   95  0   15  1   98  0   14  1   98  0   14  1   101 0   15  1   101 0   15  1   103 0   17  1   103 0   17  1   105 0   19  1   105 0   19  1   106 0   22  1   7   255 
                                           83  0   22  1   113 0   22  1   7   255 98  0   7   1   98  0   37  1   7   255 45  0   22  1   45  0   25  1   45  0   25  1   43  0   27  1   43  0   27  1   41  0   29  1   41  0   29  1   38  0   29  1   38  0   29  1   35  0   29  1   35  0   29  1   
                                           33  0   27  1   33  0   27  1   31  0   25  1   31  0   25  1   30  0   22  1   30  0   22  1   31  0   19  1   31  0   19  1   33  0   17  1   33  0   17  1   35  0   15  1   35  0   15  1   38  0   14  1   38  0   14  1   41  0   15  1   41  0   15  1   
                                           43  0   17  1   43  0   17  1   45  0   19  1   45  0   19  1   45  0   22  1   7   255 23  0   22  1   53  0   22  1   7   255 38  0   7   1   38  0   37  1   7   255 106 0   217 1   105 0   220 1   105 0   220 1   103 0   223 1   103 0   223 1   101 0   
                                           224 1   101 0   224 1   98  0   225 1   98  0   225 1   95  0   224 1   95  0   224 1   93  0   223 1   93  0   223 1   91  0   220 1   91  0   220 1   91  0   217 1   91  0   217 1   91  0   215 1   91  0   215 1   93  0   212 1   93  0   212 1   95  0   
                                           211 1   95  0   211 1   98  0   210 1   98  0   210 1   101 0   211 1   101 0   211 1   103 0   212 1   103 0   212 1   105 0   215 1   105 0   215 1   106 0   217 1   7   255 83  0   217 1   113 0   217 1   7   255 98  0   202 1   98  0   233 1   7   255 
                                           45  0   217 1   45  0   220 1   45  0   220 1   43  0   223 1   43  0   223 1   41  0   224 1   41  0   224 1   38  0   225 1   38  0   225 1   35  0   224 1   35  0   224 1   33  0   223 1   33  0   223 1   31  0   220 1   31  0   220 1   30  0   217 1   
                                           30  0   217 1   31  0   215 1   31  0   215 1   33  0   212 1   33  0   212 1   35  0   211 1   35  0   211 1   38  0   210 1   38  0   210 1   41  0   211 1   41  0   211 1   43  0   212 1   43  0   212 1   45  0   215 1   45  0   215 1   45  0   217 1   
                                           7   255 23  0   217 1   53  0   217 1   7   255 38  0   202 1   38  0   233 1   7   255 61  2   217 1   60  2   220 1   60  2   220 1   58  2   223 1   58  2   223 1   56  2   224 1   56  2   224 1   53  2   225 1   53  2   225 1   50  2   224 1   50  2   
                                           224 1   48  2   223 1   48  2   223 1   46  2   220 1   46  2   220 1   45  2   217 1   45  2   217 1   46  2   215 1   46  2   215 1   48  2   212 1   48  2   212 1   50  2   211 1   50  2   211 1   53  2   210 1   53  2   210 1   56  2   211 1   56  2   
                                           211 1   58  2   212 1   58  2   212 1   60  2   215 1   60  2   215 1   61  2   217 1   7   255 38  2   217 1   68  2   217 1   7   255 53  2   202 1   53  2   233 1   7   255 61  2   22  1   60  2   25  1   60  2   25  1   58  2   27  1   58  2   27  1   
                                           56  2   29  1   56  2   29  1   53  2   29  1   53  2   29  1   50  2   29  1   50  2   29  1   48  2   27  1   48  2   27  1   46  2   25  1   46  2   25  1   45  2   22  1   45  2   22  1   46  2   19  1   46  2   19  1   48  2   17  1   48  2   17  1   
                                           50  2   15  1   50  2   15  1   53  2   14  1   53  2   14  1   56  2   15  1   56  2   15  1   58  2   17  1   58  2   17  1   60  2   19  1   60  2   19  1   61  2   22  1   7   255 38  2   22  1   68  2   22  1   7   255 53  2   7   1   53  2   37  1   
                                           7   255 106 0   120 1   105 0   123 1   105 0   123 1   103 0   125 1   103 0   125 1   101 0   127 1   101 0   127 1   98  0   127 1   98  0   127 1   95  0   127 1   95  0   127 1   93  0   125 1   93  0   125 1   91  0   123 1   91  0   123 1   91  0   
                                           )) "a")
 (_WriteStream FILE (vl-list->string (list 120 1   91  0   120 1   91  0   117 1   91  0   117 1   93  0   114 1   93  0   114 1   95  0   113 1   95  0   113 1   98  0   112 1   98  0   112 1   101 0   113 1   101 0   113 1   103 0   114 1   103 0   114 1   105 0   117 1   105 0   117 1   106 0   
                                           120 1   7   255 83  0   120 1   113 0   120 1   7   255 98  0   105 1   98  0   135 1   7   255 56  0   200 1   56  0   214 1   56  0   214 1   68  0   217 1   68  0   217 1   128 0   217 1   128 0   217 1   140 0   214 1   140 0   214 1   140 0   200 1   
                                           140 0   200 1   128 0   196 1   128 0   196 1   68  0   196 1   68  0   196 1   56  0   200 1   7   255 56  0   26  1   56  0   39  1   56  0   39  1   68  0   43  1   68  0   43  1   128 0   43  1   128 0   43  1   140 0   39  1   140 0   39  1   140 0   
                                           26  1   140 0   26  1   128 0   22  1   128 0   22  1   68  0   22  1   68  0   22  1   56  0   26  1   7   255 211 1   22  1   61  6   22  1   61  6   22  1   61  6   217 1   61  6   217 1   211 1   217 1   211 1   217 1   211 1   22  1   7   255 211 1   
                                           22  1   211 1   22  1   7   255 211 1   22  1   211 1   22  1   7   255 61  2   120 1   60  2   123 1   60  2   123 1   59  2   125 1   59  2   125 1   56  2   127 1   56  2   127 1   53  2   127 1   53  2   127 1   50  2   127 1   50  2   127 1   47  2   
                                           125 1   47  2   125 1   46  2   123 1   46  2   123 1   45  2   120 1   45  2   120 1   46  2   117 1   46  2   117 1   47  2   114 1   47  2   114 1   50  2   112 1   50  2   112 1   53  2   112 1   53  2   112 1   56  2   112 1   56  2   112 1   59  2   
                                           114 1   59  2   114 1   60  2   117 1   60  2   117 1   61  2   120 1   7   255 99  5   64  1   99  5   77  1   99  5   77  1   110 5   81  1   110 5   81  1   171 5   81  1   171 5   81  1   183 5   77  1   183 5   77  1   183 5   64  1   183 5   64  1   
                                           171 5   60  1   171 5   60  1   110 5   60  1   110 5   60  1   99  5   64  1   7   255 99  5   26  1   99  5   39  1   99  5   39  1   110 5   43  1   110 5   43  1   171 5   43  1   171 5   43  1   183 5   39  1   183 5   39  1   183 5   26  1   183 5   
                                           26  1   171 5   22  1   171 5   22  1   110 5   22  1   110 5   22  1   99  5   26  1   7   255 99  5   163 1   99  5   176 1   99  5   176 1   110 5   180 1   110 5   180 1   171 5   180 1   171 5   180 1   183 5   176 1   183 5   176 1   183 5   163 1   
                                           183 5   163 1   171 5   159 1   171 5   159 1   110 5   159 1   110 5   159 1   99  5   163 1   7   255 99  5   200 1   99  5   214 1   99  5   214 1   110 5   217 1   110 5   217 1   171 5   217 1   171 5   217 1   183 5   214 1   183 5   214 1   183 5   
                                           200 1   183 5   200 1   171 5   196 1   171 5   196 1   110 5   196 1   110 5   196 1   99  5   200 1   7   255 194 5   64  1   194 5   77  1   194 5   77  1   206 5   81  1   206 5   81  1   11  6   81  1   11  6   81  1   22  6   77  1   22  6   77  1   
                                           22  6   64  1   22  6   64  1   11  6   60  1   11  6   60  1   206 5   60  1   206 5   60  1   194 5   64  1   7   255 194 5   26  1   194 5   39  1   194 5   39  1   206 5   43  1   206 5   43  1   11  6   43  1   11  6   43  1   22  6   39  1   22  6   
                                           39  1   22  6   26  1   22  6   26  1   11  6   22  1   11  6   22  1   206 5   22  1   206 5   22  1   194 5   26  1   7   255 194 5   163 1   194 5   176 1   194 5   176 1   206 5   180 1   206 5   180 1   11  6   180 1   11  6   180 1   22  6   176 1   
                                           22  6   176 1   22  6   163 1   22  6   163 1   11  6   159 1   11  6   159 1   206 5   159 1   206 5   159 1   194 5   163 1   7   255 194 5   200 1   194 5   214 1   194 5   214 1   206 5   217 1   206 5   217 1   11  6   217 1   11  6   217 1   22  6   
                                           214 1   22  6   214 1   22  6   200 1   22  6   200 1   11  6   196 1   11  6   196 1   206 5   196 1   206 5   196 1   194 5   200 1   7   255 61  2   120 1   60  2   123 1   60  2   123 1   58  2   125 1   58  2   125 1   56  2   127 1   56  2   127 1   
                                           53  2   127 1   53  2   127 1   50  2   127 1   50  2   127 1   48  2   125 1   48  2   125 1   46  2   123 1   46  2   123 1   45  2   120 1   45  2   120 1   46  2   117 1   46  2   117 1   48  2   114 1   48  2   114 1   50  2   113 1   50  2   113 1   
                                           53  2   112 1   53  2   112 1   56  2   113 1   56  2   113 1   58  2   114 1   58  2   114 1   60  2   117 1   60  2   117 1   61  2   120 1   7   255 38  2   120 1   68  2   120 1   7   255 53  2   105 1   53  2   135 1   7   255 219 1   22  1   218 1   
                                           25  1   218 1   25  1   216 1   27  1   216 1   27  1   214 1   29  1   214 1   29  1   211 1   29  1   211 1   29  1   208 1   29  1   208 1   29  1   206 1   27  1   206 1   27  1   204 1   25  1   204 1   25  1   204 1   22  1   204 1   22  1   204 1   
                                           19  1   204 1   19  1   206 1   17  1   206 1   17  1   208 1   15  1   208 1   15  1   211 1   14  1   211 1   14  1   214 1   15  1   214 1   15  1   216 1   17  1   216 1   17  1   218 1   19  1   218 1   19  1   219 1   22  1   7   255 196 1   22  1   
                                           226 1   22  1   7   255 211 1   7   1   211 1   37  1   7   255 219 1   217 1   218 1   220 1   218 1   220 1   216 1   223 1   216 1   223 1   214 1   224 1   214 1   224 1   211 1   225 1   211 1   225 1   208 1   224 1   208 1   224 1   206 1   223 1   
                                           206 1   223 1   204 1   220 1   204 1   220 1   204 1   217 1   204 1   217 1   204 1   215 1   204 1   215 1   206 1   212 1   206 1   212 1   208 1   211 1   208 1   211 1   211 1   210 1   211 1   210 1   214 1   211 1   214 1   211 1   216 1   212 1   
                                           216 1   212 1   218 1   215 1   218 1   215 1   219 1   217 1   7   255 196 1   217 1   226 1   217 1   7   255 211 1   202 1   211 1   233 1   7   255 68  6   217 1   68  6   220 1   68  6   220 1   66  6   223 1   66  6   223 1   63  6   224 1   63  6   
                                           224 1   61  6   225 1   61  6   225 1   58  6   224 1   58  6   224 1   55  6   223 1   55  6   223 1   54  6   220 1   54  6   220 1   53  6   217 1   53  6   217 1   54  6   215 1   54  6   215 1   55  6   212 1   55  6   212 1   58  6   211 1   58  6   
                                           211 1   61  6   210 1   61  6   210 1   63  6   211 1   63  6   211 1   66  6   212 1   66  6   212 1   68  6   215 1   68  6   215 1   68  6   217 1   7   255 46  6   217 1   76  6   217 1   7   255 61  6   202 1   61  6   233 1   7   255 68  6   22  1   
                                           68  6   25  1   68  6   25  1   66  6   27  1   66  6   27  1   63  6   29  1   63  6   29  1   61  6   29  1   61  6   29  1   58  6   29  1   58  6   29  1   55  6   27  1   55  6   27  1   54  6   25  1   54  6   25  1   53  6   22  1   53  6   22  1   
                                           54  6   19  1   54  6   19  1   55  6   17  1   55  6   17  1   58  6   15  1   58  6   15  1   61  6   14  1   61  6   14  1   63  6   15  1   63  6   15  1   66  6   17  1   66  6   17  1   68  6   19  1   68  6   19  1   68  6   22  1   7   255 46  6   
                                           22  1   76  6   22  1   7   255 61  6   7   1   61  6   37  1   7   255 196 5   217 1   196 5   220 1   196 5   220 1   194 5   223 1   194 5   223 1   191 5   224 1   191 5   224 1   189 5   225 1   189 5   225 1   186 5   224 1   186 5   224 1   183 5   
                                           223 1   183 5   223 1   182 5   220 1   182 5   220 1   181 5   217 1   181 5   217 1   182 5   215 1   182 5   215 1   183 5   212 1   183 5   212 1   186 5   211 1   186 5   211 1   189 5   210 1   189 5   210 1   191 5   211 1   191 5   211 1   194 5   
                                           212 1   194 5   212 1   196 5   215 1   196 5   215 1   196 5   217 1   7   255 174 5   217 1   204 5   217 1   7   255 189 5   202 1   189 5   233 1   7   255 196 5   22  1   196 5   25  1   196 5   25  1   194 5   27  1   194 5   27  1   191 5   29  1   
                                           191 5   29  1   189 5   29  1   189 5   29  1   186 5   29  1   186 5   29  1   183 5   27  1   183 5   27  1   182 5   25  1   182 5   25  1   181 5   22  1   181 5   22  1   182 5   19  1   182 5   19  1   183 5   17  1   183 5   17  1   186 5   15  1   
                                           186 5   15  1   189 5   14  1   189 5   14  1   191 5   15  1   191 5   15  1   194 5   17  1   194 5   17  1   196 5   19  1   196 5   19  1   196 5   22  1   7   255 174 5   22  1   204 5   22  1   7   255 189 5   7   1   189 5   37  1   0   252 65  117 
                                           116 111 67  65  68  32  83  108 105 100 101 13  10  26  0   86  2   73  6   247 2   97  120 67  1   2   0   52  18  7   255 7   255 93  0   241 0   220 5   241 0   220 5   241 0   220 5   14  2   220 5   14  2   93  0   14  2   93  0   14  2   93  0   241 
                                           0   7   255 93  0   241 0   93  0   241 0   7   255 93  0   241 0   93  0   241 0   7   255 93  0   241 0   93  0   241 0   7   255 220 3   44  1   220 3   63  1   220 3   63  1   237 3   68  1   237 3   68  1   67  4   68  1   67  4   68  1   83  4   63  
                                           1   83  4   63  1   83  4   44  1   83  4   44  1   67  4   39  1   67  4   39  1   237 3   39  1   237 3   39  1   220 3   44  1   7   255 220 3   247 0   220 3   9   1   220 3   9   1   237 3   15  1   237 3   15  1   67  4   15  1   67  4   15  1   83  
                                           4   9   1   83  4   9   1   83  4   247 0   83  4   247 0   67  4   241 0   67  4   241 0   237 3   241 0   237 3   241 0   220 3   247 0   7   255 220 3   193 1   220 3   211 1   220 3   211 1   237 3   217 1   237 3   217 1   67  4   217 1   67  4   217 
                                           1   83  4   211 1   83  4   211 1   83  4   193 1   83  4   193 1   67  4   187 1   67  4   187 1   237 3   187 1   237 3   187 1   220 3   193 1   7   255 220 3   246 1   220 3   9   2   220 3   9   2   237 3   14  2   237 3   14  2   67  4   14  2   67  
                                           4   14  2   83  4   9   2   83  4   9   2   83  4   246 1   83  4   246 1   67  4   240 1   67  4   240 1   237 3   240 1   237 3   240 1   220 3   246 1   7   255 121 4   44  1   121 4   63  1   121 4   63  1   138 4   68  1   138 4   68  1   223 4   68  
                                           1   223 4   68  1   240 4   63  1   240 4   63  1   240 4   44  1   240 4   44  1   223 4   39  1   223 4   39  1   138 4   39  1   138 4   39  1   121 4   44  1   7   255 121 4   247 0   121 4   9   1   121 4   9   1   138 4   15  1   138 4   15  1   223 
                                           4   15  1   223 4   15  1   240 4   9   1   240 4   9   1   240 4   247 0   240 4   247 0   223 4   241 0   223 4   241 0   138 4   241 0   138 4   241 0   121 4   247 0   7   255 121 4   193 1   121 4   211 1   121 4   211 1   138 4   217 1   138 4   217 
                                           1   223 4   217 1   223 4   217 1   240 4   211 1   240 4   211 1   240 4   193 1   240 4   193 1   223 4   187 1   223 4   187 1   138 4   187 1   138 4   187 1   121 4   193 1   7   255 121 4   246 1   121 4   9   2   121 4   9   2   138 4   14  2   138 
                                           4   14  2   223 4   14  2   223 4   14  2   240 4   9   2   240 4   9   2   240 4   246 1   240 4   246 1   223 4   240 1   223 4   240 1   138 4   240 1   138 4   240 1   121 4   246 1   7   255 96  0   241 0   95  0   244 0   95  0   244 0   93  0   245 
                                           0   93  0   245 0   90  0   244 0   90  0   244 0   89  0   241 0   89  0   241 0   90  0   239 0   90  0   239 0   93  0   238 0   93  0   238 0   95  0   239 0   95  0   239 0   96  0   241 0   7   255 86  0   241 0   100 0   241 0   7   255 93  0   234 
                                           0   93  0   248 0   7   255 96  0   14  2   95  0   17  2   95  0   17  2   93  0   18  2   93  0   18  2   90  0   17  2   90  0   17  2   89  0   14  2   89  0   14  2   90  0   12  2   90  0   12  2   93  0   11  2   93  0   11  2   95  0   12  2   95  
                                           0   12  2   96  0   14  2   7   255 86  0   14  2   100 0   14  2   7   255 93  0   7   2   93  0   21  2   7   255 239 0   14  2   238 0   17  2   238 0   17  2   235 0   18  2   235 0   18  2   233 0   17  2   233 0   17  2   232 0   14  2   232 0   14  
                                           2   233 0   12  2   233 0   12  2   235 0   11  2   235 0   11  2   238 0   12  2   238 0   12  2   239 0   14  2   7   255 228 0   14  2   242 0   14  2   7   255 235 0   7   2   235 0   21  2   7   255 106 4   14  2   105 4   17  2   105 4   17  2   102 
                                           4   18  2   102 4   18  2   100 4   17  2   100 4   17  2   99  4   14  2   99  4   14  2   100 4   12  2   100 4   12  2   102 4   11  2   102 4   11  2   105 4   12  2   105 4   12  2   106 4   14  2   7   255 95  4   14  2   109 4   14  2   7   255 102 
                                           4   7   2   102 4   21  2   7   255 224 5   14  2   223 5   17  2   223 5   17  2   220 5   18  2   220 5   18  2   218 5   17  2   218 5   17  2   217 5   14  2   217 5   14  2   218 5   12  2   218 5   12  2   220 5   11  2   220 5   11  2   223 5   12  
                                           2   223 5   12  2   224 5   14  2   7   255 213 5   14  2   228 5   14  2   7   255 220 5   7   2   220 5   21  2   7   255 224 5   241 0   223 5   244 0   223 5   244 0   220 5   245 0   220 5   245 0   218 5   244 0   218 5   244 0   217 5   241 0   217 
                                           5   241 0   218 5   239 0   218 5   239 0   220 5   238 0   220 5   238 0   223 5   239 0   223 5   239 0   224 5   241 0   7   255 213 5   241 0   228 5   241 0   7   255 220 5   234 0   220 5   248 0   7   255 106 4   241 0   105 4   244 0   105 4   244 
                                           0   102 4   245 0   102 4   245 0   100 4   244 0   100 4   244 0   99  4   241 0   99  4   241 0   100 4   239 0   100 4   239 0   102 4   238 0   102 4   238 0   105 4   239 0   105 4   239 0   106 4   241 0   7   255 95  4   241 0   109 4   241 0   7   
                                           255 102 4   234 0   102 4   248 0   7   255 239 0   241 0   238 0   244 0   238 0   244 0   235 0   245 0   235 0   245 0   233 0   244 0   233 0   244 0   232 0   241 0   232 0   241 0   233 0   239 0   233 0   239 0   235 0   238 0   235 0   238 0   238 
                                           0   239 0   238 0   239 0   239 0   241 0   7   255 228 0   241 0   242 0   241 0   7   255 235 0   234 0   235 0   248 0   7   255 239 0   128 1   238 0   130 1   238 0   130 1   235 0   131 1   235 0   131 1   233 0   130 1   233 0   130 1   232 0   128 
                                           1   232 0   128 1   233 0   125 1   233 0   125 1   235 0   124 1   235 0   124 1   238 0   125 1   238 0   125 1   239 0   128 1   7   255 228 0   128 1   242 0   128 1   7   255 235 0   121 1   235 0   135 1   51  255 51  255 93  0   241 0   220 5   241 
                                           0   220 5   241 0   220 5   14  2   220 5   14  2   93  0   14  2   93  0   14  2   93  0   241 0   7   255 7   255 176 0   246 1   176 0   9   2   176 0   9   2   193 0   14  2   193 0   14  2   22  1   14  2   22  1   14  2   39  1   9   2   39  1   9   
                                           2   39  1   246 1   39  1   246 1   22  1   240 1   22  1   240 1   193 0   240 1   193 0   240 1   176 0   246 1   7   255 176 0   247 0   176 0   9   1   176 0   9   1   193 0   15  1   193 0   15  1   22  1   15  1   22  1   15  1   39  1   9   1   39  
                                           1   9   1   39  1   247 0   39  1   247 0   22  1   241 0   22  1   241 0   193 0   241 0   193 0   241 0   176 0   247 0   0   252 65  117 116 111 67  65  68  32  83  108 105 100 101 13  10  26  0   86  2   106 6   234 2   99  219 79  1   2   0   52  18  
                                           7   255 7   255 109 0   212 0   253 5   212 0   253 5   212 0   253 5   22  2   253 5   22  2   109 0   22  2   109 0   22  2   109 0   212 0   7   255 109 0   212 0   109 0   212 0   7   255 109 0   212 0   109 0   212 0   7   255 82  4   18  1   82  4   
                                           38  1   82  4   38  1   100 4   44  1   100 4   44  1   191 4   44  1   191 4   44  1   208 4   38  1   208 4   38  1   208 4   18  1   208 4   18  1   191 4   13  1   191 4   13  1   100 4   13  1   100 4   13  1   82  4   18  1   7   255 82  4   218 0   
                                           82  4   237 0   82  4   237 0   100 4   243 0   100 4   243 0   191 4   243 0   191 4   243 0   208 4   237 0   208 4   237 0   208 4   218 0   208 4   218 0   191 4   212 0   191 4   212 0   100 4   212 0   100 4   212 0   82  4   218 0   7   255 82  4   
                                           196 1   82  4   215 1   82  4   215 1   100 4   221 1   100 4   221 1   191 4   221 1   191 4   221 1   208 4   215 1   208 4   215 1   208 4   196 1   208 4   196 1   191 4   190 1   191 4   190 1   100 4   190 1   100 4   190 1   82  4   196 1   7   255 
                                           82  4   252 1   82  4   16  2   82  4   16  2   100 4   22  2   100 4   22  2   191 4   22  2   191 4   22  2   208 4   16  2   208 4   16  2   208 4   252 1   208 4   252 1   191 4   246 1   191 4   246 1   100 4   246 1   100 4   246 1   82  4   252 1   
                                           7   255 240 4   18  1   240 4   38  1   240 4   38  1   1   5   44  1   1   5   44  1   92  5   44  1   92  5   44  1   109 5   38  1   109 5   38  1   109 5   18  1   109 5   18  1   92  5   13  1   92  5   13  1   1   5   13  1   1   5   13  1   240 4   
                                           18  1   7   255 240 4   218 0   240 4   237 0   240 4   237 0   1   5   243 0   1   5   243 0   92  5   243 0   92  5   243 0   109 5   237 0   109 5   237 0   109 5   218 0   109 5   218 0   92  5   212 0   92  5   212 0   1   5   212 0   1   5   212 0   
                                           240 4   218 0   7   255 240 4   196 1   240 4   215 1   240 4   215 1   1   5   221 1   1   5   221 1   92  5   221 1   92  5   221 1   109 5   215 1   109 5   215 1   109 5   196 1   109 5   196 1   92  5   190 1   92  5   190 1   1   5   190 1   1   5   
                                           )) "a")
 (_WriteStream FILE (vl-list->string (list 190 1   240 4   196 1   7   255 240 4   252 1   240 4   16  2   240 4   16  2   1   5   22  2   1   5   22  2   92  5   22  2   92  5   22  2   109 5   16  2   109 5   16  2   109 5   252 1   109 5   252 1   92  5   246 1   92  5   246 1   1   5   246 1   
                                           1   5   246 1   240 4   252 1   7   255 121 0   212 0   120 0   218 0   120 0   218 0   115 0   223 0   115 0   223 0   109 0   224 0   109 0   224 0   103 0   223 0   103 0   223 0   98  0   218 0   98  0   218 0   96  0   212 0   96  0   212 0   98  0   
                                           206 0   98  0   206 0   103 0   201 0   103 0   201 0   109 0   200 0   109 0   200 0   115 0   201 0   115 0   201 0   120 0   206 0   120 0   206 0   121 0   212 0   7   255 84  0   212 0   134 0   212 0   7   255 109 0   187 0   109 0   237 0   7   255 
                                           121 0   22  2   120 0   28  2   120 0   28  2   115 0   32  2   115 0   32  2   109 0   34  2   109 0   34  2   103 0   32  2   103 0   32  2   98  0   28  2   98  0   28  2   96  0   22  2   96  0   22  2   98  0   15  2   98  0   15  2   103 0   11  2   
                                           103 0   11  2   109 0   9   2   109 0   9   2   115 0   11  2   115 0   11  2   120 0   15  2   120 0   15  2   121 0   22  2   7   255 84  0   22  2   134 0   22  2   7   255 109 0   253 1   109 0   46  2   7   255 9   6   22  2   7   6   28  2   7   6   
                                           28  2   3   6   32  2   3   6   32  2   253 5   34  2   253 5   34  2   246 5   32  2   246 5   32  2   242 5   28  2   242 5   28  2   240 5   22  2   240 5   22  2   242 5   15  2   242 5   15  2   246 5   11  2   246 5   11  2   253 5   9   2   253 5   
                                           9   2   3   6   11  2   3   6   11  2   7   6   15  2   7   6   15  2   9   6   22  2   7   255 228 5   22  2   21  6   22  2   7   255 253 5   253 1   253 5   46  2   7   255 9   6   212 0   7   6   218 0   7   6   218 0   3   6   223 0   3   6   223 0   
                                           253 5   224 0   253 5   224 0   246 5   223 0   246 5   223 0   242 5   218 0   242 5   218 0   240 5   212 0   240 5   212 0   242 5   206 0   242 5   206 0   246 5   201 0   246 5   201 0   253 5   200 0   253 5   200 0   3   6   201 0   3   6   201 0   
                                           7   6   206 0   7   6   206 0   9   6   212 0   7   255 228 5   212 0   21  6   212 0   7   255 253 5   187 0   253 5   237 0   7   255 220 0   212 0   219 0   218 0   219 0   218 0   214 0   223 0   214 0   223 0   208 0   224 0   208 0   224 0   202 0   
                                           223 0   202 0   223 0   197 0   218 0   197 0   218 0   196 0   212 0   196 0   212 0   197 0   206 0   197 0   206 0   202 0   201 0   202 0   201 0   208 0   200 0   208 0   200 0   214 0   201 0   214 0   201 0   219 0   206 0   219 0   206 0   220 0   
                                           212 0   7   255 183 0   212 0   233 0   212 0   7   255 208 0   187 0   208 0   237 0   7   255 220 0   22  2   219 0   28  2   219 0   28  2   214 0   32  2   214 0   32  2   208 0   34  2   208 0   34  2   202 0   32  2   202 0   32  2   197 0   28  2   
                                           197 0   28  2   196 0   22  2   196 0   22  2   197 0   15  2   197 0   15  2   202 0   11  2   202 0   11  2   208 0   9   2   208 0   9   2   214 0   11  2   214 0   11  2   219 0   15  2   219 0   15  2   220 0   22  2   7   255 183 0   22  2   233 0   
                                           22  2   7   255 208 0   253 1   208 0   46  2   7   255 220 0   117 1   219 0   123 1   219 0   123 1   214 0   128 1   214 0   128 1   208 0   129 1   208 0   129 1   202 0   128 1   202 0   128 1   197 0   123 1   197 0   123 1   196 0   117 1   196 0   
                                           117 1   197 0   111 1   197 0   111 1   202 0   106 1   202 0   106 1   208 0   104 1   208 0   104 1   214 0   106 1   214 0   106 1   219 0   111 1   219 0   111 1   220 0   117 1   7   255 183 0   117 1   233 0   117 1   7   255 208 0   92  1   208 0   
                                           142 1   7   255 236 4   22  2   235 4   28  2   235 4   28  2   230 4   32  2   230 4   32  2   224 4   34  2   224 4   34  2   218 4   32  2   218 4   32  2   213 4   28  2   213 4   28  2   211 4   22  2   211 4   22  2   213 4   15  2   213 4   15  2   
                                           218 4   11  2   218 4   11  2   224 4   9   2   224 4   9   2   230 4   11  2   230 4   11  2   235 4   15  2   235 4   15  2   236 4   22  2   7   255 199 4   22  2   249 4   22  2   7   255 224 4   253 1   224 4   46  2   7   255 236 4   212 0   235 4   
                                           218 0   235 4   218 0   230 4   223 0   230 4   223 0   224 4   224 0   224 4   224 0   218 4   223 0   218 4   223 0   213 4   218 0   213 4   218 0   211 4   212 0   211 4   212 0   213 4   206 0   213 4   206 0   218 4   201 0   218 4   201 0   224 4   
                                           200 0   224 4   200 0   230 4   201 0   230 4   201 0   235 4   206 0   235 4   206 0   236 4   212 0   7   255 199 4   212 0   249 4   212 0   7   255 224 4   187 0   224 4   237 0   7   255 145 0   218 0   145 0   237 0   145 0   237 0   163 0   243 0   
                                           163 0   243 0   253 0   243 0   253 0   243 0   15  1   237 0   15  1   237 0   15  1   218 0   15  1   218 0   253 0   212 0   253 0   212 0   163 0   212 0   163 0   212 0   145 0   218 0   7   255 145 0   252 1   145 0   16  2   145 0   16  2   163 0   
                                           22  2   163 0   22  2   253 0   22  2   253 0   22  2   15  1   16  2   15  1   16  2   15  1   252 1   15  1   252 1   253 0   246 1   253 0   246 1   163 0   246 1   163 0   246 1   145 0   252 1   0   252 65  117 116 111 67  65  68  32  83  108 105 100 
                                           101 13  10  26  0   86  2   73  6   247 2   97  120 67  1   2   0   52  18  7   255 7   255 217 1   36  1   33  6   36  1   33  6   36  1   33  6   211 1   33  6   211 1   217 1   211 1   217 1   211 1   217 1   36  1   7   255 217 1   36  1   217 1   36  
                                           1   7   255 217 1   36  1   217 1   36  1   7   255 217 1   36  1   217 1   36  1   7   255 30  2   124 1   28  2   128 1   28  2   128 1   23  2   131 1   23  2   131 1   18  2   128 1   18  2   128 1   16  2   124 1   16  2   124 1   18  2   119 1   18  
                                           2   119 1   23  2   116 1   23  2   116 1   28  2   119 1   28  2   119 1   30  2   124 1   7   255 120 5   73  1   120 5   85  1   120 5   85  1   130 5   89  1   130 5   89  1   179 5   89  1   179 5   89  1   188 5   85  1   188 5   85  1   188 5   73  
                                           1   188 5   73  1   179 5   70  1   179 5   70  1   130 5   70  1   130 5   70  1   120 5   73  1   7   255 120 5   39  1   120 5   51  1   120 5   51  1   130 5   55  1   130 5   55  1   179 5   55  1   179 5   55  1   188 5   51  1   188 5   51  1   188 
                                           5   39  1   188 5   39  1   179 5   36  1   179 5   36  1   130 5   36  1   130 5   36  1   120 5   39  1   7   255 120 5   162 1   120 5   174 1   120 5   174 1   130 5   177 1   130 5   177 1   179 5   177 1   179 5   177 1   188 5   174 1   188 5   174 
                                           1   188 5   162 1   188 5   162 1   179 5   158 1   179 5   158 1   130 5   158 1   130 5   158 1   120 5   162 1   7   255 120 5   196 1   120 5   208 1   120 5   208 1   130 5   211 1   130 5   211 1   179 5   211 1   179 5   211 1   188 5   208 1   188 
                                           5   208 1   188 5   196 1   188 5   196 1   179 5   192 1   179 5   192 1   130 5   192 1   130 5   192 1   120 5   196 1   7   255 203 5   73  1   203 5   85  1   203 5   85  1   213 5   89  1   213 5   89  1   6   6   89  1   6   6   89  1   15  6   85  
                                           1   15  6   85  1   15  6   73  1   15  6   73  1   6   6   70  1   6   6   70  1   213 5   70  1   213 5   70  1   203 5   73  1   7   255 203 5   39  1   203 5   51  1   203 5   51  1   213 5   55  1   213 5   55  1   6   6   55  1   6   6   55  1   15  
                                           6   51  1   15  6   51  1   15  6   39  1   15  6   39  1   6   6   36  1   6   6   36  1   213 5   36  1   213 5   36  1   203 5   39  1   7   255 203 5   162 1   203 5   174 1   203 5   174 1   213 5   177 1   213 5   177 1   6   6   177 1   6   6   177 
                                           1   15  6   174 1   15  6   174 1   15  6   162 1   15  6   162 1   6   6   158 1   6   6   158 1   213 5   158 1   213 5   158 1   203 5   162 1   7   255 203 5   196 1   203 5   208 1   203 5   208 1   213 5   211 1   213 5   211 1   6   6   211 1   6   
                                           6   211 1   15  6   208 1   15  6   208 1   15  6   196 1   15  6   196 1   6   6   192 1   6   6   192 1   213 5   192 1   213 5   192 1   203 5   196 1   7   255 219 1   36  1   218 1   37  1   218 1   37  1   217 1   38  1   217 1   38  1   215 1   37  
                                           1   215 1   37  1   215 1   36  1   215 1   36  1   215 1   34  1   215 1   34  1   217 1   34  1   217 1   34  1   218 1   34  1   218 1   34  1   219 1   36  1   7   255 213 1   36  1   221 1   36  1   7   255 217 1   32  1   217 1   40  1   7   255 219 
                                           1   211 1   218 1   213 1   218 1   213 1   217 1   213 1   217 1   213 1   215 1   213 1   215 1   213 1   215 1   211 1   215 1   211 1   215 1   210 1   215 1   210 1   217 1   209 1   217 1   209 1   218 1   210 1   218 1   210 1   219 1   211 1   7   
                                           255 213 1   211 1   221 1   211 1   7   255 217 1   207 1   217 1   215 1   7   255 35  6   36  1   34  6   37  1   34  6   37  1   33  6   38  1   33  6   38  1   31  6   37  1   31  6   37  1   31  6   36  1   31  6   36  1   31  6   34  1   31  6   34  
                                           1   33  6   34  1   33  6   34  1   34  6   34  1   34  6   34  1   35  6   36  1   7   255 29  6   36  1   37  6   36  1   7   255 33  6   32  1   33  6   40  1   7   255 35  6   211 1   34  6   213 1   34  6   213 1   33  6   213 1   33  6   213 1   31  
                                           6   213 1   31  6   213 1   31  6   211 1   31  6   211 1   31  6   210 1   31  6   210 1   33  6   209 1   33  6   209 1   34  6   210 1   34  6   210 1   35  6   211 1   7   255 29  6   211 1   37  6   211 1   7   255 33  6   207 1   33  6   215 1   7   
                                           255 198 5   36  1   197 5   37  1   197 5   37  1   196 5   38  1   196 5   38  1   194 5   37  1   194 5   37  1   194 5   36  1   194 5   36  1   194 5   34  1   194 5   34  1   196 5   34  1   196 5   34  1   197 5   34  1   197 5   34  1   198 5   36  
                                           1   7   255 192 5   36  1   200 5   36  1   7   255 196 5   32  1   196 5   40  1   7   255 198 5   211 1   197 5   213 1   197 5   213 1   196 5   213 1   196 5   213 1   194 5   213 1   194 5   213 1   194 5   211 1   194 5   211 1   194 5   210 1   194 
                                           5   210 1   196 5   209 1   196 5   209 1   197 5   210 1   197 5   210 1   198 5   211 1   7   255 192 5   211 1   200 5   211 1   7   255 196 5   207 1   196 5   215 1   7   255 25  2   124 1   24  2   125 1   24  2   125 1   23  2   126 1   23  2   126 
                                           1   21  2   125 1   21  2   125 1   21  2   124 1   21  2   124 1   21  2   122 1   21  2   122 1   23  2   121 1   23  2   121 1   24  2   122 1   24  2   122 1   25  2   124 1   7   255 19  2   124 1   27  2   124 1   7   255 23  2   119 1   23  2   128 
                                           1   7   255 49  0   41  1   103 1   41  1   103 1   41  1   103 1   94  1   7   255 103 1   94  1   66  2   94  1   7   255 66  2   94  1   66  2   153 1   66  2   153 1   103 1   153 1   103 1   153 1   103 1   206 1   103 1   206 1   49  0   206 1   49  
                                           0   206 1   49  0   41  1   7   255 49  0   41  1   49  0   41  1   7   255 49  0   41  1   49  0   41  1   7   255 49  0   41  1   49  0   41  1   7   255 40  2   140 1   29  2   146 1   29  2   146 1   17  2   146 1   17  2   146 1   6   2   140 1   6   
                                           2   140 1   0   2   130 1   0   2   130 1   0   2   117 1   0   2   117 1   6   2   107 1   6   2   107 1   17  2   101 1   17  2   101 1   29  2   101 1   29  2   101 1   40  2   107 1   7   255 40  2   107 1   40  2   140 1   7   255 198 1   79  1   198 
                                           1   90  1   198 1   90  1   208 1   94  1   208 1   94  1   7   2   94  1   7   2   94  1   17  2   90  1   17  2   90  1   17  2   79  1   17  2   79  1   7   2   75  1   7   2   75  1   208 1   75  1   208 1   75  1   198 1   79  1   7   255 198 1   44  
                                           1   198 1   56  1   198 1   56  1   208 1   60  1   208 1   60  1   7   2   60  1   7   2   60  1   17  2   56  1   17  2   56  1   17  2   44  1   17  2   44  1   7   2   41  1   7   2   41  1   208 1   41  1   208 1   41  1   198 1   44  1   7   255 198 
                                           1   157 1   198 1   169 1   198 1   169 1   208 1   172 1   208 1   172 1   7   2   172 1   7   2   172 1   17  2   169 1   17  2   169 1   17  2   157 1   17  2   157 1   7   2   153 1   7   2   153 1   208 1   153 1   208 1   153 1   198 1   157 1   7   
                                           255 198 1   191 1   198 1   203 1   198 1   203 1   208 1   206 1   208 1   206 1   7   2   206 1   7   2   206 1   17  2   203 1   17  2   203 1   17  2   191 1   17  2   191 1   7   2   187 1   7   2   187 1   208 1   187 1   208 1   187 1   198 1   191 
                                           1   7   255 28  2   79  1   28  2   90  1   28  2   90  1   39  2   94  1   39  2   94  1   94  2   94  1   94  2   94  1   104 2   90  1   104 2   90  1   104 2   79  1   104 2   79  1   94  2   75  1   94  2   75  1   39  2   75  1   39  2   75  1   28  
                                           2   79  1   7   255 28  2   44  1   28  2   56  1   28  2   56  1   39  2   60  1   39  2   60  1   94  2   60  1   94  2   60  1   104 2   56  1   104 2   56  1   104 2   44  1   104 2   44  1   94  2   41  1   94  2   41  1   39  2   41  1   39  2   41  
                                           1   28  2   44  1   7   255 28  2   157 1   28  2   169 1   28  2   169 1   39  2   172 1   39  2   172 1   94  2   172 1   94  2   172 1   104 2   169 1   104 2   169 1   104 2   157 1   104 2   157 1   94  2   153 1   94  2   153 1   39  2   153 1   39  
                                           2   153 1   28  2   157 1   7   255 28  2   191 1   28  2   203 1   28  2   203 1   39  2   206 1   39  2   206 1   94  2   206 1   94  2   206 1   104 2   203 1   104 2   203 1   104 2   191 1   104 2   191 1   94  2   187 1   94  2   187 1   39  2   187 
                                           1   39  2   187 1   28  2   191 1   7   255 51  0   41  1   50  0   42  1   50  0   42  1   49  0   43  1   49  0   43  1   47  0   42  1   47  0   42  1   47  0   41  1   47  0   41  1   47  0   39  1   47  0   39  1   49  0   39  1   49  0   39  1   50  
                                           0   39  1   50  0   39  1   51  0   41  1   7   255 45  0   41  1   53  0   41  1   7   255 49  0   37  1   49  0   45  1   7   255 51  0   206 1   50  0   208 1   50  0   208 1   49  0   208 1   49  0   208 1   47  0   208 1   47  0   208 1   47  0   206 
                                           1   47  0   206 1   47  0   205 1   47  0   205 1   49  0   204 1   49  0   204 1   50  0   205 1   50  0   205 1   51  0   206 1   7   255 45  0   206 1   53  0   206 1   7   255 49  0   202 1   49  0   210 1   7   255 134 0   206 1   133 0   208 1   133 
                                           0   208 1   132 0   208 1   132 0   208 1   130 0   208 1   130 0   208 1   130 0   206 1   130 0   206 1   130 0   205 1   130 0   205 1   132 0   204 1   132 0   204 1   133 0   205 1   133 0   205 1   134 0   206 1   7   255 127 0   206 1   136 0   206 
                                           1   7   255 132 0   202 1   132 0   210 1   7   255 134 0   124 1   133 0   125 1   133 0   125 1   132 0   126 1   132 0   126 1   130 0   125 1   130 0   125 1   130 0   124 1   130 0   124 1   130 0   122 1   130 0   122 1   132 0   121 1   132 0   121 
                                           1   133 0   122 1   133 0   122 1   134 0   124 1   7   255 127 0   124 1   136 0   124 1   7   255 132 0   119 1   132 0   128 1   7   255 25  2   206 1   24  2   208 1   24  2   208 1   23  2   208 1   23  2   208 1   21  2   208 1   21  2   208 1   21  
                                           2   206 1   21  2   206 1   21  2   205 1   21  2   205 1   23  2   204 1   23  2   204 1   24  2   205 1   24  2   205 1   25  2   206 1   7   255 19  2   206 1   27  2   206 1   7   255 23  2   202 1   23  2   210 1   7   255 25  2   41  1   24  2   42  
                                           1   24  2   42  1   23  2   43  1   23  2   43  1   21  2   42  1   21  2   42  1   21  2   41  1   21  2   41  1   21  2   39  1   21  2   39  1   23  2   39  1   23  2   39  1   24  2   39  1   24  2   39  1   25  2   41  1   7   255 19  2   41  1   27  
                                           2   41  1   7   255 23  2   37  1   23  2   45  1   7   255 25  2   124 1   24  2   125 1   24  2   125 1   23  2   126 1   23  2   126 1   21  2   125 1   21  2   125 1   21  2   124 1   21  2   124 1   21  2   122 1   21  2   122 1   23  2   121 1   23  
                                           2   121 1   24  2   122 1   24  2   122 1   25  2   124 1   7   255 19  2   124 1   27  2   124 1   7   255 23  2   119 1   23  2   128 1   7   255 94  0   44  1   94  0   56  1   94  0   56  1   104 0   60  1   104 0   60  1   159 0   60  1   159 0   60  
                                           1   170 0   56  1   170 0   56  1   170 0   44  1   170 0   44  1   159 0   41  1   159 0   41  1   104 0   41  1   104 0   41  1   94  0   44  1   7   255 94  0   191 1   94  0   203 1   94  0   203 1   104 0   206 1   104 0   206 1   159 0   206 1   159 
                                           0   206 1   170 0   203 1   170 0   203 1   170 0   191 1   170 0   191 1   159 0   187 1   159 0   187 1   104 0   187 1   104 0   187 1   94  0   191 1   0   252 65  117 116 111 67  65  68  32  83  108 105 100 101 13  10  26  0   86  2   73  6   247 2   
                                           97  120 67  1   2   0   52  18  51  255 51  255 2   1   6   1   9   5   6   1   9   5   6   1   9   5   199 1   9   5   199 1   2   1   199 1   2   1   199 1   2   1   6   1   7   255 7   255 2   1   6   1   9   5   6   1   9   5   6   1   9   5   199 1   
                                           )) "a")
 (_WriteStream FILE (vl-list->string (list 9   5   199 1   2   1   199 1   2   1   199 1   2   1   6   1   7   255 2   1   6   1   2   1   6   1   7   255 2   1   6   1   2   1   6   1   7   255 2   1   6   1   2   1   6   1   7   255 188 3   10  1   188 3   22  1   188 3   22  1   199 3   25  1   
                                           199 3   25  1   253 3   25  1   253 3   25  1   8   4   22  1   8   4   22  1   8   4   10  1   8   4   10  1   253 3   6   1   253 3   6   1   199 3   6   1   199 3   6   1   188 3   10  1   7   255 188 3   183 1   188 3   195 1   188 3   195 1   199 3   
                                           199 1   199 3   199 1   253 3   199 1   253 3   199 1   8   4   195 1   8   4   195 1   8   4   183 1   8   4   183 1   253 3   180 1   253 3   180 1   199 3   180 1   199 3   180 1   188 3   183 1   7   255 23  4   10  1   23  4   22  1   23  4   22  1   
                                           33  4   25  1   33  4   25  1   88  4   25  1   88  4   25  1   98  4   22  1   98  4   22  1   98  4   10  1   98  4   10  1   88  4   6   1   88  4   6   1   33  4   6   1   33  4   6   1   23  4   10  1   7   255 23  4   183 1   23  4   195 1   23  4   
                                           195 1   33  4   199 1   33  4   199 1   88  4   199 1   88  4   199 1   98  4   195 1   98  4   195 1   98  4   183 1   98  4   183 1   88  4   180 1   88  4   180 1   33  4   180 1   33  4   180 1   23  4   183 1   7   255 4   1   6   1   3   1   8   1   
                                           3   1   8   1   2   1   8   1   2   1   8   1   0   1   8   1   0   1   8   1   255 0   6   1   255 0   6   1   0   1   5   1   0   1   5   1   2   1   4   1   2   1   4   1   3   1   5   1   3   1   5   1   4   1   6   1   7   255 253 0   6   1   6   1   
                                           6   1   7   255 2   1   2   1   2   1   11  1   7   255 4   1   199 1   3   1   200 1   3   1   200 1   2   1   201 1   2   1   201 1   0   1   200 1   0   1   200 1   255 0   199 1   255 0   199 1   0   1   197 1   0   1   197 1   2   1   196 1   2   1   
                                           196 1   3   1   197 1   3   1   197 1   4   1   199 1   7   255 253 0   199 1   6   1   199 1   7   255 2   1   194 1   2   1   203 1   7   255 144 1   199 1   144 1   200 1   144 1   200 1   142 1   201 1   142 1   201 1   140 1   200 1   140 1   200 1   
                                           140 1   199 1   140 1   199 1   140 1   197 1   140 1   197 1   142 1   196 1   142 1   196 1   144 1   197 1   144 1   197 1   144 1   199 1   7   255 137 1   199 1   147 1   199 1   7   255 142 1   194 1   142 1   203 1   7   255 144 1   6   1   144 1   
                                           8   1   144 1   8   1   142 1   8   1   142 1   8   1   140 1   8   1   140 1   8   1   140 1   6   1   140 1   6   1   140 1   5   1   140 1   5   1   142 1   4   1   142 1   4   1   144 1   5   1   144 1   5   1   144 1   6   1   7   255 137 1   6   1   
                                           147 1   6   1   7   255 142 1   2   1   142 1   11  1   7   255 11  5   199 1   10  5   200 1   10  5   200 1   9   5   201 1   9   5   201 1   7   5   200 1   7   5   200 1   6   5   199 1   6   5   199 1   7   5   197 1   7   5   197 1   9   5   196 1   
                                           9   5   196 1   10  5   197 1   10  5   197 1   11  5   199 1   7   255 4   5   199 1   13  5   199 1   7   255 9   5   194 1   9   5   203 1   7   255 11  5   6   1   10  5   8   1   10  5   8   1   9   5   8   1   9   5   8   1   7   5   8   1   7   5   
                                           8   1   6   5   6   1   6   5   6   1   7   5   5   1   7   5   5   1   9   5   4   1   9   5   4   1   10  5   5   1   10  5   5   1   11  5   6   1   7   255 4   5   6   1   13  5   6   1   7   255 9   5   2   1   9   5   11  1   7   255 144 1   102 1   
                                           144 1   104 1   144 1   104 1   142 1   105 1   142 1   105 1   140 1   104 1   140 1   104 1   140 1   102 1   140 1   102 1   140 1   101 1   140 1   101 1   142 1   100 1   142 1   100 1   144 1   101 1   144 1   101 1   144 1   102 1   7   255 137 1   
                                           102 1   147 1   102 1   7   255 142 1   98  1   142 1   107 1   7   255 18  4   6   1   17  4   8   1   17  4   8   1   15  4   8   1   15  4   8   1   14  4   8   1   14  4   8   1   13  4   6   1   13  4   6   1   14  4   5   1   14  4   5   1   15  4   
                                           4   1   15  4   4   1   17  4   5   1   17  4   5   1   18  4   6   1   7   255 11  4   6   1   20  4   6   1   7   255 15  4   2   1   15  4   11  1   7   255 18  4   199 1   17  4   200 1   17  4   200 1   15  4   201 1   15  4   201 1   14  4   200 1   
                                           14  4   200 1   13  4   199 1   13  4   199 1   14  4   197 1   14  4   197 1   15  4   196 1   15  4   196 1   17  4   197 1   17  4   197 1   18  4   199 1   7   255 11  4   199 1   20  4   199 1   7   255 15  4   194 1   15  4   203 1   7   255 104 1   
                                           183 1   104 1   195 1   104 1   195 1   115 1   199 1   115 1   199 1   169 1   199 1   169 1   199 1   180 1   195 1   180 1   195 1   180 1   183 1   180 1   183 1   169 1   180 1   169 1   180 1   115 1   180 1   115 1   180 1   104 1   183 1   7   255 
                                           104 1   10  1   104 1   22  1   104 1   22  1   115 1   25  1   115 1   25  1   169 1   25  1   169 1   25  1   180 1   22  1   180 1   22  1   180 1   10  1   180 1   10  1   169 1   6   1   169 1   6   1   115 1   6   1   115 1   6   1   104 1   10  1   
                                           0   252 65  117 116 111 67  65  68  32  83  108 105 100 101 13  10  26  0   86  2   73  6   247 2   97  120 67  1   2   0   52  18  51  255 51  255 43  0   24  1   213 2   24  1   213 2   24  1   213 2   20  2   213 2   20  2   43  0   20  2   43  0   20  
                                           2   43  0   24  1   7   255 7   255 43  0   24  1   213 2   24  1   213 2   24  1   213 2   20  2   213 2   20  2   43  0   20  2   43  0   20  2   43  0   24  1   7   255 43  0   24  1   43  0   24  1   7   255 43  0   24  1   43  0   24  1   7   255 43  
                                           0   24  1   43  0   24  1   7   255 252 1   46  1   252 1   57  1   252 1   57  1   7   2   61  1   7   2   61  1   61  2   61  1   61  2   61  1   71  2   57  1   71  2   57  1   71  2   46  1   71  2   46  1   61  2   42  1   61  2   42  1   7   2   42  
                                           1   7   2   42  1   252 1   46  1   7   255 252 1   243 1   252 1   254 1   252 1   254 1   7   2   2   2   7   2   2   2   61  2   2   2   61  2   2   2   71  2   254 1   71  2   254 1   71  2   243 1   71  2   243 1   61  2   239 1   61  2   239 1   7   
                                           2   239 1   7   2   239 1   252 1   243 1   7   255 154 0   150 1   153 0   152 1   153 0   152 1   152 0   153 1   152 0   153 1   150 0   154 1   150 0   154 1   149 0   153 1   149 0   153 1   147 0   152 1   147 0   152 1   147 0   150 1   147 0   150 
                                           1   147 0   148 1   147 0   148 1   149 0   147 1   149 0   147 1   150 0   146 1   150 0   146 1   152 0   147 1   152 0   147 1   153 0   148 1   153 0   148 1   154 0   150 1   7   255 143 0   150 1   158 0   150 1   7   255 150 0   143 1   150 0   157 
                                           1   7   255 154 0   2   2   153 0   4   2   153 0   4   2   152 0   5   2   152 0   5   2   150 0   5   2   150 0   5   2   149 0   5   2   149 0   5   2   147 0   4   2   147 0   4   2   147 0   2   2   147 0   2   2   147 0   0   2   147 0   0   2   149 
                                           0   255 1   149 0   255 1   150 0   254 1   150 0   254 1   152 0   255 1   152 0   255 1   153 0   0   2   153 0   0   2   154 0   2   2   7   255 143 0   2   2   158 0   2   2   7   255 150 0   251 1   150 0   9   2   7   255 154 0   42  1   153 0   44  
                                           1   153 0   44  1   152 0   45  1   152 0   45  1   150 0   46  1   150 0   46  1   149 0   45  1   149 0   45  1   147 0   44  1   147 0   44  1   147 0   42  1   147 0   42  1   147 0   40  1   147 0   40  1   149 0   39  1   149 0   39  1   150 0   39  
                                           1   150 0   39  1   152 0   39  1   152 0   39  1   153 0   40  1   153 0   40  1   154 0   42  1   7   255 143 0   42  1   158 0   42  1   7   255 150 0   35  1   150 0   49  1   7   255 46  0   20  2   46  0   21  2   46  0   21  2   44  0   23  2   44  
                                           0   23  2   43  0   23  2   43  0   23  2   41  0   23  2   41  0   23  2   39  0   21  2   39  0   21  2   39  0   20  2   39  0   20  2   39  0   18  2   39  0   18  2   41  0   17  2   41  0   17  2   43  0   16  2   43  0   16  2   44  0   17  2   44  
                                           0   17  2   46  0   18  2   46  0   18  2   46  0   20  2   7   255 35  0   20  2   50  0   20  2   7   255 43  0   12  2   43  0   27  2   7   255 46  0   24  1   46  0   26  1   46  0   26  1   44  0   27  1   44  0   27  1   43  0   28  1   43  0   28  
                                           1   41  0   27  1   41  0   27  1   39  0   26  1   39  0   26  1   39  0   24  1   39  0   24  1   39  0   22  1   39  0   22  1   41  0   21  1   41  0   21  1   43  0   21  1   43  0   21  1   44  0   21  1   44  0   21  1   46  0   22  1   46  0   22  
                                           1   46  0   24  1   7   255 35  0   24  1   50  0   24  1   7   255 43  0   17  1   43  0   31  1   7   255 37  2   42  1   37  2   44  1   37  2   44  1   35  2   45  1   35  2   45  1   34  2   46  1   34  2   46  1   32  2   45  1   32  2   45  1   31  
                                           2   44  1   31  2   44  1   30  2   42  1   30  2   42  1   31  2   40  1   31  2   40  1   32  2   39  1   32  2   39  1   34  2   39  1   34  2   39  1   35  2   39  1   35  2   39  1   37  2   40  1   37  2   40  1   37  2   42  1   7   255 27  2   42  
                                           1   41  2   42  1   7   255 34  2   35  1   34  2   49  1   7   255 37  2   2   2   37  2   4   2   37  2   4   2   35  2   5   2   35  2   5   2   34  2   5   2   34  2   5   2   32  2   5   2   32  2   5   2   31  2   4   2   31  2   4   2   30  2   2   
                                           2   30  2   2   2   31  2   0   2   31  2   0   2   32  2   255 1   32  2   255 1   34  2   254 1   34  2   254 1   35  2   255 1   35  2   255 1   37  2   0   2   37  2   0   2   37  2   2   2   7   255 27  2   2   2   41  2   2   2   7   255 34  2   251 
                                           1   34  2   9   2   7   255 217 2   20  2   216 2   21  2   216 2   21  2   215 2   23  2   215 2   23  2   213 2   23  2   213 2   23  2   212 2   23  2   212 2   23  2   210 2   21  2   210 2   21  2   210 2   20  2   210 2   20  2   210 2   18  2   210 
                                           2   18  2   212 2   17  2   212 2   17  2   213 2   16  2   213 2   16  2   215 2   17  2   215 2   17  2   216 2   18  2   216 2   18  2   217 2   20  2   7   255 206 2   20  2   221 2   20  2   7   255 213 2   12  2   213 2   27  2   7   255 217 2   24  
                                           1   216 2   26  1   216 2   26  1   215 2   27  1   215 2   27  1   213 2   28  1   213 2   28  1   212 2   27  1   212 2   27  1   210 2   26  1   210 2   26  1   210 2   24  1   210 2   24  1   210 2   22  1   210 2   22  1   212 2   21  1   212 2   21  
                                           1   213 2   21  1   213 2   21  1   215 2   21  1   215 2   21  1   216 2   22  1   216 2   22  1   217 2   24  1   7   255 206 2   24  1   221 2   24  1   7   255 213 2   17  1   213 2   31  1   7   255 217 2   150 1   216 2   152 1   216 2   152 1   215 
                                           2   153 1   215 2   153 1   213 2   154 1   213 2   154 1   212 2   153 1   212 2   153 1   210 2   152 1   210 2   152 1   210 2   150 1   210 2   150 1   210 2   148 1   210 2   148 1   212 2   147 1   212 2   147 1   213 2   146 1   213 2   146 1   215 
                                           2   147 1   215 2   147 1   216 2   148 1   216 2   148 1   217 2   150 1   7   255 206 2   150 1   221 2   150 1   7   255 213 2   143 1   213 2   157 1   7   255 113 0   46  1   113 0   57  1   113 0   57  1   123 0   61  1   123 0   61  1   177 0   61  
                                           1   177 0   61  1   188 0   57  1   188 0   57  1   188 0   46  1   188 0   46  1   177 0   42  1   177 0   42  1   123 0   42  1   123 0   42  1   113 0   46  1   7   255 113 0   243 1   113 0   254 1   113 0   254 1   123 0   2   2   123 0   2   2   177 
                                           0   2   2   177 0   2   2   188 0   254 1   188 0   254 1   188 0   243 1   188 0   243 1   177 0   239 1   177 0   239 1   123 0   239 1   123 0   239 1   113 0   243 1   51  255 51  255 213 2   150 1   65  3   38  2   65  3   38  2   16  6   38  2   16  
                                           6   38  2   16  6   6   1   16  6   6   1   65  3   6   1   65  3   6   1   213 2   150 1   7   255 7   255 65  3   6   1   16  6   6   1   16  6   6   1   16  6   38  2   16  6   38  2   65  3   38  2   65  3   38  2   65  3   6   1   7   255 65  3   6   
                                           1   65  3   6   1   7   255 65  3   6   1   65  3   6   1   7   255 65  3   6   1   65  3   6   1   7   255 213 2   150 1   65  3   150 1   7   255 233 2   150 1   232 2   155 1   232 2   155 1   230 2   160 1   230 2   160 1   227 2   164 1   227 2   164 
                                           1   223 2   167 1   223 2   167 1   218 2   168 1   218 2   168 1   213 2   169 1   213 2   169 1   208 2   168 1   208 2   168 1   204 2   167 1   204 2   167 1   200 2   164 1   200 2   164 1   197 2   160 1   197 2   160 1   195 2   155 1   195 2   155 
                                           1   194 2   150 1   194 2   150 1   195 2   145 1   195 2   145 1   197 2   140 1   197 2   140 1   200 2   136 1   200 2   136 1   204 2   133 1   204 2   133 1   208 2   131 1   208 2   131 1   213 2   131 1   213 2   131 1   218 2   131 1   218 2   131 
                                           1   223 2   133 1   223 2   133 1   227 2   136 1   227 2   136 1   230 2   140 1   230 2   140 1   232 2   145 1   232 2   145 1   233 2   150 1   7   255 203 4   10  1   203 4   22  1   203 4   22  1   213 4   25  1   213 4   25  1   11  5   25  1   11  
                                           5   25  1   22  5   22  1   22  5   22  1   22  5   10  1   22  5   10  1   11  5   6   1   11  5   6   1   213 4   6   1   213 4   6   1   203 4   10  1   7   255 203 4   22  2   203 4   34  2   203 4   34  2   213 4   38  2   213 4   38  2   11  5   38  
                                           2   11  5   38  2   22  5   34  2   22  5   34  2   22  5   22  2   22  5   22  2   11  5   19  2   11  5   19  2   213 4   19  2   213 4   19  2   203 4   22  2   7   255 69  3   6   1   68  3   8   1   68  3   8   1   67  3   9   1   67  3   9   1   65  
                                           3   10  1   65  3   10  1   63  3   9   1   63  3   9   1   62  3   8   1   62  3   8   1   62  3   6   1   62  3   6   1   62  3   5   1   62  3   5   1   63  3   3   1   63  3   3   1   65  3   3   1   65  3   3   1   67  3   3   1   67  3   3   1   68  
                                           3   5   1   68  3   5   1   69  3   6   1   7   255 58  3   6   1   72  3   6   1   7   255 65  3   255 0   65  3   14  1   7   255 244 4   6   1   244 4   8   1   244 4   8   1   242 4   9   1   242 4   9   1   240 4   10  1   240 4   10  1   239 4   9   
                                           1   239 4   9   1   237 4   8   1   237 4   8   1   237 4   6   1   237 4   6   1   237 4   5   1   237 4   5   1   239 4   3   1   239 4   3   1   240 4   3   1   240 4   3   1   242 4   3   1   242 4   3   1   244 4   5   1   244 4   5   1   244 4   6   
                                           1   7   255 233 4   6   1   248 4   6   1   7   255 240 4   255 0   240 4   14  1   7   255 244 4   38  2   244 4   39  2   244 4   39  2   242 4   41  2   242 4   41  2   240 4   41  2   240 4   41  2   239 4   41  2   239 4   41  2   237 4   39  2   237 
                                           4   39  2   237 4   38  2   237 4   38  2   237 4   36  2   237 4   36  2   239 4   35  2   239 4   35  2   240 4   34  2   240 4   34  2   242 4   35  2   242 4   35  2   244 4   36  2   244 4   36  2   244 4   38  2   7   255 233 4   38  2   248 4   38  
                                           2   7   255 240 4   30  2   240 4   45  2   7   255 20  6   38  2   19  6   39  2   19  6   39  2   18  6   41  2   18  6   41  2   16  6   41  2   16  6   41  2   14  6   41  2   14  6   41  2   13  6   39  2   13  6   39  2   12  6   38  2   12  6   38  
                                           2   13  6   36  2   13  6   36  2   14  6   35  2   14  6   35  2   16  6   34  2   16  6   34  2   18  6   35  2   18  6   35  2   19  6   36  2   19  6   36  2   20  6   38  2   7   255 9   6   38  2   23  6   38  2   7   255 16  6   30  2   16  6   45  
                                           2   7   255 20  6   6   1   19  6   8   1   19  6   8   1   18  6   9   1   18  6   9   1   16  6   10  1   16  6   10  1   14  6   9   1   14  6   9   1   13  6   8   1   13  6   8   1   12  6   6   1   12  6   6   1   13  6   5   1   13  6   5   1   14  
                                           6   3   1   14  6   3   1   16  6   3   1   16  6   3   1   18  6   3   1   18  6   3   1   19  6   5   1   19  6   5   1   20  6   6   1   7   255 9   6   6   1   23  6   6   1   7   255 16  6   255 0   16  6   14  1   7   255 69  3   38  2   68  3   39  
                                           2   68  3   39  2   67  3   41  2   67  3   41  2   65  3   41  2   65  3   41  2   63  3   41  2   63  3   41  2   62  3   39  2   62  3   39  2   62  3   38  2   62  3   38  2   62  3   36  2   62  3   36  2   63  3   35  2   63  3   35  2   65  3   34  
                                           2   65  3   34  2   67  3   35  2   67  3   35  2   68  3   36  2   68  3   36  2   69  3   38  2   7   255 58  3   38  2   72  3   38  2   7   255 65  3   30  2   65  3   45  2   7   255 217 2   150 1   216 2   152 1   216 2   152 1   215 2   153 1   215 
                                           2   153 1   213 2   154 1   213 2   154 1   212 2   153 1   212 2   153 1   210 2   152 1   210 2   152 1   210 2   150 1   210 2   150 1   210 2   148 1   210 2   148 1   212 2   147 1   212 2   147 1   213 2   146 1   213 2   146 1   215 2   147 1   215 
                                           2   147 1   216 2   148 1   216 2   148 1   217 2   150 1   7   255 206 2   150 1   221 2   150 1   7   255 213 2   143 1   213 2   157 1   0   252 65  117 116 111 67  65  68  32  83  108 105 100 101 13  10  26  0   86  2   73  6   247 2   97  120 67  1   
                                           )) "a")
 (_WriteStream FILE (vl-list->string (list 2   0   52  18  7   255 7   255 93  0   230 0   240 5   230 0   240 5   230 0   240 5   3   2   240 5   3   2   93  0   3   2   93  0   3   2   93  0   230 0   7   255 93  0   230 0   93  0   230 0   7   255 93  0   230 0   93  0   230 0   7   255 93  0   
                                           230 0   93  0   230 0   7   255 229 3   236 0   229 3   254 0   229 3   254 0   246 3   4   1   246 3   4   1   75  4   4   1   75  4   4   1   92  4   254 0   92  4   254 0   92  4   236 0   92  4   236 0   75  4   230 0   75  4   230 0   246 3   230 0   
                                           246 3   230 0   229 3   236 0   7   255 229 3   235 1   229 3   254 1   229 3   254 1   246 3   3   2   246 3   3   2   75  4   3   2   75  4   3   2   92  4   254 1   92  4   254 1   92  4   235 1   92  4   235 1   75  4   230 1   75  4   230 1   246 3   
                                           230 1   246 3   230 1   229 3   235 1   7   255 96  0   230 0   95  0   233 0   95  0   233 0   93  0   234 0   93  0   234 0   90  0   233 0   90  0   233 0   89  0   230 0   89  0   230 0   90  0   228 0   90  0   228 0   93  0   227 0   93  0   227 0   
                                           95  0   228 0   95  0   228 0   96  0   230 0   7   255 86  0   230 0   100 0   230 0   7   255 93  0   223 0   93  0   237 0   7   255 90  1   230 0   89  1   233 0   89  1   233 0   87  1   234 0   87  1   234 0   84  1   233 0   84  1   233 0   83  1   
                                           230 0   83  1   230 0   84  1   228 0   84  1   228 0   87  1   227 0   87  1   227 0   89  1   228 0   89  1   228 0   90  1   230 0   7   255 79  1   230 0   94  1   230 0   7   255 87  1   223 0   87  1   237 0   7   255 36  4   230 0   35  4   233 0   
                                           35  4   233 0   32  4   234 0   32  4   234 0   30  4   233 0   30  4   233 0   29  4   230 0   29  4   230 0   30  4   228 0   30  4   228 0   32  4   227 0   32  4   227 0   35  4   228 0   35  4   228 0   36  4   230 0   7   255 25  4   230 0   40  4   
                                           230 0   7   255 32  4   223 0   32  4   237 0   7   255 244 5   230 0   243 5   233 0   243 5   233 0   240 5   234 0   240 5   234 0   238 5   233 0   238 5   233 0   237 5   230 0   237 5   230 0   238 5   228 0   238 5   228 0   240 5   227 0   240 5   
                                           227 0   243 5   228 0   243 5   228 0   244 5   230 0   7   255 233 5   230 0   247 5   230 0   7   255 240 5   223 0   240 5   237 0   7   255 244 5   3   2   243 5   6   2   243 5   6   2   240 5   7   2   240 5   7   2   238 5   6   2   238 5   6   2   
                                           237 5   3   2   237 5   3   2   238 5   1   2   238 5   1   2   240 5   0   2   240 5   0   2   243 5   1   2   243 5   1   2   244 5   3   2   7   255 233 5   3   2   247 5   3   2   7   255 240 5   252 1   240 5   11  2   7   255 36  4   3   2   35  4   
                                           6   2   35  4   6   2   32  4   7   2   32  4   7   2   30  4   6   2   30  4   6   2   29  4   3   2   29  4   3   2   30  4   1   2   30  4   1   2   32  4   0   2   32  4   0   2   35  4   1   2   35  4   1   2   36  4   3   2   7   255 25  4   3   2   
                                           40  4   3   2   7   255 32  4   252 1   32  4   11  2   7   255 90  1   3   2   89  1   6   2   89  1   6   2   87  1   7   2   87  1   7   2   84  1   6   2   84  1   6   2   83  1   3   2   83  1   3   2   84  1   1   2   84  1   1   2   87  1   0   2   
                                           87  1   0   2   89  1   1   2   89  1   1   2   90  1   3   2   7   255 79  1   3   2   94  1   3   2   7   255 87  1   252 1   87  1   11  2   7   255 96  0   3   2   95  0   6   2   95  0   6   2   93  0   7   2   93  0   7   2   90  0   6   2   90  0   
                                           6   2   89  0   3   2   89  0   3   2   90  0   1   2   90  0   1   2   93  0   0   2   93  0   0   2   95  0   1   2   95  0   1   2   96  0   3   2   7   255 86  0   3   2   100 0   3   2   7   255 93  0   252 1   93  0   11  2   7   255 90  1   117 1   
                                           89  1   119 1   89  1   119 1   87  1   120 1   87  1   120 1   84  1   119 1   84  1   119 1   83  1   117 1   83  1   117 1   84  1   114 1   84  1   114 1   87  1   113 1   87  1   113 1   89  1   114 1   89  1   114 1   90  1   117 1   7   255 79  1   
                                           117 1   94  1   117 1   7   255 87  1   110 1   87  1   124 1   51  255 51  255 93  0   230 0   240 5   230 0   240 5   230 0   240 5   3   2   240 5   3   2   93  0   3   2   93  0   3   2   93  0   230 0   7   255 7   255 27  1   235 1   27  1   254 1   
                                           27  1   254 1   44  1   3   2   44  1   3   2   129 1   3   2   129 1   3   2   146 1   254 1   146 1   254 1   146 1   235 1   146 1   235 1   129 1   230 1   129 1   230 1   44  1   230 1   44  1   230 1   27  1   235 1   7   255 27  1   236 0   27  1   
                                           254 0   27  1   254 0   44  1   4   1   44  1   4   1   129 1   4   1   129 1   4   1   146 1   254 0   146 1   254 0   146 1   236 0   146 1   236 0   129 1   230 0   129 1   230 0   44  1   230 0   44  1   230 0   27  1   236 0   0   252 65  117 116 111 
                                           67  65  68  32  83  108 105 100 101 13  10  26  0   86  2   106 6   234 2   99  219 79  1   2   0   52  18  7   255 7   255 26  0   50  1   183 0   50  1   183 0   50  1   183 0   91  1   7   255 183 0   91  1   179 1   91  1   7   255 179 1   91  1   179 
                                           1   145 1   179 1   145 1   183 0   145 1   183 0   145 1   183 0   185 1   183 0   185 1   26  0   185 1   26  0   185 1   26  0   50  1   7   255 26  0   50  1   26  0   50  1   7   255 26  0   50  1   26  0   50  1   7   255 156 1   132 1   153 1   134 
                                           1   153 1   134 1   150 1   136 1   150 1   136 1   146 1   137 1   146 1   137 1   142 1   137 1   142 1   137 1   139 1   137 1   139 1   137 1   135 1   136 1   135 1   136 1   132 1   134 1   132 1   134 1   129 1   132 1   129 1   132 1   126 1   129 
                                           1   126 1   129 1   125 1   125 1   125 1   125 1   124 1   122 1   124 1   122 1   123 1   118 1   123 1   118 1   124 1   114 1   124 1   114 1   125 1   110 1   125 1   110 1   126 1   107 1   126 1   107 1   129 1   104 1   129 1   104 1   132 1   102 
                                           1   132 1   102 1   135 1   100 1   135 1   100 1   139 1   99  1   139 1   99  1   142 1   99  1   142 1   99  1   146 1   99  1   146 1   99  1   150 1   100 1   150 1   100 1   153 1   102 1   153 1   102 1   156 1   104 1   7   255 156 1   104 1   156 
                                           1   132 1   7   255 77  1   79  1   77  1   88  1   77  1   88  1   85  1   91  1   85  1   91  1   127 1   91  1   127 1   91  1   135 1   88  1   135 1   88  1   135 1   79  1   135 1   79  1   127 1   76  1   127 1   76  1   85  1   76  1   85  1   76  
                                           1   77  1   79  1   7   255 77  1   53  1   77  1   62  1   77  1   62  1   85  1   65  1   85  1   65  1   127 1   65  1   127 1   65  1   135 1   62  1   135 1   62  1   135 1   53  1   135 1   53  1   127 1   50  1   127 1   50  1   85  1   50  1   85  
                                           1   50  1   77  1   53  1   7   255 77  1   148 1   77  1   157 1   77  1   157 1   85  1   159 1   85  1   159 1   127 1   159 1   127 1   159 1   135 1   157 1   135 1   157 1   135 1   148 1   135 1   148 1   127 1   145 1   127 1   145 1   85  1   145 
                                           1   85  1   145 1   77  1   148 1   7   255 77  1   174 1   77  1   183 1   77  1   183 1   85  1   185 1   85  1   185 1   127 1   185 1   127 1   185 1   135 1   183 1   135 1   183 1   135 1   174 1   135 1   174 1   127 1   171 1   127 1   171 1   85  
                                           1   171 1   85  1   171 1   77  1   174 1   7   255 150 1   79  1   150 1   88  1   150 1   88  1   158 1   91  1   158 1   91  1   200 1   91  1   200 1   91  1   208 1   88  1   208 1   88  1   208 1   79  1   208 1   79  1   200 1   76  1   200 1   76  
                                           1   158 1   76  1   158 1   76  1   150 1   79  1   7   255 150 1   53  1   150 1   62  1   150 1   62  1   158 1   65  1   158 1   65  1   200 1   65  1   200 1   65  1   208 1   62  1   208 1   62  1   208 1   53  1   208 1   53  1   200 1   50  1   200 
                                           1   50  1   158 1   50  1   158 1   50  1   150 1   53  1   7   255 150 1   148 1   150 1   157 1   150 1   157 1   158 1   159 1   158 1   159 1   200 1   159 1   200 1   159 1   208 1   157 1   208 1   157 1   208 1   148 1   208 1   148 1   200 1   145 
                                           1   200 1   145 1   158 1   145 1   158 1   145 1   150 1   148 1   7   255 150 1   174 1   150 1   183 1   150 1   183 1   158 1   185 1   158 1   185 1   200 1   185 1   200 1   185 1   208 1   183 1   208 1   183 1   208 1   174 1   208 1   174 1   200 
                                           1   171 1   200 1   171 1   158 1   171 1   158 1   171 1   150 1   174 1   7   255 49  0   53  1   49  0   62  1   49  0   62  1   58  0   65  1   58  0   65  1   99  0   65  1   99  0   65  1   108 0   62  1   108 0   62  1   108 0   53  1   108 0   53  
                                           1   99  0   50  1   99  0   50  1   58  0   50  1   58  0   50  1   49  0   53  1   7   255 49  0   174 1   49  0   183 1   49  0   183 1   58  0   185 1   58  0   185 1   99  0   185 1   99  0   185 1   108 0   183 1   108 0   183 1   108 0   174 1   108 
                                           0   174 1   99  0   171 1   99  0   171 1   58  0   171 1   58  0   171 1   49  0   174 1   7   255 32  0   50  1   31  0   52  1   31  0   52  1   30  0   54  1   30  0   54  1   28  0   55  1   28  0   55  1   26  0   56  1   26  0   56  1   25  0   55  
                                           1   25  0   55  1   23  0   54  1   23  0   54  1   22  0   52  1   22  0   52  1   21  0   50  1   21  0   50  1   22  0   48  1   22  0   48  1   23  0   47  1   23  0   47  1   25  0   46  1   25  0   46  1   26  0   45  1   26  0   45  1   28  0   46  
                                           1   28  0   46  1   30  0   47  1   30  0   47  1   31  0   48  1   31  0   48  1   32  0   50  1   7   255 16  0   50  1   37  0   50  1   7   255 26  0   40  1   26  0   61  1   7   255 84  0   118 1   83  0   120 1   83  0   120 1   82  0   122 1   82  
                                           0   122 1   81  0   123 1   81  0   123 1   79  0   123 1   79  0   123 1   77  0   123 1   77  0   123 1   75  0   122 1   75  0   122 1   74  0   120 1   74  0   120 1   73  0   118 1   73  0   118 1   74  0   116 1   74  0   116 1   75  0   114 1   75  
                                           0   114 1   77  0   113 1   77  0   113 1   79  0   113 1   79  0   113 1   81  0   113 1   81  0   113 1   82  0   114 1   82  0   114 1   83  0   116 1   83  0   116 1   84  0   118 1   7   255 68  0   118 1   89  0   118 1   7   255 79  0   107 1   79  
                                           0   128 1   7   255 148 1   118 1   147 1   120 1   147 1   120 1   146 1   122 1   146 1   122 1   144 1   123 1   144 1   123 1   142 1   123 1   142 1   123 1   140 1   123 1   140 1   123 1   139 1   122 1   139 1   122 1   138 1   120 1   138 1   120 
                                           1   137 1   118 1   137 1   118 1   138 1   116 1   138 1   116 1   139 1   114 1   139 1   114 1   140 1   113 1   140 1   113 1   142 1   113 1   142 1   113 1   144 1   113 1   144 1   113 1   146 1   114 1   146 1   114 1   147 1   116 1   147 1   116 
                                           1   148 1   118 1   7   255 132 1   118 1   153 1   118 1   7   255 142 1   107 1   142 1   128 1   7   255 32  0   185 1   31  0   187 1   31  0   187 1   30  0   189 1   30  0   189 1   28  0   190 1   28  0   190 1   26  0   191 1   26  0   191 1   25  
                                           0   190 1   25  0   190 1   23  0   189 1   23  0   189 1   22  0   187 1   22  0   187 1   21  0   185 1   21  0   185 1   22  0   183 1   22  0   183 1   23  0   182 1   23  0   182 1   25  0   181 1   25  0   181 1   26  0   180 1   26  0   180 1   28  
                                           0   181 1   28  0   181 1   30  0   182 1   30  0   182 1   31  0   183 1   31  0   183 1   32  0   185 1   7   255 16  0   185 1   37  0   185 1   7   255 26  0   175 1   26  0   196 1   7   255 148 1   185 1   147 1   187 1   147 1   187 1   146 1   189 
                                           1   146 1   189 1   144 1   190 1   144 1   190 1   142 1   191 1   142 1   191 1   140 1   190 1   140 1   190 1   139 1   189 1   139 1   189 1   138 1   187 1   138 1   187 1   137 1   185 1   137 1   185 1   138 1   183 1   138 1   183 1   139 1   182 
                                           1   139 1   182 1   140 1   181 1   140 1   181 1   142 1   180 1   142 1   180 1   144 1   181 1   144 1   181 1   146 1   182 1   146 1   182 1   147 1   183 1   147 1   183 1   148 1   185 1   7   255 132 1   185 1   153 1   185 1   7   255 142 1   175 
                                           1   142 1   196 1   7   255 148 1   50  1   147 1   52  1   147 1   52  1   146 1   54  1   146 1   54  1   144 1   55  1   144 1   55  1   142 1   56  1   142 1   56  1   140 1   55  1   140 1   55  1   139 1   54  1   139 1   54  1   138 1   52  1   138 
                                           1   52  1   137 1   50  1   137 1   50  1   138 1   48  1   138 1   48  1   139 1   47  1   139 1   47  1   140 1   46  1   140 1   46  1   142 1   45  1   142 1   45  1   144 1   46  1   144 1   46  1   146 1   47  1   146 1   47  1   147 1   48  1   147 
                                           1   48  1   148 1   50  1   7   255 132 1   50  1   153 1   50  1   7   255 142 1   40  1   142 1   61  1   7   255 237 0   35  1   77  6   35  1   77  6   35  1   77  6   201 1   77  6   201 1   237 0   201 1   237 0   201 1   237 0   35  1   7   255 237 
                                           0   35  1   237 0   35  1   7   255 237 0   35  1   237 0   35  1   7   255 148 1   118 1   147 1   120 1   147 1   120 1   146 1   122 1   146 1   122 1   145 1   123 1   145 1   123 1   142 1   123 1   142 1   123 1   140 1   123 1   140 1   123 1   139 
                                           1   122 1   139 1   122 1   137 1   120 1   137 1   120 1   137 1   118 1   137 1   118 1   137 1   116 1   137 1   116 1   139 1   114 1   139 1   114 1   140 1   113 1   140 1   113 1   142 1   112 1   142 1   112 1   145 1   113 1   145 1   113 1   146 
                                           1   114 1   146 1   114 1   147 1   116 1   147 1   116 1   148 1   118 1   7   255 19  4   79  1   19  4   88  1   19  4   88  1   27  4   91  1   27  4   91  1   69  4   91  1   69  4   91  1   77  4   88  1   77  4   88  1   77  4   79  1   77  4   79  
                                           1   69  4   76  1   69  4   76  1   27  4   76  1   27  4   76  1   19  4   79  1   7   255 19  4   53  1   19  4   62  1   19  4   62  1   27  4   65  1   27  4   65  1   69  4   65  1   69  4   65  1   77  4   62  1   77  4   62  1   77  4   53  1   77  
                                           4   53  1   69  4   50  1   69  4   50  1   27  4   50  1   27  4   50  1   19  4   53  1   7   255 19  4   148 1   19  4   157 1   19  4   157 1   27  4   159 1   27  4   159 1   69  4   159 1   69  4   159 1   77  4   157 1   77  4   157 1   77  4   148 
                                           1   77  4   148 1   69  4   145 1   69  4   145 1   27  4   145 1   27  4   145 1   19  4   148 1   7   255 19  4   174 1   19  4   183 1   19  4   183 1   27  4   185 1   27  4   185 1   69  4   185 1   69  4   185 1   77  4   183 1   77  4   183 1   77  
                                           4   174 1   77  4   174 1   69  4   171 1   69  4   171 1   27  4   171 1   27  4   171 1   19  4   174 1   7   255 92  4   79  1   92  4   88  1   92  4   88  1   100 4   91  1   100 4   91  1   142 4   91  1   142 4   91  1   150 4   88  1   150 4   88  
                                           1   150 4   79  1   150 4   79  1   142 4   76  1   142 4   76  1   100 4   76  1   100 4   76  1   92  4   79  1   7   255 92  4   53  1   92  4   62  1   92  4   62  1   100 4   65  1   100 4   65  1   142 4   65  1   142 4   65  1   150 4   62  1   150 
                                           4   62  1   150 4   53  1   150 4   53  1   142 4   50  1   142 4   50  1   100 4   50  1   100 4   50  1   92  4   53  1   7   255 92  4   148 1   92  4   157 1   92  4   157 1   100 4   159 1   100 4   159 1   142 4   159 1   142 4   159 1   150 4   157 
                                           1   150 4   157 1   150 4   148 1   150 4   148 1   142 4   145 1   142 4   145 1   100 4   145 1   100 4   145 1   92  4   148 1   7   255 92  4   174 1   92  4   183 1   92  4   183 1   100 4   185 1   100 4   185 1   142 4   185 1   142 4   185 1   150 
                                           4   183 1   150 4   183 1   150 4   174 1   150 4   174 1   142 4   171 1   142 4   171 1   100 4   171 1   100 4   171 1   92  4   174 1   7   255 242 0   201 1   242 0   203 1   242 0   203 1   241 0   205 1   241 0   205 1   239 0   206 1   239 0   206 
                                           1   237 0   206 1   237 0   206 1   235 0   206 1   235 0   206 1   234 0   205 1   234 0   205 1   232 0   203 1   232 0   203 1   232 0   201 1   232 0   201 1   232 0   199 1   232 0   199 1   234 0   197 1   234 0   197 1   235 0   196 1   235 0   196 
                                           1   237 0   196 1   237 0   196 1   239 0   196 1   239 0   196 1   241 0   197 1   241 0   197 1   242 0   199 1   242 0   199 1   242 0   201 1   7   255 227 0   201 1   248 0   201 1   7   255 237 0   191 1   237 0   211 1   7   255 242 0   35  1   242 
                                           0   37  1   242 0   37  1   241 0   38  1   241 0   38  1   239 0   40  1   239 0   40  1   237 0   40  1   237 0   40  1   235 0   40  1   235 0   40  1   234 0   38  1   234 0   38  1   232 0   37  1   232 0   37  1   232 0   35  1   232 0   35  1   232 
                                           0   33  1   232 0   33  1   234 0   31  1   234 0   31  1   235 0   30  1   235 0   30  1   237 0   30  1   237 0   30  1   239 0   30  1   239 0   30  1   241 0   31  1   241 0   31  1   242 0   33  1   242 0   33  1   242 0   35  1   7   255 227 0   35  
                                           1   248 0   35  1   7   255 237 0   24  1   237 0   45  1   7   255 82  6   35  1   82  6   37  1   82  6   37  1   81  6   38  1   81  6   38  1   79  6   40  1   79  6   40  1   77  6   40  1   77  6   40  1   75  6   40  1   75  6   40  1   74  6   38  
                                           )) "a")
 (_WriteStream FILE (vl-list->string (list 1   74  6   38  1   72  6   37  1   72  6   37  1   72  6   35  1   72  6   35  1   72  6   33  1   72  6   33  1   74  6   31  1   74  6   31  1   75  6   30  1   75  6   30  1   77  6   30  1   77  6   30  1   79  6   30  1   79  6   30  1   81  6   31  
                                           1   81  6   31  1   82  6   33  1   82  6   33  1   82  6   35  1   7   255 67  6   35  1   88  6   35  1   7   255 77  6   24  1   77  6   45  1   7   255 82  6   201 1   82  6   203 1   82  6   203 1   81  6   205 1   81  6   205 1   79  6   206 1   79  
                                           6   206 1   77  6   206 1   77  6   206 1   75  6   206 1   75  6   206 1   74  6   205 1   74  6   205 1   72  6   203 1   72  6   203 1   72  6   201 1   72  6   201 1   72  6   199 1   72  6   199 1   74  6   197 1   74  6   197 1   75  6   196 1   75  
                                           6   196 1   77  6   196 1   77  6   196 1   79  6   196 1   79  6   196 1   81  6   197 1   81  6   197 1   82  6   199 1   82  6   199 1   82  6   201 1   7   255 67  6   201 1   88  6   201 1   7   255 77  6   191 1   77  6   211 1   7   255 148 1   118 
                                           1   147 1   120 1   147 1   120 1   146 1   122 1   146 1   122 1   144 1   123 1   144 1   123 1   142 1   123 1   142 1   123 1   140 1   123 1   140 1   123 1   139 1   122 1   139 1   122 1   138 1   120 1   138 1   120 1   137 1   118 1   137 1   118 
                                           1   138 1   116 1   138 1   116 1   139 1   114 1   139 1   114 1   140 1   113 1   140 1   113 1   142 1   113 1   142 1   113 1   144 1   113 1   144 1   113 1   146 1   114 1   146 1   114 1   147 1   116 1   147 1   116 1   148 1   118 1   7   255 132 
                                           1   118 1   153 1   118 1   7   255 142 1   107 1   142 1   128 1   7   255 90  4   185 1   89  4   187 1   89  4   187 1   88  4   189 1   88  4   189 1   87  4   190 1   87  4   190 1   85  4   191 1   85  4   191 1   83  4   190 1   83  4   190 1   81  
                                           4   189 1   81  4   189 1   80  4   187 1   80  4   187 1   79  4   185 1   79  4   185 1   80  4   183 1   80  4   183 1   81  4   182 1   81  4   182 1   83  4   181 1   83  4   181 1   85  4   180 1   85  4   180 1   87  4   181 1   87  4   181 1   88  
                                           4   182 1   88  4   182 1   89  4   183 1   89  4   183 1   90  4   185 1   7   255 74  4   185 1   95  4   185 1   7   255 85  4   175 1   85  4   196 1   7   255 90  4   50  1   89  4   52  1   89  4   52  1   88  4   54  1   88  4   54  1   87  4   55  
                                           1   87  4   55  1   85  4   56  1   85  4   56  1   83  4   55  1   83  4   55  1   81  4   54  1   81  4   54  1   80  4   52  1   80  4   52  1   79  4   50  1   79  4   50  1   80  4   48  1   80  4   48  1   81  4   47  1   81  4   47  1   83  4   46  
                                           1   83  4   46  1   85  4   45  1   85  4   45  1   87  4   46  1   87  4   46  1   88  4   47  1   88  4   47  1   89  4   48  1   89  4   48  1   90  4   50  1   7   255 74  4   50  1   95  4   50  1   7   255 85  4   40  1   85  4   61  1   0   252 65  
                                           117 116 111 67  65  68  32  83  108 105 100 101 13  10  26  0   86  2   73  6   247 2   97  120 67  1   2   0   52  18  7   255 7   255 239 1   40  1   37  6   40  1   37  6   40  1   37  6   212 1   37  6   212 1   239 1   212 1   239 1   212 1   239 1   
                                           40  1   7   255 239 1   40  1   239 1   40  1   7   255 239 1   40  1   239 1   40  1   7   255 239 1   40  1   239 1   40  1   7   255 10  5   76  1   10  5   88  1   10  5   88  1   20  5   92  1   20  5   92  1   74  5   92  1   74  5   92  1   84  5   
                                           88  1   84  5   88  1   84  5   76  1   84  5   76  1   74  5   73  1   74  5   73  1   20  5   73  1   20  5   73  1   10  5   76  1   7   255 10  5   43  1   10  5   55  1   10  5   55  1   20  5   58  1   20  5   58  1   74  5   58  1   74  5   58  1   
                                           84  5   55  1   84  5   55  1   84  5   43  1   84  5   43  1   74  5   40  1   74  5   40  1   20  5   40  1   20  5   40  1   10  5   43  1   7   255 10  5   164 1   10  5   176 1   10  5   176 1   20  5   179 1   20  5   179 1   74  5   179 1   74  5   
                                           179 1   84  5   176 1   84  5   176 1   84  5   164 1   84  5   164 1   74  5   160 1   74  5   160 1   20  5   160 1   20  5   160 1   10  5   164 1   7   255 10  5   197 1   10  5   209 1   10  5   209 1   20  5   212 1   20  5   212 1   74  5   212 1   
                                           74  5   212 1   84  5   209 1   84  5   209 1   84  5   197 1   84  5   197 1   74  5   194 1   74  5   194 1   20  5   194 1   20  5   194 1   10  5   197 1   7   255 96  5   76  1   96  5   88  1   96  5   88  1   107 5   92  1   107 5   92  1   160 5   
                                           92  1   160 5   92  1   171 5   88  1   171 5   88  1   171 5   76  1   171 5   76  1   160 5   73  1   160 5   73  1   107 5   73  1   107 5   73  1   96  5   76  1   7   255 96  5   43  1   96  5   55  1   96  5   55  1   107 5   58  1   107 5   58  1   
                                           160 5   58  1   160 5   58  1   171 5   55  1   171 5   55  1   171 5   43  1   171 5   43  1   160 5   40  1   160 5   40  1   107 5   40  1   107 5   40  1   96  5   43  1   7   255 96  5   164 1   96  5   176 1   96  5   176 1   107 5   179 1   107 5   
                                           179 1   160 5   179 1   160 5   179 1   171 5   176 1   171 5   176 1   171 5   164 1   171 5   164 1   160 5   160 1   160 5   160 1   107 5   160 1   107 5   160 1   96  5   164 1   7   255 96  5   197 1   96  5   209 1   96  5   209 1   107 5   212 1   
                                           107 5   212 1   160 5   212 1   160 5   212 1   171 5   209 1   171 5   209 1   171 5   197 1   171 5   197 1   160 5   194 1   160 5   194 1   107 5   194 1   107 5   194 1   96  5   197 1   7   255 183 5   76  1   183 5   88  1   183 5   88  1   193 5   
                                           92  1   193 5   92  1   247 5   92  1   247 5   92  1   1   6   88  1   1   6   88  1   1   6   76  1   1   6   76  1   247 5   73  1   247 5   73  1   193 5   73  1   193 5   73  1   183 5   76  1   7   255 183 5   43  1   183 5   55  1   183 5   55  1   
                                           193 5   58  1   193 5   58  1   247 5   58  1   247 5   58  1   1   6   55  1   1   6   55  1   1   6   43  1   1   6   43  1   247 5   40  1   247 5   40  1   193 5   40  1   193 5   40  1   183 5   43  1   7   255 183 5   164 1   183 5   176 1   183 5   
                                           176 1   193 5   179 1   193 5   179 1   247 5   179 1   247 5   179 1   1   6   176 1   1   6   176 1   1   6   164 1   1   6   164 1   247 5   160 1   247 5   160 1   193 5   160 1   193 5   160 1   183 5   164 1   7   255 183 5   197 1   183 5   209 1   
                                           183 5   209 1   193 5   212 1   193 5   212 1   247 5   212 1   247 5   212 1   1   6   209 1   1   6   209 1   1   6   197 1   1   6   197 1   247 5   194 1   247 5   194 1   193 5   194 1   193 5   194 1   183 5   197 1   7   255 140 5   212 1   139 5   
                                           216 1   139 5   216 1   137 5   218 1   137 5   218 1   134 5   219 1   134 5   219 1   130 5   218 1   130 5   218 1   128 5   216 1   128 5   216 1   127 5   212 1   127 5   212 1   128 5   209 1   128 5   209 1   130 5   207 1   130 5   207 1   134 5   
                                           206 1   134 5   206 1   137 5   207 1   137 5   207 1   139 5   209 1   139 5   209 1   140 5   212 1   7   255 120 5   212 1   147 5   212 1   7   255 134 5   199 1   134 5   226 1   7   255 140 5   40  1   139 5   43  1   139 5   43  1   137 5   45  1   
                                           137 5   45  1   134 5   46  1   134 5   46  1   130 5   45  1   130 5   45  1   128 5   43  1   128 5   43  1   127 5   40  1   127 5   40  1   128 5   36  1   128 5   36  1   130 5   34  1   130 5   34  1   134 5   33  1   134 5   33  1   137 5   34  1   
                                           137 5   34  1   139 5   36  1   139 5   36  1   140 5   40  1   7   255 120 5   40  1   147 5   40  1   7   255 134 5   26  1   134 5   53  1   7   255 44  6   40  1   43  6   43  1   43  6   43  1   41  6   45  1   41  6   45  1   37  6   46  1   37  6   
                                           46  1   34  6   45  1   34  6   45  1   31  6   43  1   31  6   43  1   31  6   40  1   31  6   40  1   31  6   36  1   31  6   36  1   34  6   34  1   34  6   34  1   37  6   33  1   37  6   33  1   41  6   34  1   41  6   34  1   43  6   36  1   43  6   
                                           36  1   44  6   40  1   7   255 24  6   40  1   51  6   40  1   7   255 37  6   26  1   37  6   53  1   7   255 44  6   212 1   43  6   216 1   43  6   216 1   41  6   218 1   41  6   218 1   37  6   219 1   37  6   219 1   34  6   218 1   34  6   218 1   
                                           31  6   216 1   31  6   216 1   31  6   212 1   31  6   212 1   31  6   209 1   31  6   209 1   34  6   207 1   34  6   207 1   37  6   206 1   37  6   206 1   41  6   207 1   41  6   207 1   43  6   209 1   43  6   209 1   44  6   212 1   7   255 24  6   
                                           212 1   51  6   212 1   7   255 37  6   199 1   37  6   226 1   7   255 246 1   40  1   245 1   43  1   245 1   43  1   242 1   45  1   242 1   45  1   239 1   46  1   239 1   46  1   236 1   45  1   236 1   45  1   233 1   43  1   233 1   43  1   232 1   
                                           40  1   232 1   40  1   233 1   36  1   233 1   36  1   236 1   34  1   236 1   34  1   239 1   33  1   239 1   33  1   242 1   34  1   242 1   34  1   245 1   36  1   245 1   36  1   246 1   40  1   7   255 226 1   40  1   252 1   40  1   7   255 239 1   
                                           26  1   239 1   53  1   7   255 246 1   212 1   245 1   216 1   245 1   216 1   242 1   218 1   242 1   218 1   239 1   219 1   239 1   219 1   236 1   218 1   236 1   218 1   233 1   216 1   233 1   216 1   232 1   212 1   232 1   212 1   233 1   209 1   
                                           233 1   209 1   236 1   207 1   236 1   207 1   239 1   206 1   239 1   206 1   242 1   207 1   242 1   207 1   245 1   209 1   245 1   209 1   246 1   212 1   7   255 226 1   212 1   252 1   212 1   7   255 239 1   199 1   239 1   226 1   7   255 76  2   
                                           126 1   75  2   129 1   75  2   129 1   73  2   132 1   73  2   132 1   70  2   133 1   70  2   133 1   66  2   132 1   66  2   132 1   64  2   129 1   64  2   129 1   63  2   126 1   63  2   126 1   64  2   123 1   64  2   123 1   66  2   120 1   66  2   
                                           120 1   70  2   119 1   70  2   119 1   73  2   120 1   73  2   120 1   75  2   123 1   75  2   123 1   76  2   126 1   7   255 56  2   126 1   83  2   126 1   7   255 70  2   113 1   70  2   139 1   7   255 43  0   40  1   66  1   40  1   66  1   40  1   
                                           66  1   92  1   66  1   92  1   113 2   92  1   113 2   92  1   113 2   160 1   113 2   160 1   66  1   160 1   66  1   160 1   66  1   212 1   66  1   212 1   43  0   212 1   43  0   212 1   43  0   40  1   7   255 43  0   40  1   43  0   40  1   7   255 
                                           43  0   40  1   43  0   40  1   7   255 43  0   40  1   43  0   40  1   7   255 87  2   143 1   85  2   145 1   85  2   145 1   82  2   147 1   82  2   147 1   80  2   149 1   80  2   149 1   77  2   150 1   77  2   150 1   74  2   150 1   74  2   150 1   
                                           71  2   151 1   71  2   151 1   68  2   151 1   68  2   151 1   65  2   150 1   65  2   150 1   62  2   150 1   62  2   150 1   59  2   149 1   59  2   149 1   57  2   147 1   57  2   147 1   54  2   145 1   54  2   145 1   52  2   143 1   52  2   143 1   
                                           50  2   141 1   50  2   141 1   48  2   139 1   48  2   139 1   47  2   136 1   47  2   136 1   46  2   133 1   46  2   133 1   45  2   130 1   45  2   130 1   45  2   127 1   45  2   127 1   45  2   125 1   45  2   125 1   45  2   122 1   45  2   122 1   
                                           46  2   119 1   46  2   119 1   47  2   116 1   47  2   116 1   48  2   113 1   48  2   113 1   50  2   111 1   50  2   111 1   52  2   109 1   52  2   109 1   54  2   107 1   54  2   107 1   57  2   105 1   57  2   105 1   59  2   103 1   59  2   103 1   
                                           62  2   102 1   62  2   102 1   65  2   102 1   65  2   102 1   68  2   101 1   68  2   101 1   71  2   101 1   71  2   101 1   74  2   102 1   74  2   102 1   77  2   102 1   77  2   102 1   80  2   103 1   80  2   103 1   82  2   105 1   82  2   105 1   
                                           85  2   107 1   85  2   107 1   87  2   109 1   7   255 87  2   109 1   87  2   143 1   7   255 245 1   76  1   245 1   88  1   245 1   88  1   0   2   92  1   0   2   92  1   53  2   92  1   53  2   92  1   64  2   88  1   64  2   88  1   64  2   76  1   
                                           64  2   76  1   53  2   73  1   53  2   73  1   0   2   73  1   0   2   73  1   245 1   76  1   7   255 245 1   43  1   245 1   55  1   245 1   55  1   0   2   58  1   0   2   58  1   53  2   58  1   53  2   58  1   64  2   55  1   64  2   55  1   64  2   
                                           43  1   64  2   43  1   53  2   40  1   53  2   40  1   0   2   40  1   0   2   40  1   245 1   43  1   7   255 245 1   164 1   245 1   176 1   245 1   176 1   0   2   179 1   0   2   179 1   53  2   179 1   53  2   179 1   64  2   176 1   64  2   176 1   
                                           64  2   164 1   64  2   164 1   53  2   160 1   53  2   160 1   0   2   160 1   0   2   160 1   245 1   164 1   7   255 245 1   197 1   245 1   209 1   245 1   209 1   0   2   212 1   0   2   212 1   53  2   212 1   53  2   212 1   64  2   209 1   64  2   
                                           209 1   64  2   197 1   64  2   197 1   53  2   194 1   53  2   194 1   0   2   194 1   0   2   194 1   245 1   197 1   7   255 76  2   76  1   76  2   88  1   76  2   88  1   86  2   92  1   86  2   92  1   140 2   92  1   140 2   92  1   150 2   88  1   
                                           150 2   88  1   150 2   76  1   150 2   76  1   140 2   73  1   140 2   73  1   86  2   73  1   86  2   73  1   76  2   76  1   7   255 76  2   43  1   76  2   55  1   76  2   55  1   86  2   58  1   86  2   58  1   140 2   58  1   140 2   58  1   150 2   
                                           55  1   150 2   55  1   150 2   43  1   150 2   43  1   140 2   40  1   140 2   40  1   86  2   40  1   86  2   40  1   76  2   43  1   7   255 76  2   164 1   76  2   176 1   76  2   176 1   86  2   179 1   86  2   179 1   140 2   179 1   140 2   179 1   
                                           150 2   176 1   150 2   176 1   150 2   164 1   150 2   164 1   140 2   160 1   140 2   160 1   86  2   160 1   86  2   160 1   76  2   164 1   7   255 76  2   197 1   76  2   209 1   76  2   209 1   86  2   212 1   86  2   212 1   140 2   212 1   140 2   
                                           212 1   150 2   209 1   150 2   209 1   150 2   197 1   150 2   197 1   140 2   194 1   140 2   194 1   86  2   194 1   86  2   194 1   76  2   197 1   7   255 132 0   197 1   132 0   209 1   132 0   209 1   142 0   212 1   142 0   212 1   196 0   212 1   
                                           196 0   212 1   206 0   209 1   206 0   209 1   206 0   197 1   206 0   197 1   196 0   194 1   196 0   194 1   142 0   194 1   142 0   194 1   132 0   197 1   7   255 132 0   43  1   132 0   55  1   132 0   55  1   142 0   58  1   142 0   58  1   196 0   
                                           58  1   196 0   58  1   206 0   55  1   206 0   55  1   206 0   43  1   206 0   43  1   196 0   40  1   196 0   40  1   142 0   40  1   142 0   40  1   132 0   43  1   7   255 176 0   40  1   175 0   41  1   175 0   41  1   175 0   42  1   175 0   42  1   
                                           174 0   44  1   174 0   44  1   173 0   45  1   173 0   45  1   172 0   46  1   172 0   46  1   170 0   46  1   170 0   46  1   169 0   46  1   169 0   46  1   168 0   46  1   168 0   46  1   166 0   46  1   166 0   46  1   165 0   45  1   165 0   45  1   
                                           164 0   44  1   164 0   44  1   163 0   42  1   163 0   42  1   163 0   41  1   163 0   41  1   162 0   40  1   162 0   40  1   163 0   38  1   163 0   38  1   163 0   37  1   163 0   37  1   164 0   35  1   164 0   35  1   165 0   34  1   165 0   34  1   
                                           166 0   34  1   166 0   34  1   168 0   33  1   168 0   33  1   169 0   33  1   169 0   33  1   170 0   33  1   170 0   33  1   172 0   34  1   172 0   34  1   173 0   34  1   173 0   34  1   174 0   35  1   174 0   35  1   175 0   37  1   175 0   37  1   
                                           175 0   38  1   175 0   38  1   176 0   40  1   7   255 156 0   40  1   182 0   40  1   7   255 169 0   26  1   169 0   53  1   7   255 176 0   212 1   175 0   214 1   175 0   214 1   175 0   215 1   175 0   215 1   174 0   217 1   174 0   217 1   173 0   
                                           218 1   173 0   218 1   172 0   218 1   172 0   218 1   170 0   219 1   170 0   219 1   169 0   219 1   169 0   219 1   168 0   219 1   168 0   219 1   166 0   218 1   166 0   218 1   165 0   218 1   165 0   218 1   164 0   217 1   164 0   217 1   163 0   
                                           215 1   163 0   215 1   163 0   214 1   163 0   214 1   162 0   212 1   162 0   212 1   163 0   211 1   163 0   211 1   163 0   210 1   163 0   210 1   164 0   208 1   164 0   208 1   165 0   207 1   165 0   207 1   166 0   206 1   166 0   206 1   168 0   
                                           206 1   168 0   206 1   169 0   206 1   169 0   206 1   170 0   206 1   170 0   206 1   172 0   206 1   172 0   206 1   173 0   207 1   173 0   207 1   174 0   208 1   174 0   208 1   175 0   210 1   175 0   210 1   175 0   211 1   175 0   211 1   176 0   
                                           212 1   7   255 156 0   212 1   182 0   212 1   7   255 169 0   199 1   169 0   226 1   7   255 176 0   126 1   175 0   127 1   175 0   127 1   175 0   129 1   175 0   129 1   174 0   130 1   174 0   130 1   173 0   131 1   173 0   131 1   172 0   132 1   
                                           172 0   132 1   170 0   132 1   170 0   132 1   169 0   133 1   169 0   133 1   168 0   132 1   168 0   132 1   166 0   132 1   166 0   132 1   165 0   131 1   165 0   131 1   164 0   130 1   164 0   130 1   163 0   129 1   163 0   129 1   163 0   127 1   
                                           )) "a")
 (_WriteStream FILE (vl-list->string (list 163 0   127 1   162 0   126 1   162 0   126 1   163 0   125 1   163 0   125 1   163 0   123 1   163 0   123 1   164 0   122 1   164 0   122 1   165 0   121 1   165 0   121 1   166 0   120 1   166 0   120 1   168 0   120 1   168 0   120 1   169 0   119 1   
                                           169 0   119 1   170 0   120 1   170 0   120 1   172 0   120 1   172 0   120 1   173 0   121 1   173 0   121 1   174 0   122 1   174 0   122 1   175 0   123 1   175 0   123 1   175 0   125 1   175 0   125 1   176 0   126 1   7   255 156 0   126 1   182 0   
                                           126 1   7   255 169 0   113 1   169 0   139 1   7   255 76  2   212 1   76  2   214 1   76  2   214 1   76  2   215 1   76  2   215 1   75  2   217 1   75  2   217 1   74  2   218 1   74  2   218 1   73  2   218 1   73  2   218 1   71  2   219 1   71  2   
                                           219 1   70  2   219 1   70  2   219 1   68  2   219 1   68  2   219 1   67  2   218 1   67  2   218 1   65  2   218 1   65  2   218 1   64  2   217 1   64  2   217 1   64  2   215 1   64  2   215 1   63  2   214 1   63  2   214 1   63  2   212 1   63  2   
                                           212 1   63  2   211 1   63  2   211 1   64  2   210 1   64  2   210 1   64  2   208 1   64  2   208 1   65  2   207 1   65  2   207 1   67  2   206 1   67  2   206 1   68  2   206 1   68  2   206 1   70  2   206 1   70  2   206 1   71  2   206 1   71  2   
                                           206 1   73  2   206 1   73  2   206 1   74  2   207 1   74  2   207 1   75  2   208 1   75  2   208 1   76  2   210 1   76  2   210 1   76  2   211 1   76  2   211 1   76  2   212 1   7   255 56  2   212 1   83  2   212 1   7   255 70  2   199 1   70  2   
                                           226 1   7   255 76  2   126 1   76  2   127 1   76  2   127 1   76  2   129 1   76  2   129 1   75  2   130 1   75  2   130 1   74  2   131 1   74  2   131 1   73  2   132 1   73  2   132 1   71  2   132 1   71  2   132 1   70  2   133 1   70  2   133 1   
                                           68  2   132 1   68  2   132 1   67  2   132 1   67  2   132 1   65  2   131 1   65  2   131 1   64  2   130 1   64  2   130 1   64  2   129 1   64  2   129 1   63  2   127 1   63  2   127 1   63  2   126 1   63  2   126 1   63  2   125 1   63  2   125 1   
                                           64  2   123 1   64  2   123 1   64  2   122 1   64  2   122 1   65  2   121 1   65  2   121 1   67  2   120 1   67  2   120 1   68  2   120 1   68  2   120 1   70  2   119 1   70  2   119 1   71  2   120 1   71  2   120 1   73  2   120 1   73  2   120 1   
                                           74  2   121 1   74  2   121 1   75  2   122 1   75  2   122 1   76  2   123 1   76  2   123 1   76  2   125 1   76  2   125 1   76  2   126 1   7   255 56  2   126 1   83  2   126 1   7   255 70  2   113 1   70  2   139 1   7   255 49  0   212 1   49  0   
                                           214 1   49  0   214 1   49  0   215 1   49  0   215 1   48  0   217 1   48  0   217 1   47  0   218 1   47  0   218 1   45  0   218 1   45  0   218 1   44  0   219 1   44  0   219 1   43  0   219 1   43  0   219 1   41  0   219 1   41  0   219 1   40  0   
                                           218 1   40  0   218 1   38  0   218 1   38  0   218 1   37  0   217 1   37  0   217 1   37  0   215 1   37  0   215 1   36  0   214 1   36  0   214 1   36  0   212 1   36  0   212 1   36  0   211 1   36  0   211 1   37  0   210 1   37  0   210 1   37  0   
                                           208 1   37  0   208 1   38  0   207 1   38  0   207 1   40  0   206 1   40  0   206 1   41  0   206 1   41  0   206 1   43  0   206 1   43  0   206 1   44  0   206 1   44  0   206 1   45  0   206 1   45  0   206 1   47  0   207 1   47  0   207 1   48  0   
                                           208 1   48  0   208 1   49  0   210 1   49  0   210 1   49  0   211 1   49  0   211 1   49  0   212 1   7   255 29  0   212 1   56  0   212 1   7   255 43  0   199 1   43  0   226 1   7   255 49  0   40  1   49  0   41  1   49  0   41  1   49  0   42  1   
                                           49  0   42  1   48  0   44  1   48  0   44  1   47  0   45  1   47  0   45  1   45  0   46  1   45  0   46  1   44  0   46  1   44  0   46  1   43  0   46  1   43  0   46  1   41  0   46  1   41  0   46  1   40  0   46  1   40  0   46  1   38  0   45  1   
                                           38  0   45  1   37  0   44  1   37  0   44  1   37  0   42  1   37  0   42  1   36  0   41  1   36  0   41  1   36  0   40  1   36  0   40  1   36  0   38  1   36  0   38  1   37  0   37  1   37  0   37  1   37  0   35  1   37  0   35  1   38  0   34  1   
                                           38  0   34  1   40  0   34  1   40  0   34  1   41  0   33  1   41  0   33  1   43  0   33  1   43  0   33  1   44  0   33  1   44  0   33  1   45  0   34  1   45  0   34  1   47  0   34  1   47  0   34  1   48  0   35  1   48  0   35  1   49  0   37  1   
                                           49  0   37  1   49  0   38  1   49  0   38  1   49  0   40  1   7   255 29  0   40  1   56  0   40  1   7   255 43  0   26  1   43  0   53  1   7   255 76  2   40  1   76  2   41  1   76  2   41  1   76  2   42  1   76  2   42  1   75  2   44  1   75  2   
                                           44  1   74  2   45  1   74  2   45  1   73  2   46  1   73  2   46  1   71  2   46  1   71  2   46  1   70  2   46  1   70  2   46  1   68  2   46  1   68  2   46  1   67  2   46  1   67  2   46  1   65  2   45  1   65  2   45  1   64  2   44  1   64  2   
                                           44  1   64  2   42  1   64  2   42  1   63  2   41  1   63  2   41  1   63  2   40  1   63  2   40  1   63  2   38  1   63  2   38  1   64  2   37  1   64  2   37  1   64  2   35  1   64  2   35  1   65  2   34  1   65  2   34  1   67  2   34  1   67  2   
                                           34  1   68  2   33  1   68  2   33  1   70  2   33  1   70  2   33  1   71  2   33  1   71  2   33  1   73  2   34  1   73  2   34  1   74  2   34  1   74  2   34  1   75  2   35  1   75  2   35  1   76  2   37  1   76  2   37  1   76  2   38  1   76  2   
                                           38  1   76  2   40  1   7   255 56  2   40  1   83  2   40  1   7   255 70  2   26  1   70  2   53  1   0   252 65  117 116 111 67  65  68  32  83  108 105 100 101 13  10  26  0   86  2   73  6   247 2   97  120 67  1   2   0   52  18  51  255 51  255 243 
                                           0   155 0   59  5   155 0   59  5   155 0   59  5   46  2   59  5   46  2   243 0   46  2   243 0   46  2   243 0   155 0   7   255 7   255 243 0   155 0   59  5   155 0   59  5   155 0   59  5   46  2   59  5   46  2   243 0   46  2   243 0   46  2   243 
                                           0   155 0   7   255 243 0   155 0   243 0   155 0   7   255 243 0   155 0   243 0   155 0   7   255 243 0   155 0   243 0   155 0   7   255 223 3   189 0   223 3   208 0   223 3   208 0   240 3   214 0   240 3   214 0   70  4   214 0   70  4   214 0   87  
                                           4   208 0   87  4   208 0   87  4   189 0   87  4   189 0   70  4   184 0   70  4   184 0   240 3   184 0   240 3   184 0   223 3   189 0   7   255 223 3   249 1   223 3   12  2   223 3   12  2   240 3   18  2   240 3   18  2   70  4   18  2   70  4   18  
                                           2   87  4   12  2   87  4   12  2   87  4   249 1   87  4   249 1   70  4   244 1   70  4   244 1   240 3   244 1   240 3   244 1   223 3   249 1   7   255 166 1   101 1   164 1   105 1   164 1   105 1   160 1   106 1   160 1   106 1   156 1   105 1   156 
                                           1   105 1   154 1   101 1   154 1   101 1   156 1   97  1   156 1   97  1   160 1   95  1   160 1   95  1   164 1   97  1   164 1   97  1   166 1   101 1   7   255 149 1   101 1   172 1   101 1   7   255 160 1   89  1   160 1   112 1   7   255 166 1   18  
                                           2   164 1   22  2   164 1   22  2   160 1   23  2   160 1   23  2   156 1   22  2   156 1   22  2   154 1   18  2   154 1   18  2   156 1   14  2   156 1   14  2   160 1   12  2   160 1   12  2   164 1   14  2   164 1   14  2   166 1   18  2   7   255 149 
                                           1   18  2   172 1   18  2   7   255 160 1   6   2   160 1   29  2   7   255 166 1   184 0   164 1   188 0   164 1   188 0   160 1   189 0   160 1   189 0   156 1   188 0   156 1   188 0   154 1   184 0   154 1   184 0   156 1   180 0   156 1   180 0   160 
                                           1   178 0   160 1   178 0   164 1   180 0   164 1   180 0   166 1   184 0   7   255 149 1   184 0   172 1   184 0   7   255 160 1   172 0   160 1   195 0   7   255 249 0   46  2   247 0   51  2   247 0   51  2   243 0   52  2   243 0   52  2   239 0   51  
                                           2   239 0   51  2   237 0   46  2   237 0   46  2   239 0   42  2   239 0   42  2   243 0   41  2   243 0   41  2   247 0   42  2   247 0   42  2   249 0   46  2   7   255 231 0   46  2   255 0   46  2   7   255 243 0   35  2   243 0   58  2   7   255 249 
                                           0   155 0   247 0   159 0   247 0   159 0   243 0   161 0   243 0   161 0   239 0   159 0   239 0   159 0   237 0   155 0   237 0   155 0   239 0   151 0   239 0   151 0   243 0   149 0   243 0   149 0   247 0   151 0   247 0   151 0   249 0   155 0   7   
                                           255 231 0   155 0   255 0   155 0   7   255 243 0   143 0   243 0   166 0   7   255 33  4   184 0   31  4   188 0   31  4   188 0   27  4   189 0   27  4   189 0   23  4   188 0   23  4   188 0   21  4   184 0   21  4   184 0   23  4   180 0   23  4   180 
                                           0   27  4   178 0   27  4   178 0   31  4   180 0   31  4   180 0   33  4   184 0   7   255 15  4   184 0   38  4   184 0   7   255 27  4   172 0   27  4   195 0   7   255 33  4   18  2   31  4   22  2   31  4   22  2   27  4   23  2   27  4   23  2   23  
                                           4   22  2   23  4   22  2   21  4   18  2   21  4   18  2   23  4   14  2   23  4   14  2   27  4   12  2   27  4   12  2   31  4   14  2   31  4   14  2   33  4   18  2   7   255 15  4   18  2   38  4   18  2   7   255 27  4   6   2   27  4   29  2   7   
                                           255 65  5   46  2   64  5   51  2   64  5   51  2   59  5   52  2   59  5   52  2   55  5   51  2   55  5   51  2   54  5   46  2   54  5   46  2   55  5   42  2   55  5   42  2   59  5   41  2   59  5   41  2   64  5   42  2   64  5   42  2   65  5   46  
                                           2   7   255 48  5   46  2   71  5   46  2   7   255 59  5   35  2   59  5   58  2   7   255 65  5   155 0   64  5   159 0   64  5   159 0   59  5   161 0   59  5   161 0   55  5   159 0   55  5   159 0   54  5   155 0   54  5   155 0   55  5   151 0   55  
                                           5   151 0   59  5   149 0   59  5   149 0   64  5   151 0   64  5   151 0   65  5   155 0   7   255 48  5   155 0   71  5   155 0   7   255 59  5   143 0   59  5   166 0   7   255 65  5   101 1   64  5   105 1   64  5   105 1   59  5   106 1   59  5   106 
                                           1   55  5   105 1   55  5   105 1   54  5   101 1   54  5   101 1   55  5   97  1   55  5   97  1   59  5   95  1   59  5   95  1   64  5   97  1   64  5   97  1   65  5   101 1   7   255 48  5   101 1   71  5   101 1   7   255 59  5   89  1   59  5   112 
                                           1   7   255 100 1   189 0   100 1   208 0   100 1   208 0   117 1   214 0   117 1   214 0   203 1   214 0   203 1   214 0   220 1   208 0   220 1   208 0   220 1   189 0   220 1   189 0   203 1   184 0   203 1   184 0   117 1   184 0   117 1   184 0   100 
                                           1   189 0   7   255 100 1   249 1   100 1   12  2   100 1   12  2   117 1   18  2   117 1   18  2   203 1   18  2   203 1   18  2   220 1   12  2   220 1   12  2   220 1   249 1   220 1   249 1   203 1   244 1   203 1   244 1   117 1   244 1   117 1   244 
                                           1   100 1   249 1   0   252 65  117 116 111 67  65  68  32  83  108 105 100 101 13  10  26  0   86  2   106 6   234 2   99  219 79  1   2   0   52  18  7   255 7   255 36  0   6   1   44  3   6   1   44  3   6   1   44  3   228 1   44  3   228 1   36  0   
                                           228 1   36  0   228 1   36  0   6   1   7   255 36  0   6   1   36  0   6   1   7   255 36  0   6   1   36  0   6   1   7   255 44  3   117 1   95  3   117 1   7   255 104 3   117 1   103 3   121 1   103 3   121 1   102 3   123 1   102 3   123 1   99  3   
                                           125 1   99  3   125 1   95  3   126 1   95  3   126 1   92  3   125 1   92  3   125 1   89  3   123 1   89  3   123 1   87  3   121 1   87  3   121 1   87  3   117 1   87  3   117 1   87  3   114 1   87  3   114 1   89  3   111 1   89  3   111 1   92  3   
                                           109 1   92  3   109 1   95  3   109 1   95  3   109 1   99  3   109 1   99  3   109 1   102 3   111 1   102 3   111 1   103 3   114 1   103 3   114 1   104 3   117 1   7   255 129 2   11  1   129 2   24  1   129 2   24  1   141 2   28  1   141 2   28  1   
                                           204 2   28  1   204 2   28  1   216 2   24  1   216 2   24  1   216 2   11  1   216 2   11  1   204 2   6   1   204 2   6   1   141 2   6   1   141 2   6   1   129 2   11  1   7   255 129 2   210 1   129 2   224 1   129 2   224 1   141 2   228 1   141 2   
                                           228 1   204 2   228 1   204 2   228 1   216 2   224 1   216 2   224 1   216 2   210 1   216 2   210 1   204 2   206 1   204 2   206 1   141 2   206 1   141 2   206 1   129 2   210 1   7   255 206 0   210 1   206 0   224 1   206 0   224 1   218 0   228 1   
                                           218 0   228 1   25  1   228 1   25  1   228 1   37  1   224 1   37  1   224 1   37  1   210 1   37  1   210 1   25  1   206 1   25  1   206 1   218 0   206 1   218 0   206 1   206 0   210 1   7   255 45  0   228 1   44  0   231 1   44  0   231 1   43  0   
                                           234 1   43  0   234 1   40  0   236 1   40  0   236 1   36  0   236 1   36  0   236 1   33  0   236 1   33  0   236 1   30  0   234 1   30  0   234 1   29  0   231 1   29  0   231 1   28  0   228 1   28  0   228 1   29  0   225 1   29  0   225 1   30  0   
                                           222 1   30  0   222 1   33  0   220 1   33  0   220 1   36  0   219 1   36  0   219 1   40  0   220 1   40  0   220 1   43  0   222 1   43  0   222 1   44  0   225 1   44  0   225 1   45  0   228 1   7   255 19  0   228 1   54  0   228 1   7   255 36  0   
                                           211 1   36  0   245 1   7   255 45  0   6   1   44  0   10  1   44  0   10  1   43  0   12  1   43  0   12  1   40  0   14  1   40  0   14  1   36  0   15  1   36  0   15  1   33  0   14  1   33  0   14  1   30  0   12  1   30  0   12  1   29  0   10  1   
                                           29  0   10  1   28  0   6   1   28  0   6   1   29  0   3   1   29  0   3   1   30  0   0   1   30  0   0   1   33  0   255 0   33  0   255 0   36  0   254 0   36  0   254 0   40  0   255 0   40  0   255 0   43  0   0   1   43  0   0   1   44  0   3   1   
                                           44  0   3   1   45  0   6   1   7   255 19  0   6   1   54  0   6   1   7   255 36  0   245 0   36  0   23  1   7   255 53  3   6   1   52  3   10  1   52  3   10  1   50  3   12  1   50  3   12  1   48  3   14  1   48  3   14  1   44  3   15  1   44  3   
                                           15  1   41  3   14  1   41  3   14  1   38  3   12  1   38  3   12  1   36  3   10  1   36  3   10  1   36  3   6   1   36  3   6   1   36  3   3   1   36  3   3   1   38  3   0   1   38  3   0   1   41  3   255 0   41  3   255 0   44  3   254 0   44  3   
                                           254 0   48  3   255 0   48  3   255 0   50  3   0   1   50  3   0   1   52  3   3   1   52  3   3   1   53  3   6   1   7   255 27  3   6   1   61  3   6   1   7   255 44  3   245 0   44  3   23  1   7   255 53  3   228 1   52  3   231 1   52  3   231 1   
                                           50  3   234 1   50  3   234 1   48  3   236 1   48  3   236 1   44  3   236 1   44  3   236 1   41  3   236 1   41  3   236 1   38  3   234 1   38  3   234 1   36  3   231 1   36  3   231 1   36  3   228 1   36  3   228 1   36  3   225 1   36  3   225 1   
                                           38  3   222 1   38  3   222 1   41  3   220 1   41  3   220 1   44  3   219 1   44  3   219 1   48  3   220 1   48  3   220 1   50  3   222 1   50  3   222 1   52  3   225 1   52  3   225 1   53  3   228 1   7   255 27  3   228 1   61  3   228 1   7   255 
                                           44  3   211 1   44  3   245 1   7   255 181 2   228 1   180 2   231 1   180 2   231 1   178 2   234 1   178 2   234 1   176 2   236 1   176 2   236 1   172 2   236 1   172 2   236 1   169 2   236 1   169 2   236 1   166 2   234 1   166 2   234 1   165 2   
                                           231 1   165 2   231 1   164 2   228 1   164 2   228 1   165 2   225 1   165 2   225 1   166 2   222 1   166 2   222 1   169 2   220 1   169 2   220 1   172 2   219 1   172 2   219 1   176 2   220 1   176 2   220 1   178 2   222 1   178 2   222 1   180 2   
                                           225 1   180 2   225 1   181 2   228 1   7   255 155 2   228 1   189 2   228 1   7   255 172 2   211 1   172 2   245 1   7   255 181 2   6   1   180 2   10  1   180 2   10  1   178 2   12  1   178 2   12  1   176 2   14  1   176 2   14  1   172 2   15  1   
                                           172 2   15  1   169 2   14  1   169 2   14  1   166 2   12  1   166 2   12  1   165 2   10  1   165 2   10  1   164 2   6   1   164 2   6   1   165 2   3   1   165 2   3   1   166 2   0   1   166 2   0   1   169 2   255 0   169 2   255 0   172 2   254 0   
                                           172 2   254 0   176 2   255 0   176 2   255 0   178 2   0   1   178 2   0   1   180 2   3   1   180 2   3   1   181 2   6   1   7   255 155 2   6   1   189 2   6   1   7   255 172 2   245 0   172 2   23  1   7   255 2   1   6   1   2   1   10  1   2   1   
                                           10  1   0   1   12  1   0   1   12  1   253 0   14  1   253 0   14  1   250 0   15  1   250 0   15  1   246 0   14  1   246 0   14  1   244 0   12  1   244 0   12  1   242 0   10  1   242 0   10  1   241 0   6   1   241 0   6   1   242 0   3   1   242 0   
                                           3   1   244 0   0   1   244 0   0   1   246 0   255 0   246 0   255 0   250 0   254 0   250 0   254 0   253 0   255 0   253 0   255 0   0   1   0   1   0   1   0   1   2   1   3   1   2   1   3   1   2   1   6   1   7   255 233 0   6   1   11  1   6   1   
                                           )) "a")
 (_WriteStream FILE (vl-list->string (list 7   255 250 0   245 0   250 0   23  1   7   255 2   1   228 1   2   1   231 1   2   1   231 1   0   1   234 1   0   1   234 1   253 0   236 1   253 0   236 1   250 0   236 1   250 0   236 1   246 0   236 1   246 0   236 1   244 0   234 1   244 0   234 1   
                                           242 0   231 1   242 0   231 1   241 0   228 1   241 0   228 1   242 0   225 1   242 0   225 1   244 0   222 1   244 0   222 1   246 0   220 1   246 0   220 1   250 0   219 1   250 0   219 1   253 0   220 1   253 0   220 1   0   1   222 1   0   1   222 1   
                                           2   1   225 1   2   1   225 1   2   1   228 1   7   255 233 0   228 1   11  1   228 1   7   255 250 0   211 1   250 0   245 1   7   255 2   1   118 1   2   1   122 1   2   1   122 1   0   1   124 1   0   1   124 1   253 0   126 1   253 0   126 1   250 0   
                                           127 1   250 0   127 1   246 0   126 1   246 0   126 1   244 0   124 1   244 0   124 1   242 0   122 1   242 0   122 1   241 0   118 1   241 0   118 1   242 0   115 1   242 0   115 1   244 0   112 1   244 0   112 1   246 0   110 1   246 0   110 1   250 0   
                                           110 1   250 0   110 1   253 0   110 1   253 0   110 1   0   1   112 1   0   1   112 1   2   1   115 1   2   1   115 1   2   1   118 1   7   255 233 0   118 1   11  1   118 1   7   255 250 0   101 1   250 0   135 1   7   255 104 3   117 1   103 3   120 1   
                                           103 3   120 1   102 3   123 1   102 3   123 1   99  3   125 1   99  3   125 1   95  3   126 1   95  3   126 1   92  3   125 1   92  3   125 1   89  3   123 1   89  3   123 1   88  3   120 1   88  3   120 1   87  3   117 1   87  3   117 1   88  3   114 1   
                                           88  3   114 1   89  3   111 1   89  3   111 1   92  3   109 1   92  3   109 1   95  3   109 1   95  3   109 1   99  3   109 1   99  3   109 1   102 3   111 1   102 3   111 1   103 3   114 1   103 3   114 1   104 3   117 1   7   255 78  3   117 1   113 3   
                                           117 1   7   255 95  3   100 1   95  3   134 1   7   255 206 0   11  1   206 0   24  1   206 0   24  1   218 0   28  1   218 0   28  1   25  1   28  1   25  1   28  1   37  1   24  1   37  1   24  1   37  1   11  1   37  1   11  1   25  1   6   1   25  1   
                                           6   1   218 0   6   1   218 0   6   1   206 0   11  1   7   255 147 3   6   1   69  6   6   1   69  6   6   1   69  6   228 1   69  6   228 1   147 3   228 1   147 3   228 1   147 3   6   1   7   255 147 3   6   1   147 3   6   1   7   255 147 3   6   1   
                                           147 3   6   1   7   255 95  3   117 1   147 3   117 1   7   255 110 3   117 1   110 3   122 1   110 3   122 1   107 3   126 1   107 3   126 1   104 3   129 1   104 3   129 1   100 3   131 1   100 3   131 1   95  3   132 1   95  3   132 1   91  3   131 1   
                                           91  3   131 1   87  3   129 1   87  3   129 1   84  3   126 1   84  3   126 1   81  3   122 1   81  3   122 1   81  3   117 1   81  3   117 1   81  3   113 1   81  3   113 1   84  3   109 1   84  3   109 1   87  3   105 1   87  3   105 1   91  3   103 1   
                                           91  3   103 1   95  3   102 1   95  3   102 1   100 3   103 1   100 3   103 1   104 3   105 1   104 3   105 1   107 3   109 1   107 3   109 1   110 3   113 1   110 3   113 1   110 3   117 1   7   255 35  5   11  1   35  5   24  1   35  5   24  1   47  5   
                                           28  1   47  5   28  1   109 5   28  1   109 5   28  1   121 5   24  1   121 5   24  1   121 5   11  1   121 5   11  1   109 5   6   1   109 5   6   1   47  5   6   1   47  5   6   1   35  5   11  1   7   255 35  5   210 1   35  5   224 1   35  5   224 1   
                                           47  5   228 1   47  5   228 1   109 5   228 1   109 5   228 1   121 5   224 1   121 5   224 1   121 5   210 1   121 5   210 1   109 5   206 1   109 5   206 1   47  5   206 1   47  5   206 1   35  5   210 1   7   255 104 3   117 1   103 3   120 1   103 3   
                                           120 1   102 3   123 1   102 3   123 1   99  3   125 1   99  3   125 1   95  3   126 1   95  3   126 1   92  3   125 1   92  3   125 1   89  3   123 1   89  3   123 1   88  3   120 1   88  3   120 1   87  3   117 1   87  3   117 1   88  3   114 1   88  3   
                                           114 1   89  3   111 1   89  3   111 1   92  3   109 1   92  3   109 1   95  3   109 1   95  3   109 1   99  3   109 1   99  3   109 1   102 3   111 1   102 3   111 1   103 3   114 1   103 3   114 1   104 3   117 1   7   255 78  3   117 1   113 3   117 1   
                                           7   255 95  3   100 1   95  3   134 1   7   255 155 3   6   1   155 3   10  1   155 3   10  1   153 3   12  1   153 3   12  1   150 3   14  1   150 3   14  1   147 3   15  1   147 3   15  1   143 3   14  1   143 3   14  1   141 3   12  1   141 3   12  1   
                                           139 3   10  1   139 3   10  1   138 3   6   1   138 3   6   1   139 3   3   1   139 3   3   1   141 3   0   1   141 3   0   1   143 3   255 0   143 3   255 0   147 3   254 0   147 3   254 0   150 3   255 0   150 3   255 0   153 3   0   1   153 3   0   1   
                                           155 3   3   1   155 3   3   1   155 3   6   1   7   255 130 3   6   1   164 3   6   1   7   255 147 3   245 0   147 3   23  1   7   255 155 3   228 1   155 3   231 1   155 3   231 1   153 3   234 1   153 3   234 1   150 3   236 1   150 3   236 1   147 3   
                                           236 1   147 3   236 1   143 3   236 1   143 3   236 1   141 3   234 1   141 3   234 1   139 3   231 1   139 3   231 1   138 3   228 1   138 3   228 1   139 3   225 1   139 3   225 1   141 3   222 1   141 3   222 1   143 3   220 1   143 3   220 1   147 3   
                                           219 1   147 3   219 1   150 3   220 1   150 3   220 1   153 3   222 1   153 3   222 1   155 3   225 1   155 3   225 1   155 3   228 1   7   255 130 3   228 1   164 3   228 1   7   255 147 3   211 1   147 3   245 1   7   255 78  6   228 1   77  6   231 1   
                                           77  6   231 1   75  6   234 1   75  6   234 1   72  6   236 1   72  6   236 1   69  6   236 1   69  6   236 1   66  6   236 1   66  6   236 1   63  6   234 1   63  6   234 1   61  6   231 1   61  6   231 1   61  6   228 1   61  6   228 1   61  6   225 1   
                                           61  6   225 1   63  6   222 1   63  6   222 1   66  6   220 1   66  6   220 1   69  6   219 1   69  6   219 1   72  6   220 1   72  6   220 1   75  6   222 1   75  6   222 1   77  6   225 1   77  6   225 1   78  6   228 1   7   255 52  6   228 1   86  6   
                                           228 1   7   255 69  6   211 1   69  6   245 1   7   255 78  6   6   1   77  6   10  1   77  6   10  1   75  6   12  1   75  6   12  1   72  6   14  1   72  6   14  1   69  6   15  1   69  6   15  1   66  6   14  1   66  6   14  1   63  6   12  1   63  6   
                                           12  1   61  6   10  1   61  6   10  1   61  6   6   1   61  6   6   1   61  6   3   1   61  6   3   1   63  6   0   1   63  6   0   1   66  6   255 0   66  6   255 0   69  6   254 0   69  6   254 0   72  6   255 0   72  6   255 0   75  6   0   1   75  6   
                                           0   1   77  6   3   1   77  6   3   1   78  6   6   1   7   255 52  6   6   1   86  6   6   1   7   255 69  6   245 0   69  6   23  1   7   255 86  5   6   1   86  5   10  1   86  5   10  1   84  5   12  1   84  5   12  1   81  5   14  1   81  5   14  1   
                                           78  5   15  1   78  5   15  1   75  5   14  1   75  5   14  1   72  5   12  1   72  5   12  1   70  5   10  1   70  5   10  1   69  5   6   1   69  5   6   1   70  5   3   1   70  5   3   1   72  5   0   1   72  5   0   1   75  5   255 0   75  5   255 0   
                                           78  5   254 0   78  5   254 0   81  5   255 0   81  5   255 0   84  5   0   1   84  5   0   1   86  5   3   1   86  5   3   1   86  5   6   1   7   255 61  5   6   1   95  5   6   1   7   255 78  5   245 0   78  5   23  1   7   255 86  5   228 1   86  5   
                                           231 1   86  5   231 1   84  5   234 1   84  5   234 1   81  5   236 1   81  5   236 1   78  5   236 1   78  5   236 1   75  5   236 1   75  5   236 1   72  5   234 1   72  5   234 1   70  5   231 1   70  5   231 1   69  5   228 1   69  5   228 1   70  5   
                                           225 1   70  5   225 1   72  5   222 1   72  5   222 1   75  5   220 1   75  5   220 1   78  5   219 1   78  5   219 1   81  5   220 1   81  5   220 1   84  5   222 1   84  5   222 1   86  5   225 1   86  5   225 1   86  5   228 1   7   255 61  5   228 1   
                                           95  5   228 1   7   255 78  5   211 1   78  5   245 1   0   252 65  117 116 111 67  65  68  32  83  108 105 100 101 13  10  26  0   86  2   106 6   234 2   99  219 79  1   2   0   52  18  7   255 7   255 167 0   132 0   191 5   132 0   191 5   132 0   191 
                                           5   85  2   191 5   85  2   167 0   85  2   167 0   85  2   167 0   132 0   7   255 167 0   132 0   167 0   132 0   7   255 167 0   132 0   167 0   132 0   7   255 64  4   139 0   64  4   164 0   64  4   164 0   87  4   172 0   87  4   172 0   202 4   172 
                                           0   202 4   172 0   224 4   164 0   224 4   164 0   224 4   139 0   224 4   139 0   202 4   132 0   202 4   132 0   87  4   132 0   87  4   132 0   64  4   139 0   7   255 64  4   53  2   64  4   78  2   64  4   78  2   87  4   85  2   87  4   85  2   202 
                                           4   85  2   202 4   85  2   224 4   78  2   224 4   78  2   224 4   53  2   224 4   53  2   202 4   45  2   202 4   45  2   87  4   45  2   87  4   45  2   64  4   53  2   7   255 190 0   85  2   187 0   97  2   187 0   97  2   179 0   105 2   179 0   105 
                                           2   167 0   108 2   167 0   108 2   155 0   105 2   155 0   105 2   147 0   97  2   147 0   97  2   144 0   85  2   144 0   85  2   147 0   73  2   147 0   73  2   155 0   65  2   155 0   65  2   167 0   62  2   167 0   62  2   179 0   65  2   179 0   65  
                                           2   187 0   73  2   187 0   73  2   190 0   85  2   7   255 120 0   85  2   214 0   85  2   7   255 167 0   39  2   167 0   132 2   7   255 190 1   85  2   187 1   97  2   187 1   97  2   179 1   105 2   179 1   105 2   167 1   108 2   167 1   108 2   155 
                                           1   105 2   155 1   105 2   147 1   97  2   147 1   97  2   144 1   85  2   144 1   85  2   147 1   73  2   147 1   73  2   155 1   65  2   155 1   65  2   167 1   62  2   167 1   62  2   179 1   65  2   179 1   65  2   187 1   73  2   187 1   73  2   190 
                                           1   85  2   7   255 121 1   85  2   214 1   85  2   7   255 167 1   39  2   167 1   132 2   7   255 167 4   85  2   164 4   97  2   164 4   97  2   156 4   105 2   156 4   105 2   144 4   108 2   144 4   108 2   132 4   105 2   132 4   105 2   124 4   97  
                                           2   124 4   97  2   121 4   85  2   121 4   85  2   124 4   73  2   124 4   73  2   132 4   65  2   132 4   65  2   144 4   62  2   144 4   62  2   156 4   65  2   156 4   65  2   164 4   73  2   164 4   73  2   167 4   85  2   7   255 98  4   85  2   191 
                                           4   85  2   7   255 144 4   39  2   144 4   132 2   7   255 214 5   85  2   211 5   97  2   211 5   97  2   202 5   105 2   202 5   105 2   191 5   108 2   191 5   108 2   179 5   105 2   179 5   105 2   171 5   97  2   171 5   97  2   168 5   85  2   168 
                                           5   85  2   171 5   73  2   171 5   73  2   179 5   65  2   179 5   65  2   191 5   62  2   191 5   62  2   202 5   65  2   202 5   65  2   211 5   73  2   211 5   73  2   214 5   85  2   7   255 144 5   85  2   237 5   85  2   7   255 191 5   39  2   191 
                                           5   132 2   7   255 214 5   132 0   211 5   143 0   211 5   143 0   202 5   152 0   202 5   152 0   191 5   155 0   191 5   155 0   179 5   152 0   179 5   152 0   171 5   143 0   171 5   143 0   168 5   132 0   168 5   132 0   171 5   120 0   171 5   120 
                                           0   179 5   112 0   179 5   112 0   191 5   109 0   191 5   109 0   202 5   112 0   202 5   112 0   211 5   120 0   211 5   120 0   214 5   132 0   7   255 144 5   132 0   237 5   132 0   7   255 191 5   85  0   191 5   178 0   7   255 167 4   132 0   164 
                                           4   143 0   164 4   143 0   156 4   152 0   156 4   152 0   144 4   155 0   144 4   155 0   132 4   152 0   132 4   152 0   124 4   143 0   124 4   143 0   121 4   132 0   121 4   132 0   124 4   120 0   124 4   120 0   132 4   112 0   132 4   112 0   144 
                                           4   109 0   144 4   109 0   156 4   112 0   156 4   112 0   164 4   120 0   164 4   120 0   167 4   132 0   7   255 98  4   132 0   191 4   132 0   7   255 144 4   85  0   144 4   178 0   7   255 190 1   132 0   187 1   143 0   187 1   143 0   179 1   152 
                                           0   179 1   152 0   167 1   155 0   167 1   155 0   155 1   152 0   155 1   152 0   147 1   143 0   147 1   143 0   144 1   132 0   144 1   132 0   147 1   120 0   147 1   120 0   155 1   112 0   155 1   112 0   167 1   109 0   167 1   109 0   179 1   112 
                                           0   179 1   112 0   187 1   120 0   187 1   120 0   190 1   132 0   7   255 121 1   132 0   214 1   132 0   7   255 167 1   85  0   167 1   178 0   7   255 190 0   132 0   187 0   143 0   187 0   143 0   179 0   152 0   179 0   152 0   167 0   155 0   167 
                                           0   155 0   155 0   152 0   155 0   152 0   147 0   143 0   147 0   143 0   144 0   132 0   144 0   132 0   147 0   120 0   147 0   120 0   155 0   112 0   155 0   112 0   167 0   109 0   167 0   109 0   179 0   112 0   179 0   112 0   187 0   120 0   187 
                                           0   120 0   190 0   132 0   7   255 120 0   132 0   214 0   132 0   7   255 167 0   85  0   167 0   178 0   7   255 190 1   108 1   187 1   120 1   187 1   120 1   179 1   129 1   179 1   129 1   167 1   132 1   167 1   132 1   155 1   129 1   155 1   129 
                                           1   147 1   120 1   147 1   120 1   144 1   108 1   144 1   108 1   147 1   97  1   147 1   97  1   155 1   88  1   155 1   88  1   167 1   85  1   167 1   85  1   179 1   88  1   179 1   88  1   187 1   97  1   187 1   97  1   190 1   108 1   7   255 121 
                                           1   108 1   214 1   108 1   7   255 167 1   62  1   167 1   155 1   7   255 87  1   139 0   87  1   164 0   87  1   164 0   110 1   172 0   110 1   172 0   225 1   172 0   225 1   172 0   247 1   164 0   247 1   164 0   247 1   139 0   247 1   139 0   225 
                                           1   132 0   225 1   132 0   110 1   132 0   110 1   132 0   87  1   139 0   7   255 87  1   53  2   87  1   78  2   87  1   78  2   110 1   85  2   110 1   85  2   225 1   85  2   225 1   85  2   247 1   78  2   247 1   78  2   247 1   53  2   247 1   53  
                                           2   225 1   45  2   225 1   45  2   110 1   45  2   110 1   45  2   87  1   53  2   0   252 65  117 116 111 67  65  68  32  83  108 105 100 101 13  10  26  0   86  2   106 6   234 2   99  219 79  1   2   0   52  18  51  255 51  255 43  0   206 0   57  6   
                                           206 0   57  6   206 0   57  6   24  2   57  6   24  2   43  0   24  2   43  0   24  2   43  0   206 0   7   255 7   255 43  0   206 0   57  6   206 0   57  6   206 0   57  6   24  2   57  6   24  2   43  0   24  2   43  0   24  2   43  0   206 0   7   255 
                                           43  0   206 0   43  0   206 0   7   255 43  0   206 0   43  0   206 0   7   255 28  4   14  1   28  4   34  1   28  4   34  1   46  4   41  1   46  4   41  1   139 4   41  1   139 4   41  1   157 4   34  1   157 4   34  1   157 4   14  1   157 4   14  1   
                                           139 4   8   1   139 4   8   1   46  4   8   1   46  4   8   1   28  4   14  1   7   255 28  4   212 0   28  4   232 0   28  4   232 0   46  4   238 0   46  4   238 0   139 4   238 0   139 4   238 0   157 4   232 0   157 4   232 0   157 4   212 0   157 4   
                                           212 0   139 4   206 0   139 4   206 0   46  4   206 0   46  4   206 0   28  4   212 0   7   255 28  4   196 1   28  4   216 1   28  4   216 1   46  4   222 1   46  4   222 1   139 4   222 1   139 4   222 1   157 4   216 1   157 4   216 1   157 4   196 1   
                                           157 4   196 1   139 4   190 1   139 4   190 1   46  4   190 1   46  4   190 1   28  4   196 1   7   255 28  4   254 1   28  4   18  2   28  4   18  2   46  4   24  2   46  4   24  2   139 4   24  2   139 4   24  2   157 4   18  2   157 4   18  2   157 4   
                                           254 1   157 4   254 1   139 4   248 1   139 4   248 1   46  4   248 1   46  4   248 1   28  4   254 1   7   255 193 4   14  1   193 4   34  1   193 4   34  1   211 4   41  1   211 4   41  1   48  5   41  1   48  5   41  1   66  5   34  1   66  5   34  1   
                                           66  5   14  1   66  5   14  1   48  5   8   1   48  5   8   1   211 4   8   1   211 4   8   1   193 4   14  1   7   255 193 4   212 0   193 4   232 0   193 4   232 0   211 4   238 0   211 4   238 0   48  5   238 0   48  5   238 0   66  5   232 0   66  5   
                                           232 0   66  5   212 0   66  5   212 0   48  5   206 0   48  5   206 0   211 4   206 0   211 4   206 0   193 4   212 0   7   255 193 4   196 1   193 4   216 1   193 4   216 1   211 4   222 1   211 4   222 1   48  5   222 1   48  5   222 1   66  5   216 1   
                                           66  5   216 1   66  5   196 1   66  5   196 1   48  5   190 1   48  5   190 1   211 4   190 1   211 4   190 1   193 4   196 1   7   255 193 4   254 1   193 4   18  2   193 4   18  2   211 4   24  2   211 4   24  2   48  5   24  2   48  5   24  2   66  5   
                                           18  2   66  5   18  2   66  5   254 1   66  5   254 1   48  5   248 1   48  5   248 1   211 4   248 1   211 4   248 1   193 4   254 1   7   255 207 0   254 1   207 0   18  2   207 0   18  2   225 0   24  2   225 0   24  2   62  1   24  2   62  1   24  2   
                                           80  1   18  2   80  1   18  2   80  1   254 1   80  1   254 1   62  1   248 1   62  1   248 1   225 0   248 1   225 0   248 1   207 0   254 1   7   255 207 0   212 0   207 0   232 0   207 0   232 0   225 0   238 0   225 0   238 0   62  1   238 0   62  1   
                                           )) "a")
 (_WriteStream FILE (vl-list->string (list 238 0   80  1   232 0   80  1   232 0   80  1   212 0   80  1   212 0   62  1   206 0   62  1   206 0   225 0   206 0   225 0   206 0   207 0   212 0   7   255 28  1   115 1   28  1   119 1   28  1   119 1   26  1   122 1   26  1   122 1   24  1   124 1   
                                           24  1   124 1   22  1   126 1   22  1   126 1   19  1   128 1   19  1   128 1   15  1   128 1   15  1   128 1   12  1   128 1   12  1   128 1   9   1   126 1   9   1   126 1   6   1   124 1   6   1   124 1   4   1   122 1   4   1   122 1   3   1   119 1   
                                           3   1   119 1   3   1   115 1   3   1   115 1   3   1   112 1   3   1   112 1   4   1   109 1   4   1   109 1   6   1   106 1   6   1   106 1   9   1   104 1   9   1   104 1   12  1   103 1   12  1   103 1   15  1   103 1   15  1   103 1   19  1   103 1   
                                           19  1   103 1   22  1   104 1   22  1   104 1   24  1   106 1   24  1   106 1   26  1   109 1   26  1   109 1   28  1   112 1   28  1   112 1   28  1   115 1   7   255 246 0   115 1   41  1   115 1   7   255 15  1   90  1   15  1   141 1   7   255 55  0   
                                           24  2   55  0   28  2   55  0   28  2   54  0   31  2   54  0   31  2   52  0   33  2   52  0   33  2   49  0   35  2   49  0   35  2   46  0   37  2   46  0   37  2   43  0   37  2   43  0   37  2   39  0   37  2   39  0   37  2   36  0   35  2   36  0   
                                           35  2   34  0   33  2   34  0   33  2   32  0   31  2   32  0   31  2   30  0   28  2   30  0   28  2   30  0   24  2   30  0   24  2   30  0   21  2   30  0   21  2   32  0   18  2   32  0   18  2   34  0   15  2   34  0   15  2   36  0   13  2   36  0   
                                           13  2   39  0   12  2   39  0   12  2   43  0   12  2   43  0   12  2   46  0   12  2   46  0   12  2   49  0   13  2   49  0   13  2   52  0   15  2   52  0   15  2   54  0   18  2   54  0   18  2   55  0   21  2   55  0   21  2   55  0   24  2   7   255 
                                           17  0   24  2   68  0   24  2   7   255 43  0   255 1   43  0   50  2   7   255 55  0   206 0   55  0   209 0   55  0   209 0   54  0   213 0   54  0   213 0   52  0   215 0   52  0   215 0   49  0   217 0   49  0   217 0   46  0   218 0   46  0   218 0   
                                           43  0   219 0   43  0   219 0   39  0   218 0   39  0   218 0   36  0   217 0   36  0   217 0   34  0   215 0   34  0   215 0   32  0   213 0   32  0   213 0   30  0   209 0   30  0   209 0   30  0   206 0   30  0   206 0   30  0   203 0   30  0   203 0   
                                           32  0   200 0   32  0   200 0   34  0   197 0   34  0   197 0   36  0   195 0   36  0   195 0   39  0   194 0   39  0   194 0   43  0   194 0   43  0   194 0   46  0   194 0   46  0   194 0   49  0   195 0   49  0   195 0   52  0   197 0   52  0   197 0   
                                           54  0   200 0   54  0   200 0   55  0   203 0   55  0   203 0   55  0   206 0   7   255 17  0   206 0   68  0   206 0   7   255 43  0   181 0   43  0   232 0   7   255 70  6   206 0   69  6   209 0   69  6   209 0   68  6   213 0   68  6   213 0   66  6   
                                           215 0   66  6   215 0   63  6   217 0   63  6   217 0   60  6   218 0   60  6   218 0   57  6   219 0   57  6   219 0   54  6   218 0   54  6   218 0   51  6   217 0   51  6   217 0   48  6   215 0   48  6   215 0   46  6   213 0   46  6   213 0   45  6   
                                           209 0   45  6   209 0   44  6   206 0   44  6   206 0   45  6   203 0   45  6   203 0   46  6   200 0   46  6   200 0   48  6   197 0   48  6   197 0   51  6   195 0   51  6   195 0   54  6   194 0   54  6   194 0   57  6   194 0   57  6   194 0   60  6   
                                           194 0   60  6   194 0   63  6   195 0   63  6   195 0   66  6   197 0   66  6   197 0   68  6   200 0   68  6   200 0   69  6   203 0   69  6   203 0   70  6   206 0   7   255 32  6   206 0   82  6   206 0   7   255 57  6   181 0   57  6   232 0   7   255 
                                           70  6   24  2   69  6   28  2   69  6   28  2   68  6   31  2   68  6   31  2   66  6   33  2   66  6   33  2   63  6   35  2   63  6   35  2   60  6   37  2   60  6   37  2   57  6   37  2   57  6   37  2   54  6   37  2   54  6   37  2   51  6   35  2   
                                           51  6   35  2   48  6   33  2   48  6   33  2   46  6   31  2   46  6   31  2   45  6   28  2   45  6   28  2   44  6   24  2   44  6   24  2   45  6   21  2   45  6   21  2   46  6   18  2   46  6   18  2   48  6   15  2   48  6   15  2   51  6   13  2   
                                           51  6   13  2   54  6   12  2   54  6   12  2   57  6   12  2   57  6   12  2   60  6   12  2   60  6   12  2   63  6   13  2   63  6   13  2   66  6   15  2   66  6   15  2   68  6   18  2   68  6   18  2   69  6   21  2   69  6   21  2   70  6   24  2   
                                           7   255 32  6   24  2   82  6   24  2   7   255 57  6   255 1   57  6   50  2   7   255 28  1   206 0   28  1   209 0   28  1   209 0   26  1   213 0   26  1   213 0   24  1   215 0   24  1   215 0   22  1   217 0   22  1   217 0   19  1   218 0   19  1   
                                           218 0   15  1   219 0   15  1   219 0   12  1   218 0   12  1   218 0   9   1   217 0   9   1   217 0   6   1   215 0   6   1   215 0   4   1   213 0   4   1   213 0   3   1   209 0   3   1   209 0   3   1   206 0   3   1   206 0   3   1   203 0   3   1   
                                           203 0   4   1   200 0   4   1   200 0   6   1   197 0   6   1   197 0   9   1   195 0   9   1   195 0   12  1   194 0   12  1   194 0   15  1   194 0   15  1   194 0   19  1   194 0   19  1   194 0   22  1   195 0   22  1   195 0   24  1   197 0   24  1   
                                           197 0   26  1   200 0   26  1   200 0   28  1   203 0   28  1   203 0   28  1   206 0   7   255 246 0   206 0   41  1   206 0   7   255 15  1   181 0   15  1   232 0   7   255 28  1   24  2   28  1   28  2   28  1   28  2   26  1   31  2   26  1   31  2   
                                           24  1   33  2   24  1   33  2   22  1   35  2   22  1   35  2   19  1   37  2   19  1   37  2   15  1   37  2   15  1   37  2   12  1   37  2   12  1   37  2   9   1   35  2   9   1   35  2   6   1   33  2   6   1   33  2   4   1   31  2   4   1   31  2   
                                           3   1   28  2   3   1   28  2   3   1   24  2   3   1   24  2   3   1   21  2   3   1   21  2   4   1   18  2   4   1   18  2   6   1   15  2   6   1   15  2   9   1   13  2   9   1   13  2   12  1   12  2   12  1   12  2   15  1   12  2   15  1   12  2   
                                           19  1   12  2   19  1   12  2   22  1   13  2   22  1   13  2   24  1   15  2   24  1   15  2   26  1   18  2   26  1   18  2   28  1   21  2   28  1   21  2   28  1   24  2   7   255 246 0   24  2   41  1   24  2   7   255 15  1   255 1   15  1   50  2   
                                           7   255 188 4   24  2   187 4   28  2   187 4   28  2   186 4   31  2   186 4   31  2   184 4   33  2   184 4   33  2   181 4   35  2   181 4   35  2   178 4   37  2   178 4   37  2   175 4   37  2   175 4   37  2   172 4   37  2   172 4   37  2   169 4   
                                           35  2   169 4   35  2   166 4   33  2   166 4   33  2   164 4   31  2   164 4   31  2   163 4   28  2   163 4   28  2   162 4   24  2   162 4   24  2   163 4   21  2   163 4   21  2   164 4   18  2   164 4   18  2   166 4   15  2   166 4   15  2   169 4   
                                           13  2   169 4   13  2   172 4   12  2   172 4   12  2   175 4   12  2   175 4   12  2   178 4   12  2   178 4   12  2   181 4   13  2   181 4   13  2   184 4   15  2   184 4   15  2   186 4   18  2   186 4   18  2   187 4   21  2   187 4   21  2   188 4   
                                           24  2   7   255 150 4   24  2   200 4   24  2   7   255 175 4   255 1   175 4   50  2   7   255 188 4   206 0   187 4   209 0   187 4   209 0   186 4   213 0   186 4   213 0   184 4   215 0   184 4   215 0   181 4   217 0   181 4   217 0   178 4   218 0   
                                           178 4   218 0   175 4   219 0   175 4   219 0   172 4   218 0   172 4   218 0   169 4   217 0   169 4   217 0   166 4   215 0   166 4   215 0   164 4   213 0   164 4   213 0   163 4   209 0   163 4   209 0   162 4   206 0   162 4   206 0   163 4   203 0   
                                           163 4   203 0   164 4   200 0   164 4   200 0   166 4   197 0   166 4   197 0   169 4   195 0   169 4   195 0   172 4   194 0   172 4   194 0   175 4   194 0   175 4   194 0   178 4   194 0   178 4   194 0   181 4   195 0   181 4   195 0   184 4   197 0   
                                           184 4   197 0   186 4   200 0   186 4   200 0   187 4   203 0   187 4   203 0   188 4   206 0   7   255 150 4   206 0   200 4   206 0   7   255 175 4   181 0   175 4   232 0   0   252 65  117 116 111 67  65  68  32  83  108 105 100 101 13  10  26  0   86  
                                           2   73  6   247 2   97  120 67  1   2   0   52  18  51  255 51  255 230 0   245 0   31  5   245 0   31  5   245 0   31  5   21  2   31  5   21  2   230 0   21  2   230 0   21  2   230 0   245 0   7   255 7   255 230 0   245 0   31  5   245 0   31  5   245 
                                           0   31  5   21  2   31  5   21  2   230 0   21  2   230 0   21  2   230 0   245 0   7   255 230 0   245 0   230 0   245 0   7   255 230 0   245 0   230 0   245 0   7   255 230 0   245 0   230 0   245 0   7   255 11  4   251 0   11  4   14  1   11  4   14  
                                           1   28  4   19  1   28  4   19  1   114 4   19  1   114 4   19  1   131 4   14  1   131 4   14  1   131 4   251 0   131 4   251 0   114 4   245 0   114 4   245 0   28  4   245 0   28  4   245 0   11  4   251 0   7   255 11  4   253 1   11  4   16  2   11  
                                           4   16  2   28  4   21  2   28  4   21  2   114 4   21  2   114 4   21  2   131 4   16  2   131 4   16  2   131 4   253 1   131 4   253 1   114 4   247 1   114 4   247 1   28  4   247 1   28  4   247 1   11  4   253 1   7   255 234 0   245 0   233 0   248 
                                           0   233 0   248 0   230 0   249 0   230 0   249 0   228 0   248 0   228 0   248 0   227 0   245 0   227 0   245 0   228 0   243 0   228 0   243 0   230 0   242 0   230 0   242 0   233 0   243 0   233 0   243 0   234 0   245 0   7   255 223 0   245 0   237 
                                           0   245 0   7   255 230 0   238 0   230 0   252 0   7   255 122 1   245 0   121 1   248 0   121 1   248 0   118 1   249 0   118 1   249 0   116 1   248 0   116 1   248 0   115 1   245 0   115 1   245 0   116 1   243 0   116 1   243 0   118 1   242 0   118 
                                           1   242 0   121 1   243 0   121 1   243 0   122 1   245 0   7   255 111 1   245 0   125 1   245 0   7   255 118 1   238 0   118 1   252 0   7   255 74  4   245 0   73  4   248 0   73  4   248 0   71  4   249 0   71  4   249 0   68  4   248 0   68  4   248 
                                           0   67  4   245 0   67  4   245 0   68  4   243 0   68  4   243 0   71  4   242 0   71  4   242 0   73  4   243 0   73  4   243 0   74  4   245 0   7   255 64  4   245 0   78  4   245 0   7   255 71  4   238 0   71  4   252 0   7   255 35  5   245 0   34  
                                           5   248 0   34  5   248 0   31  5   249 0   31  5   249 0   28  5   248 0   28  5   248 0   27  5   245 0   27  5   245 0   28  5   243 0   28  5   243 0   31  5   242 0   31  5   242 0   34  5   243 0   34  5   243 0   35  5   245 0   7   255 24  5   245 
                                           0   38  5   245 0   7   255 31  5   238 0   31  5   252 0   7   255 35  5   21  2   34  5   24  2   34  5   24  2   31  5   25  2   31  5   25  2   28  5   24  2   28  5   24  2   27  5   21  2   27  5   21  2   28  5   19  2   28  5   19  2   31  5   18  
                                           2   31  5   18  2   34  5   19  2   34  5   19  2   35  5   21  2   7   255 24  5   21  2   38  5   21  2   7   255 31  5   14  2   31  5   28  2   7   255 74  4   21  2   73  4   24  2   73  4   24  2   71  4   25  2   71  4   25  2   68  4   24  2   68  
                                           4   24  2   67  4   21  2   67  4   21  2   68  4   19  2   68  4   19  2   71  4   18  2   71  4   18  2   73  4   19  2   73  4   19  2   74  4   21  2   7   255 64  4   21  2   78  4   21  2   7   255 71  4   14  2   71  4   28  2   7   255 122 1   21  
                                           2   121 1   24  2   121 1   24  2   118 1   25  2   118 1   25  2   116 1   24  2   116 1   24  2   115 1   21  2   115 1   21  2   116 1   19  2   116 1   19  2   118 1   18  2   118 1   18  2   121 1   19  2   121 1   19  2   122 1   21  2   7   255 111 
                                           1   21  2   125 1   21  2   7   255 118 1   14  2   118 1   28  2   7   255 234 0   21  2   233 0   24  2   233 0   24  2   230 0   25  2   230 0   25  2   228 0   24  2   228 0   24  2   227 0   21  2   227 0   21  2   228 0   19  2   228 0   19  2   230 
                                           0   18  2   230 0   18  2   233 0   19  2   233 0   19  2   234 0   21  2   7   255 223 0   21  2   237 0   21  2   7   255 230 0   14  2   230 0   28  2   7   255 122 1   133 1   121 1   136 1   121 1   136 1   118 1   137 1   118 1   137 1   116 1   136 
                                           1   116 1   136 1   115 1   133 1   115 1   133 1   116 1   131 1   116 1   131 1   118 1   130 1   118 1   130 1   121 1   131 1   121 1   131 1   122 1   133 1   7   255 111 1   133 1   125 1   133 1   7   255 118 1   126 1   118 1   140 1   7   255 34  
                                           5   133 1   33  5   136 1   33  5   136 1   30  5   137 1   30  5   137 1   28  5   136 1   28  5   136 1   27  5   133 1   27  5   133 1   28  5   131 1   28  5   131 1   30  5   130 1   30  5   130 1   33  5   131 1   33  5   131 1   34  5   133 1   7   
                                           255 23  5   133 1   38  5   133 1   7   255 30  5   126 1   30  5   140 1   7   255 58  1   253 1   58  1   16  2   58  1   16  2   75  1   21  2   75  1   21  2   162 1   21  2   162 1   21  2   179 1   16  2   179 1   16  2   179 1   253 1   179 1   253 
                                           1   162 1   247 1   162 1   247 1   75  1   247 1   75  1   247 1   58  1   253 1   7   255 58  1   251 0   58  1   14  1   58  1   14  1   75  1   19  1   75  1   19  1   162 1   19  1   162 1   19  1   179 1   14  1   179 1   14  1   179 1   251 0   179 
                                           1   251 0   162 1   245 0   162 1   245 0   75  1   245 0   75  1   245 0   58  1   251 0   0   252 65  117 116 111 67  65  68  32  83  108 105 100 101 13  10  26  0   86  2   73  6   247 2   97  120 67  1   2   0   52  18  51  255 51  255 92  1   22  1   
                                           242 4   22  1   242 4   22  1   242 4   215 1   242 4   215 1   92  1   215 1   92  1   215 1   92  1   22  1   7   255 7   255 92  1   22  1   242 4   22  1   242 4   22  1   242 4   215 1   242 4   215 1   92  1   215 1   92  1   215 1   92  1   22  1   
                                           7   255 92  1   22  1   92  1   22  1   7   255 92  1   22  1   92  1   22  1   7   255 92  1   22  1   92  1   22  1   7   255 211 3   60  1   211 3   71  1   211 3   71  1   221 3   75  1   221 3   75  1   19  4   75  1   19  4   75  1   30  4   71  1   
                                           30  4   71  1   30  4   60  1   30  4   60  1   19  4   56  1   19  4   56  1   221 3   56  1   221 3   56  1   211 3   60  1   7   255 211 3   26  1   211 3   37  1   211 3   37  1   221 3   41  1   221 3   41  1   19  4   41  1   19  4   41  1   30  4   
                                           37  1   30  4   37  1   30  4   26  1   30  4   26  1   19  4   22  1   19  4   22  1   221 3   22  1   221 3   22  1   211 3   26  1   7   255 211 3   165 1   211 3   177 1   211 3   177 1   221 3   181 1   221 3   181 1   19  4   181 1   19  4   181 1   
                                           30  4   177 1   30  4   177 1   30  4   165 1   30  4   165 1   19  4   162 1   19  4   162 1   221 3   162 1   221 3   162 1   211 3   165 1   7   255 211 3   199 1   211 3   211 1   211 3   211 1   221 3   215 1   221 3   215 1   19  4   215 1   19  4   
                                           215 1   30  4   211 1   30  4   211 1   30  4   199 1   30  4   199 1   19  4   196 1   19  4   196 1   221 3   196 1   221 3   196 1   211 3   199 1   7   255 45  4   60  1   45  4   71  1   45  4   71  1   56  4   75  1   56  4   75  1   110 4   75  1   
                                           110 4   75  1   121 4   71  1   121 4   71  1   121 4   60  1   121 4   60  1   110 4   56  1   110 4   56  1   56  4   56  1   56  4   56  1   45  4   60  1   7   255 45  4   26  1   45  4   37  1   45  4   37  1   56  4   41  1   56  4   41  1   110 4   
                                           41  1   110 4   41  1   121 4   37  1   121 4   37  1   121 4   26  1   121 4   26  1   110 4   22  1   110 4   22  1   56  4   22  1   56  4   22  1   45  4   26  1   7   255 45  4   165 1   45  4   177 1   45  4   177 1   56  4   181 1   56  4   181 1   
                                           110 4   181 1   110 4   181 1   121 4   177 1   121 4   177 1   121 4   165 1   121 4   165 1   110 4   162 1   110 4   162 1   56  4   162 1   56  4   162 1   45  4   165 1   7   255 45  4   199 1   45  4   211 1   45  4   211 1   56  4   215 1   56  4   
                                           215 1   110 4   215 1   110 4   215 1   121 4   211 1   121 4   211 1   121 4   199 1   121 4   199 1   110 4   196 1   110 4   196 1   56  4   196 1   56  4   196 1   45  4   199 1   7   255 94  1   22  1   93  1   24  1   93  1   24  1   92  1   24  1   
                                           92  1   24  1   90  1   24  1   90  1   24  1   90  1   22  1   90  1   22  1   90  1   21  1   90  1   21  1   92  1   20  1   92  1   20  1   93  1   21  1   93  1   21  1   94  1   22  1   7   255 87  1   22  1   96  1   22  1   7   255 92  1   18  1   
                                           92  1   27  1   7   255 94  1   215 1   93  1   216 1   93  1   216 1   92  1   217 1   92  1   217 1   90  1   216 1   90  1   216 1   90  1   215 1   90  1   215 1   90  1   213 1   90  1   213 1   92  1   212 1   92  1   212 1   93  1   213 1   93  1   
                                           213 1   94  1   215 1   7   255 87  1   215 1   96  1   215 1   7   255 92  1   210 1   92  1   219 1   7   255 244 4   215 1   243 4   216 1   243 4   216 1   242 4   217 1   242 4   217 1   240 4   216 1   240 4   216 1   239 4   215 1   239 4   215 1   
                                           )) "a")
 (_WriteStream FILE (vl-list->string (list 240 4   213 1   240 4   213 1   242 4   212 1   242 4   212 1   243 4   213 1   243 4   213 1   244 4   215 1   7   255 237 4   215 1   246 4   215 1   7   255 242 4   210 1   242 4   219 1   7   255 244 4   22  1   243 4   24  1   243 4   24  1   242 4   
                                           24  1   242 4   24  1   240 4   24  1   240 4   24  1   239 4   22  1   239 4   22  1   240 4   21  1   240 4   21  1   242 4   20  1   242 4   20  1   243 4   21  1   243 4   21  1   244 4   22  1   7   255 237 4   22  1   246 4   22  1   7   255 242 4   
                                           18  1   242 4   27  1   7   255 237 1   22  1   236 1   24  1   236 1   24  1   235 1   24  1   235 1   24  1   233 1   24  1   233 1   24  1   232 1   22  1   232 1   22  1   233 1   21  1   233 1   21  1   235 1   20  1   235 1   20  1   236 1   21  1   
                                           236 1   21  1   237 1   22  1   7   255 230 1   22  1   239 1   22  1   7   255 235 1   18  1   235 1   27  1   7   255 237 1   215 1   236 1   216 1   236 1   216 1   235 1   217 1   235 1   217 1   233 1   216 1   233 1   216 1   232 1   215 1   232 1   
                                           215 1   233 1   213 1   233 1   213 1   235 1   212 1   235 1   212 1   236 1   213 1   236 1   213 1   237 1   215 1   7   255 230 1   215 1   239 1   215 1   7   255 235 1   210 1   235 1   219 1   7   255 237 1   118 1   236 1   120 1   236 1   120 1   
                                           235 1   121 1   235 1   121 1   233 1   120 1   233 1   120 1   232 1   118 1   232 1   118 1   233 1   117 1   233 1   117 1   235 1   116 1   235 1   116 1   236 1   117 1   236 1   117 1   237 1   118 1   7   255 230 1   118 1   239 1   118 1   7   255 
                                           235 1   114 1   235 1   123 1   7   255 40  4   22  1   39  4   24  1   39  4   24  1   38  4   24  1   38  4   24  1   36  4   24  1   36  4   24  1   35  4   22  1   35  4   22  1   36  4   21  1   36  4   21  1   38  4   20  1   38  4   20  1   39  4   
                                           21  1   39  4   21  1   40  4   22  1   7   255 33  4   22  1   42  4   22  1   7   255 38  4   18  1   38  4   27  1   7   255 40  4   215 1   39  4   216 1   39  4   216 1   38  4   217 1   38  4   217 1   36  4   216 1   36  4   216 1   35  4   215 1   
                                           35  4   215 1   36  4   213 1   36  4   213 1   38  4   212 1   38  4   212 1   39  4   213 1   39  4   213 1   40  4   215 1   7   255 33  4   215 1   42  4   215 1   7   255 38  4   210 1   38  4   219 1   7   255 197 1   26  1   197 1   37  1   197 1   
                                           37  1   207 1   41  1   207 1   41  1   6   2   41  1   6   2   41  1   16  2   37  1   16  2   37  1   16  2   26  1   16  2   26  1   6   2   22  1   6   2   22  1   207 1   22  1   207 1   22  1   197 1   26  1   7   255 197 1   199 1   197 1   211 1   
                                           197 1   211 1   207 1   215 1   207 1   215 1   6   2   215 1   6   2   215 1   16  2   211 1   16  2   211 1   16  2   199 1   16  2   199 1   6   2   196 1   6   2   196 1   207 1   196 1   207 1   196 1   197 1   199 1   0   252 65  117 116 111 67  65  
                                           68  32  83  108 105 100 101 13  10  26  0   86  2   106 6   234 2   99  219 79  1   2   0   52  18  7   255 7   255 219 0   125 0   154 5   125 0   154 5   125 0   154 5   106 2   154 5   106 2   219 0   106 2   219 0   106 2   219 0   125 0   7   255 219 
                                           0   125 0   219 0   125 0   7   255 219 0   125 0   219 0   125 0   7   255 152 3   134 0   152 3   164 0   152 3   164 0   179 3   173 0   179 3   173 0   62  4   173 0   62  4   173 0   89  4   164 0   89  4   164 0   89  4   134 0   89  4   134 0   62  
                                           4   125 0   62  4   125 0   179 3   125 0   179 3   125 0   152 3   134 0   7   255 152 3   67  2   152 3   97  2   152 3   97  2   179 3   106 2   179 3   106 2   62  4   106 2   62  4   106 2   89  4   97  2   89  4   97  2   89  4   67  2   89  4   67  
                                           2   62  4   58  2   62  4   58  2   179 3   58  2   179 3   58  2   152 3   67  2   7   255 238 0   106 2   236 0   115 2   236 0   115 2   229 0   122 2   229 0   122 2   219 0   125 2   219 0   125 2   210 0   122 2   210 0   122 2   203 0   115 2   203 
                                           0   115 2   201 0   106 2   201 0   106 2   203 0   97  2   203 0   97  2   210 0   90  2   210 0   90  2   219 0   87  2   219 0   87  2   229 0   90  2   229 0   90  2   236 0   97  2   236 0   97  2   238 0   106 2   7   255 182 0   106 2   1   1   106 
                                           2   7   255 219 0   68  2   219 0   144 2   7   255 238 0   125 0   236 0   135 0   236 0   135 0   229 0   142 0   229 0   142 0   219 0   144 0   219 0   144 0   210 0   142 0   210 0   142 0   203 0   135 0   203 0   135 0   201 0   125 0   201 0   125 
                                           0   203 0   116 0   203 0   116 0   210 0   109 0   210 0   109 0   219 0   106 0   219 0   106 0   229 0   109 0   229 0   109 0   236 0   116 0   236 0   116 0   238 0   125 0   7   255 182 0   125 0   1   1   125 0   7   255 219 0   87  0   219 0   163 
                                           0   7   255 134 1   125 0   132 1   135 0   132 1   135 0   125 1   142 0   125 1   142 0   115 1   144 0   115 1   144 0   106 1   142 0   106 1   142 0   99  1   135 0   99  1   135 0   96  1   125 0   96  1   125 0   99  1   116 0   99  1   116 0   106 
                                           1   109 0   106 1   109 0   115 1   106 0   115 1   106 0   125 1   109 0   125 1   109 0   132 1   116 0   132 1   116 0   134 1   125 0   7   255 77  1   125 0   153 1   125 0   7   255 115 1   87  0   115 1   163 0   7   255 11  4   125 0   9   4   135 
                                           0   9   4   135 0   2   4   142 0   2   4   142 0   248 3   144 0   248 3   144 0   239 3   142 0   239 3   142 0   232 3   135 0   232 3   135 0   229 3   125 0   229 3   125 0   232 3   116 0   232 3   116 0   239 3   109 0   239 3   109 0   248 3   106 
                                           0   248 3   106 0   2   4   109 0   2   4   109 0   9   4   116 0   9   4   116 0   11  4   125 0   7   255 210 3   125 0   30  4   125 0   7   255 248 3   87  0   248 3   163 0   7   255 173 5   125 0   170 5   135 0   170 5   135 0   163 5   142 0   163 
                                           5   142 0   154 5   144 0   154 5   144 0   144 5   142 0   144 5   142 0   137 5   135 0   137 5   135 0   135 5   125 0   135 5   125 0   137 5   116 0   137 5   116 0   144 5   109 0   144 5   109 0   154 5   106 0   154 5   106 0   163 5   109 0   163 
                                           5   109 0   170 5   116 0   170 5   116 0   173 5   125 0   7   255 116 5   125 0   192 5   125 0   7   255 154 5   87  0   154 5   163 0   7   255 173 5   106 2   170 5   115 2   170 5   115 2   163 5   122 2   163 5   122 2   154 5   125 2   154 5   125 
                                           2   144 5   122 2   144 5   122 2   137 5   115 2   137 5   115 2   135 5   106 2   135 5   106 2   137 5   97  2   137 5   97  2   144 5   90  2   144 5   90  2   154 5   87  2   154 5   87  2   163 5   90  2   163 5   90  2   170 5   97  2   170 5   97  
                                           2   173 5   106 2   7   255 116 5   106 2   192 5   106 2   7   255 154 5   68  2   154 5   144 2   7   255 11  4   106 2   9   4   115 2   9   4   115 2   2   4   122 2   2   4   122 2   248 3   125 2   248 3   125 2   239 3   122 2   239 3   122 2   232 
                                           3   115 2   232 3   115 2   229 3   106 2   229 3   106 2   232 3   97  2   232 3   97  2   239 3   90  2   239 3   90  2   248 3   87  2   248 3   87  2   2   4   90  2   2   4   90  2   9   4   97  2   9   4   97  2   11  4   106 2   7   255 210 3   106 
                                           2   30  4   106 2   7   255 248 3   68  2   248 3   144 2   7   255 134 1   106 2   132 1   115 2   132 1   115 2   125 1   122 2   125 1   122 2   115 1   125 2   115 1   125 2   106 1   122 2   106 1   122 2   99  1   115 2   99  1   115 2   96  1   106 
                                           2   96  1   106 2   99  1   97  2   99  1   97  2   106 1   90  2   106 1   90  2   115 1   87  2   115 1   87  2   125 1   90  2   125 1   90  2   132 1   97  2   132 1   97  2   134 1   106 2   7   255 77  1   106 2   153 1   106 2   7   255 115 1   68  
                                           2   115 1   144 2   7   255 134 1   116 1   132 1   125 1   132 1   125 1   125 1   132 1   125 1   132 1   115 1   135 1   115 1   135 1   106 1   132 1   106 1   132 1   99  1   125 1   99  1   125 1   96  1   116 1   96  1   116 1   99  1   106 1   99  
                                           1   106 1   106 1   99  1   106 1   99  1   115 1   97  1   115 1   97  1   125 1   99  1   125 1   99  1   132 1   106 1   132 1   106 1   134 1   116 1   7   255 77  1   116 1   153 1   116 1   7   255 115 1   78  1   115 1   153 1   7   255 19  1   134 
                                           0   19  1   164 0   19  1   164 0   46  1   173 0   46  1   173 0   185 1   173 0   185 1   173 0   212 1   164 0   212 1   164 0   212 1   134 0   212 1   134 0   185 1   125 0   185 1   125 0   46  1   125 0   46  1   125 0   19  1   134 0   7   255 19  
                                           1   67  2   19  1   97  2   19  1   97  2   46  1   106 2   46  1   106 2   185 1   106 2   185 1   106 2   212 1   97  2   212 1   97  2   212 1   67  2   212 1   67  2   185 1   58  2   185 1   58  2   46  1   58  2   46  1   58  2   19  1   67  2   0   
                                           252 65  117 116 111 67  65  68  32  83  108 105 100 101 13  10  26  0   86  2   73  6   247 2   97  120 67  1   2   0   52  18  7   255 7   255 150 3   70  1   53  6   70  1   53  6   70  1   53  6   178 1   53  6   178 1   150 3   178 1   150 3   178 1   
                                           150 3   70  1   7   255 150 3   70  1   150 3   70  1   7   255 150 3   70  1   150 3   70  1   7   255 150 3   70  1   150 3   70  1   7   255 189 5   93  1   189 5   101 1   189 5   101 1   196 5   103 1   196 5   103 1   229 5   103 1   229 5   103 1   
                                           235 5   101 1   235 5   101 1   235 5   93  1   235 5   93  1   229 5   91  1   229 5   91  1   196 5   91  1   196 5   91  1   189 5   93  1   7   255 189 5   72  1   189 5   80  1   189 5   80  1   196 5   82  1   196 5   82  1   229 5   82  1   229 5   
                                           82  1   235 5   80  1   235 5   80  1   235 5   72  1   235 5   72  1   229 5   70  1   229 5   70  1   196 5   70  1   196 5   70  1   189 5   72  1   7   255 189 5   148 1   189 5   155 1   189 5   155 1   196 5   157 1   196 5   157 1   229 5   157 1   
                                           229 5   157 1   235 5   155 1   235 5   155 1   235 5   148 1   235 5   148 1   229 5   146 1   229 5   146 1   196 5   146 1   196 5   146 1   189 5   148 1   7   255 189 5   169 1   189 5   176 1   189 5   176 1   196 5   178 1   196 5   178 1   229 5   
                                           178 1   229 5   178 1   235 5   176 1   235 5   176 1   235 5   169 1   235 5   169 1   229 5   166 1   229 5   166 1   196 5   166 1   196 5   166 1   189 5   169 1   7   255 242 5   93  1   242 5   101 1   242 5   101 1   248 5   103 1   248 5   103 1   
                                           26  6   103 1   26  6   103 1   32  6   101 1   32  6   101 1   32  6   93  1   32  6   93  1   26  6   91  1   26  6   91  1   248 5   91  1   248 5   91  1   242 5   93  1   7   255 242 5   72  1   242 5   80  1   242 5   80  1   248 5   82  1   248 5   
                                           82  1   26  6   82  1   26  6   82  1   32  6   80  1   32  6   80  1   32  6   72  1   32  6   72  1   26  6   70  1   26  6   70  1   248 5   70  1   248 5   70  1   242 5   72  1   7   255 242 5   148 1   242 5   155 1   242 5   155 1   248 5   157 1   
                                           248 5   157 1   26  6   157 1   26  6   157 1   32  6   155 1   32  6   155 1   32  6   148 1   32  6   148 1   26  6   146 1   26  6   146 1   248 5   146 1   248 5   146 1   242 5   148 1   7   255 242 5   169 1   242 5   176 1   242 5   176 1   248 5   
                                           178 1   248 5   178 1   26  6   178 1   26  6   178 1   32  6   176 1   32  6   176 1   32  6   169 1   32  6   169 1   26  6   166 1   26  6   166 1   248 5   166 1   248 5   166 1   242 5   169 1   7   255 237 3   124 1   236 3   126 1   236 3   126 1   
                                           235 3   128 1   235 3   128 1   232 3   128 1   232 3   128 1   230 3   128 1   230 3   128 1   229 3   126 1   229 3   126 1   228 3   124 1   228 3   124 1   229 3   122 1   229 3   122 1   230 3   121 1   230 3   121 1   232 3   120 1   232 3   120 1   
                                           235 3   121 1   235 3   121 1   236 3   122 1   236 3   122 1   237 3   124 1   7   255 224 3   124 1   241 3   124 1   7   255 232 3   116 1   232 3   132 1   7   255 154 3   70  1   153 3   72  1   153 3   72  1   152 3   74  1   152 3   74  1   150 3   
                                           74  1   150 3   74  1   147 3   74  1   147 3   74  1   146 3   72  1   146 3   72  1   145 3   70  1   145 3   70  1   146 3   68  1   146 3   68  1   147 3   67  1   147 3   67  1   150 3   66  1   150 3   66  1   152 3   67  1   152 3   67  1   153 3   
                                           68  1   153 3   68  1   154 3   70  1   7   255 141 3   70  1   158 3   70  1   7   255 150 3   62  1   150 3   79  1   7   255 57  6   70  1   57  6   72  1   57  6   72  1   55  6   74  1   55  6   74  1   53  6   74  1   53  6   74  1   51  6   74  1   
                                           51  6   74  1   49  6   72  1   49  6   72  1   49  6   70  1   49  6   70  1   49  6   68  1   49  6   68  1   51  6   67  1   51  6   67  1   53  6   66  1   53  6   66  1   55  6   67  1   55  6   67  1   57  6   68  1   57  6   68  1   57  6   70  1   
                                           7   255 45  6   70  1   61  6   70  1   7   255 53  6   62  1   53  6   79  1   7   255 57  6   178 1   57  6   180 1   57  6   180 1   55  6   182 1   55  6   182 1   53  6   182 1   53  6   182 1   51  6   182 1   51  6   182 1   49  6   180 1   49  6   
                                           180 1   49  6   178 1   49  6   178 1   49  6   176 1   49  6   176 1   51  6   174 1   51  6   174 1   53  6   174 1   53  6   174 1   55  6   174 1   55  6   174 1   57  6   176 1   57  6   176 1   57  6   178 1   7   255 45  6   178 1   61  6   178 1   
                                           7   255 53  6   170 1   53  6   186 1   7   255 154 3   178 1   153 3   180 1   153 3   180 1   152 3   182 1   152 3   182 1   150 3   182 1   150 3   182 1   147 3   182 1   147 3   182 1   146 3   180 1   146 3   180 1   145 3   178 1   145 3   178 1   
                                           146 3   176 1   146 3   176 1   147 3   174 1   147 3   174 1   150 3   174 1   150 3   174 1   152 3   174 1   152 3   174 1   153 3   176 1   153 3   176 1   154 3   178 1   7   255 141 3   178 1   158 3   178 1   7   255 150 3   170 1   150 3   186 1   
                                           7   255 243 5   178 1   242 5   180 1   242 5   180 1   241 5   182 1   241 5   182 1   239 5   182 1   239 5   182 1   236 5   182 1   236 5   182 1   235 5   180 1   235 5   180 1   234 5   178 1   234 5   178 1   235 5   176 1   235 5   176 1   236 5   
                                           174 1   236 5   174 1   239 5   174 1   239 5   174 1   241 5   174 1   241 5   174 1   242 5   176 1   242 5   176 1   243 5   178 1   7   255 230 5   178 1   247 5   178 1   7   255 239 5   170 1   239 5   186 1   7   255 243 5   70  1   242 5   72  1   
                                           242 5   72  1   241 5   74  1   241 5   74  1   239 5   74  1   239 5   74  1   236 5   74  1   236 5   74  1   235 5   72  1   235 5   72  1   234 5   70  1   234 5   70  1   235 5   68  1   235 5   68  1   236 5   67  1   236 5   67  1   239 5   66  1   
                                           239 5   66  1   241 5   67  1   241 5   67  1   242 5   68  1   242 5   68  1   243 5   70  1   7   255 230 5   70  1   247 5   70  1   7   255 239 5   62  1   239 5   79  1   7   255 79  3   124 1   232 3   124 1   7   255 209 3   93  1   209 3   101 1   
                                           209 3   101 1   216 3   103 1   216 3   103 1   249 3   103 1   249 3   103 1   0   4   101 1   0   4   101 1   0   4   93  1   0   4   93  1   249 3   91  1   249 3   91  1   216 3   91  1   216 3   91  1   209 3   93  1   7   255 209 3   72  1   209 3   
                                           80  1   209 3   80  1   216 3   82  1   216 3   82  1   249 3   82  1   249 3   82  1   0   4   80  1   0   4   80  1   0   4   72  1   0   4   72  1   249 3   70  1   249 3   70  1   216 3   70  1   216 3   70  1   209 3   72  1   7   255 209 3   148 1   
                                           209 3   155 1   209 3   155 1   216 3   157 1   216 3   157 1   249 3   157 1   249 3   157 1   0   4   155 1   0   4   155 1   0   4   148 1   0   4   148 1   249 3   146 1   249 3   146 1   216 3   146 1   216 3   146 1   209 3   148 1   7   255 209 3   
                                           169 1   209 3   176 1   209 3   176 1   216 3   178 1   216 3   178 1   249 3   178 1   249 3   178 1   0   4   176 1   0   4   176 1   0   4   169 1   0   4   169 1   249 3   166 1   249 3   166 1   216 3   166 1   216 3   166 1   209 3   169 1   7   255 
                                           83  3   124 1   83  3   126 1   83  3   126 1   82  3   127 1   82  3   127 1   81  3   128 1   81  3   128 1   79  3   128 1   79  3   128 1   78  3   128 1   78  3   128 1   76  3   127 1   76  3   127 1   75  3   126 1   75  3   126 1   75  3   124 1   
                                           75  3   124 1   75  3   123 1   75  3   123 1   76  3   121 1   76  3   121 1   78  3   120 1   78  3   120 1   79  3   120 1   79  3   120 1   81  3   120 1   81  3   120 1   82  3   121 1   82  3   121 1   83  3   123 1   83  3   123 1   83  3   124 1   
                                           7   255 71  3   124 1   87  3   124 1   7   255 79  3   116 1   79  3   132 1   7   255 237 3   70  1   236 3   72  1   236 3   72  1   235 3   73  1   235 3   73  1   234 3   74  1   234 3   74  1   232 3   74  1   232 3   74  1   231 3   74  1   231 3   
                                           74  1   230 3   73  1   230 3   73  1   229 3   72  1   229 3   72  1   228 3   70  1   228 3   70  1   229 3   69  1   229 3   69  1   230 3   67  1   230 3   67  1   231 3   66  1   231 3   66  1   232 3   66  1   232 3   66  1   234 3   66  1   234 3   
                                           )) "a")
 (_WriteStream FILE (vl-list->string (list 66  1   235 3   67  1   235 3   67  1   236 3   69  1   236 3   69  1   237 3   70  1   7   255 224 3   70  1   241 3   70  1   7   255 232 3   62  1   232 3   79  1   7   255 237 3   178 1   236 3   180 1   236 3   180 1   235 3   181 1   235 3   181 1   
                                           234 3   182 1   234 3   182 1   232 3   182 1   232 3   182 1   231 3   182 1   231 3   182 1   230 3   181 1   230 3   181 1   229 3   180 1   229 3   180 1   228 3   178 1   228 3   178 1   229 3   176 1   229 3   176 1   230 3   175 1   230 3   175 1   
                                           231 3   174 1   231 3   174 1   232 3   174 1   232 3   174 1   234 3   174 1   234 3   174 1   235 3   175 1   235 3   175 1   236 3   176 1   236 3   176 1   237 3   178 1   7   255 224 3   178 1   241 3   178 1   7   255 232 3   170 1   232 3   186 1   
                                           7   255 237 3   124 1   236 3   126 1   236 3   126 1   235 3   127 1   235 3   127 1   234 3   128 1   234 3   128 1   232 3   128 1   232 3   128 1   231 3   128 1   231 3   128 1   230 3   127 1   230 3   127 1   229 3   126 1   229 3   126 1   228 3   
                                           124 1   228 3   124 1   229 3   123 1   229 3   123 1   230 3   121 1   230 3   121 1   231 3   120 1   231 3   120 1   232 3   120 1   232 3   120 1   234 3   120 1   234 3   120 1   235 3   121 1   235 3   121 1   236 3   123 1   236 3   123 1   237 3   
                                           124 1   7   255 224 3   124 1   241 3   124 1   7   255 232 3   116 1   232 3   132 1   7   255 176 0   70  1   79  3   70  1   79  3   70  1   79  3   178 1   79  3   178 1   176 0   178 1   176 0   178 1   176 0   70  1   7   255 176 0   70  1   176 0   
                                           70  1   7   255 176 0   70  1   176 0   70  1   7   255 176 0   70  1   176 0   70  1   7   255 211 2   93  1   211 2   101 1   211 2   101 1   218 2   103 1   218 2   103 1   251 2   103 1   251 2   103 1   1   3   101 1   1   3   101 1   1   3   93  1   
                                           1   3   93  1   251 2   91  1   251 2   91  1   218 2   91  1   218 2   91  1   211 2   93  1   7   255 211 2   72  1   211 2   80  1   211 2   80  1   218 2   82  1   218 2   82  1   251 2   82  1   251 2   82  1   1   3   80  1   1   3   80  1   1   3   
                                           72  1   1   3   72  1   251 2   70  1   251 2   70  1   218 2   70  1   218 2   70  1   211 2   72  1   7   255 211 2   148 1   211 2   155 1   211 2   155 1   218 2   157 1   218 2   157 1   251 2   157 1   251 2   157 1   1   3   155 1   1   3   155 1   
                                           1   3   148 1   1   3   148 1   251 2   146 1   251 2   146 1   218 2   146 1   218 2   146 1   211 2   148 1   7   255 211 2   169 1   211 2   176 1   211 2   176 1   218 2   178 1   218 2   178 1   251 2   178 1   251 2   178 1   1   3   176 1   1   3   
                                           176 1   1   3   169 1   1   3   169 1   251 2   166 1   251 2   166 1   218 2   166 1   218 2   166 1   211 2   169 1   7   255 8   3   93  1   8   3   101 1   8   3   101 1   14  3   103 1   14  3   103 1   48  3   103 1   48  3   103 1   54  3   101 1   
                                           54  3   101 1   54  3   93  1   54  3   93  1   48  3   91  1   48  3   91  1   14  3   91  1   14  3   91  1   8   3   93  1   7   255 8   3   72  1   8   3   80  1   8   3   80  1   14  3   82  1   14  3   82  1   48  3   82  1   48  3   82  1   54  3   
                                           80  1   54  3   80  1   54  3   72  1   54  3   72  1   48  3   70  1   48  3   70  1   14  3   70  1   14  3   70  1   8   3   72  1   7   255 8   3   148 1   8   3   155 1   8   3   155 1   14  3   157 1   14  3   157 1   48  3   157 1   48  3   157 1   
                                           54  3   155 1   54  3   155 1   54  3   148 1   54  3   148 1   48  3   146 1   48  3   146 1   14  3   146 1   14  3   146 1   8   3   148 1   7   255 8   3   169 1   8   3   176 1   8   3   176 1   14  3   178 1   14  3   178 1   48  3   178 1   48  3   
                                           178 1   54  3   176 1   54  3   176 1   54  3   169 1   54  3   169 1   48  3   166 1   48  3   166 1   14  3   166 1   14  3   166 1   8   3   169 1   7   255 3   1   124 1   2   1   126 1   2   1   126 1   1   1   127 1   1   1   127 1   0   1   128 1   
                                           0   1   128 1   254 0   128 1   254 0   128 1   253 0   128 1   253 0   128 1   252 0   127 1   252 0   127 1   251 0   126 1   251 0   126 1   250 0   124 1   250 0   124 1   251 0   123 1   251 0   123 1   252 0   121 1   252 0   121 1   253 0   120 1   
                                           253 0   120 1   254 0   120 1   254 0   120 1   0   1   120 1   0   1   120 1   1   1   121 1   1   1   121 1   2   1   123 1   2   1   123 1   3   1   124 1   7   255 246 0   124 1   7   1   124 1   7   255 254 0   116 1   254 0   132 1   7   255 180 0   
                                           70  1   180 0   72  1   180 0   72  1   179 0   73  1   179 0   73  1   177 0   74  1   177 0   74  1   176 0   74  1   176 0   74  1   174 0   74  1   174 0   74  1   173 0   73  1   173 0   73  1   172 0   72  1   172 0   72  1   172 0   70  1   172 0   
                                           70  1   172 0   69  1   172 0   69  1   173 0   67  1   173 0   67  1   174 0   66  1   174 0   66  1   176 0   66  1   176 0   66  1   177 0   66  1   177 0   66  1   179 0   67  1   179 0   67  1   180 0   69  1   180 0   69  1   180 0   70  1   7   255 
                                           167 0   70  1   184 0   70  1   7   255 176 0   62  1   176 0   79  1   7   255 180 0   178 1   180 0   180 1   180 0   180 1   179 0   181 1   179 0   181 1   177 0   182 1   177 0   182 1   176 0   182 1   176 0   182 1   174 0   182 1   174 0   182 1   
                                           173 0   181 1   173 0   181 1   172 0   180 1   172 0   180 1   172 0   178 1   172 0   178 1   172 0   176 1   172 0   176 1   173 0   175 1   173 0   175 1   174 0   174 1   174 0   174 1   176 0   174 1   176 0   174 1   177 0   174 1   177 0   174 1   
                                           179 0   175 1   179 0   175 1   180 0   176 1   180 0   176 1   180 0   178 1   7   255 167 0   178 1   184 0   178 1   7   255 176 0   170 1   176 0   186 1   7   255 83  3   178 1   83  3   180 1   83  3   180 1   82  3   181 1   82  3   181 1   81  3   
                                           182 1   81  3   182 1   79  3   182 1   79  3   182 1   78  3   182 1   78  3   182 1   76  3   181 1   76  3   181 1   75  3   180 1   75  3   180 1   75  3   178 1   75  3   178 1   75  3   176 1   75  3   176 1   76  3   175 1   76  3   175 1   78  3   
                                           174 1   78  3   174 1   79  3   174 1   79  3   174 1   81  3   174 1   81  3   174 1   82  3   175 1   82  3   175 1   83  3   176 1   83  3   176 1   83  3   178 1   7   255 71  3   178 1   87  3   178 1   7   255 79  3   170 1   79  3   186 1   7   255 
                                           83  3   124 1   83  3   126 1   83  3   126 1   82  3   127 1   82  3   127 1   81  3   128 1   81  3   128 1   79  3   128 1   79  3   128 1   78  3   128 1   78  3   128 1   76  3   127 1   76  3   127 1   75  3   126 1   75  3   126 1   75  3   124 1   
                                           75  3   124 1   75  3   123 1   75  3   123 1   76  3   121 1   76  3   121 1   78  3   120 1   78  3   120 1   79  3   120 1   79  3   120 1   81  3   120 1   81  3   120 1   82  3   121 1   82  3   121 1   83  3   123 1   83  3   123 1   83  3   124 1   
                                           7   255 71  3   124 1   87  3   124 1   7   255 79  3   116 1   79  3   132 1   7   255 83  3   70  1   83  3   72  1   83  3   72  1   82  3   73  1   82  3   73  1   81  3   74  1   81  3   74  1   79  3   74  1   79  3   74  1   78  3   74  1   78  3   
                                           74  1   76  3   73  1   76  3   73  1   75  3   72  1   75  3   72  1   75  3   70  1   75  3   70  1   75  3   69  1   75  3   69  1   76  3   67  1   76  3   67  1   78  3   66  1   78  3   66  1   79  3   66  1   79  3   66  1   81  3   66  1   81  3   
                                           66  1   82  3   67  1   82  3   67  1   83  3   69  1   83  3   69  1   83  3   70  1   7   255 71  3   70  1   87  3   70  1   7   255 79  3   62  1   79  3   79  1   7   255 9   3   178 1   8   3   180 1   8   3   180 1   7   3   181 1   7   3   181 1   
                                           6   3   182 1   6   3   182 1   5   3   182 1   5   3   182 1   3   3   182 1   3   3   182 1   2   3   181 1   2   3   181 1   1   3   180 1   1   3   180 1   0   3   178 1   0   3   178 1   1   3   176 1   1   3   176 1   2   3   175 1   2   3   175 1   
                                           3   3   174 1   3   3   174 1   5   3   174 1   5   3   174 1   6   3   174 1   6   3   174 1   7   3   175 1   7   3   175 1   8   3   176 1   8   3   176 1   9   3   178 1   7   255 252 2   178 1   13  3   178 1   7   255 5   3   170 1   5   3   186 1   
                                           7   255 9   3   70  1   8   3   72  1   8   3   72  1   7   3   73  1   7   3   73  1   6   3   74  1   6   3   74  1   5   3   74  1   5   3   74  1   3   3   74  1   3   3   74  1   2   3   73  1   2   3   73  1   1   3   72  1   1   3   72  1   0   3   
                                           70  1   0   3   70  1   1   3   69  1   1   3   69  1   2   3   67  1   2   3   67  1   3   3   66  1   3   3   66  1   5   3   66  1   5   3   66  1   6   3   66  1   6   3   66  1   7   3   67  1   7   3   67  1   8   3   69  1   8   3   69  1   9   3   
                                           70  1   7   255 252 2   70  1   13  3   70  1   7   255 5   3   62  1   5   3   79  1   7   255 14  0   70  1   138 0   70  1   138 0   70  1   138 0   103 1   138 0   103 1   25  1   103 1   25  1   103 1   25  1   146 1   25  1   146 1   138 0   146 1   
                                           138 0   146 1   138 0   178 1   138 0   178 1   14  0   178 1   14  0   178 1   14  0   70  1   7   255 14  0   70  1   14  0   70  1   7   255 14  0   70  1   14  0   70  1   7   255 14  0   70  1   14  0   70  1   7   255 9   1   135 1   7   1   137 1   
                                           7   1   137 1   4   1   138 1   4   1   138 1   1   1   139 1   1   1   139 1   254 0   140 1   254 0   140 1   251 0   139 1   251 0   139 1   249 0   138 1   249 0   138 1   246 0   137 1   246 0   137 1   244 0   135 1   244 0   135 1   242 0   133 1   
                                           242 0   133 1   240 0   130 1   240 0   130 1   239 0   127 1   239 0   127 1   239 0   124 1   239 0   124 1   239 0   121 1   239 0   121 1   240 0   118 1   240 0   118 1   242 0   116 1   242 0   116 1   244 0   113 1   244 0   113 1   246 0   111 1   
                                           246 0   111 1   249 0   110 1   249 0   110 1   251 0   109 1   251 0   109 1   254 0   109 1   254 0   109 1   1   1   109 1   1   1   109 1   4   1   110 1   4   1   110 1   7   1   111 1   7   1   111 1   9   1   113 1   7   255 9   1   113 1   9   1   
                                           135 1   7   255 205 0   93  1   205 0   101 1   205 0   101 1   211 0   103 1   211 0   103 1   245 0   103 1   245 0   103 1   251 0   101 1   251 0   101 1   251 0   93  1   251 0   93  1   245 0   91  1   245 0   91  1   211 0   91  1   211 0   91  1   
                                           205 0   93  1   7   255 205 0   72  1   205 0   80  1   205 0   80  1   211 0   82  1   211 0   82  1   245 0   82  1   245 0   82  1   251 0   80  1   251 0   80  1   251 0   72  1   251 0   72  1   245 0   70  1   245 0   70  1   211 0   70  1   211 0   
                                           70  1   205 0   72  1   7   255 205 0   148 1   205 0   155 1   205 0   155 1   211 0   157 1   211 0   157 1   245 0   157 1   245 0   157 1   251 0   155 1   251 0   155 1   251 0   148 1   251 0   148 1   245 0   146 1   245 0   146 1   211 0   146 1   
                                           211 0   146 1   205 0   148 1   7   255 205 0   169 1   205 0   176 1   205 0   176 1   211 0   178 1   211 0   178 1   245 0   178 1   245 0   178 1   251 0   176 1   251 0   176 1   251 0   169 1   251 0   169 1   245 0   166 1   245 0   166 1   211 0   
                                           166 1   211 0   166 1   205 0   169 1   7   255 2   1   93  1   2   1   101 1   2   1   101 1   8   1   103 1   8   1   103 1   41  1   103 1   41  1   103 1   48  1   101 1   48  1   101 1   48  1   93  1   48  1   93  1   41  1   91  1   41  1   91  1   
                                           8   1   91  1   8   1   91  1   2   1   93  1   7   255 2   1   72  1   2   1   80  1   2   1   80  1   8   1   82  1   8   1   82  1   41  1   82  1   41  1   82  1   48  1   80  1   48  1   80  1   48  1   72  1   48  1   72  1   41  1   70  1   41  1   
                                           70  1   8   1   70  1   8   1   70  1   2   1   72  1   7   255 2   1   148 1   2   1   155 1   2   1   155 1   8   1   157 1   8   1   157 1   41  1   157 1   41  1   157 1   48  1   155 1   48  1   155 1   48  1   148 1   48  1   148 1   41  1   146 1   
                                           41  1   146 1   8   1   146 1   8   1   146 1   2   1   148 1   7   255 2   1   169 1   2   1   176 1   2   1   176 1   8   1   178 1   8   1   178 1   41  1   178 1   41  1   178 1   48  1   176 1   48  1   176 1   48  1   169 1   48  1   169 1   41  1   
                                           166 1   41  1   166 1   8   1   166 1   8   1   166 1   2   1   169 1   7   255 20  0   169 1   20  0   176 1   20  0   176 1   26  0   178 1   26  0   178 1   60  0   178 1   60  0   178 1   66  0   176 1   66  0   176 1   66  0   169 1   66  0   169 1   
                                           60  0   166 1   60  0   166 1   26  0   166 1   26  0   166 1   20  0   169 1   7   255 20  0   72  1   20  0   80  1   20  0   80  1   26  0   82  1   26  0   82  1   60  0   82  1   60  0   82  1   66  0   80  1   66  0   80  1   66  0   72  1   66  0   
                                           72  1   60  0   70  1   60  0   70  1   26  0   70  1   26  0   70  1   20  0   72  1   7   255 18  0   70  1   18  0   72  1   18  0   72  1   17  0   73  1   17  0   73  1   16  0   74  1   16  0   74  1   14  0   74  1   14  0   74  1   12  0   74  1   
                                           12  0   74  1   11  0   73  1   11  0   73  1   10  0   72  1   10  0   72  1   10  0   70  1   10  0   70  1   10  0   69  1   10  0   69  1   11  0   67  1   11  0   67  1   12  0   66  1   12  0   66  1   14  0   66  1   14  0   66  1   16  0   66  1   
                                           16  0   66  1   17  0   67  1   17  0   67  1   18  0   69  1   18  0   69  1   18  0   70  1   7   255 6   0   70  1   22  0   70  1   7   255 14  0   62  1   14  0   79  1   7   255 18  0   178 1   18  0   180 1   18  0   180 1   17  0   181 1   17  0   
                                           181 1   16  0   182 1   16  0   182 1   14  0   182 1   14  0   182 1   12  0   182 1   12  0   182 1   11  0   181 1   11  0   181 1   10  0   180 1   10  0   180 1   10  0   178 1   10  0   178 1   10  0   176 1   10  0   176 1   11  0   175 1   11  0   
                                           175 1   12  0   174 1   12  0   174 1   14  0   174 1   14  0   174 1   16  0   174 1   16  0   174 1   17  0   175 1   17  0   175 1   18  0   176 1   18  0   176 1   18  0   178 1   7   255 6   0   178 1   22  0   178 1   7   255 14  0   170 1   14  0   
                                           186 1   7   255 47  0   178 1   47  0   180 1   47  0   180 1   46  0   181 1   46  0   181 1   45  0   182 1   45  0   182 1   43  0   182 1   43  0   182 1   41  0   182 1   41  0   182 1   40  0   181 1   40  0   181 1   39  0   180 1   39  0   180 1   
                                           39  0   178 1   39  0   178 1   39  0   176 1   39  0   176 1   40  0   175 1   40  0   175 1   41  0   174 1   41  0   174 1   43  0   174 1   43  0   174 1   45  0   174 1   45  0   174 1   46  0   175 1   46  0   175 1   47  0   176 1   47  0   176 1   
                                           47  0   178 1   7   255 35  0   178 1   51  0   178 1   7   255 43  0   170 1   43  0   186 1   7   255 47  0   70  1   47  0   72  1   47  0   72  1   46  0   73  1   46  0   73  1   45  0   74  1   45  0   74  1   43  0   74  1   43  0   74  1   41  0   
                                           74  1   41  0   74  1   40  0   73  1   40  0   73  1   39  0   72  1   39  0   72  1   39  0   70  1   39  0   70  1   39  0   69  1   39  0   69  1   40  0   67  1   40  0   67  1   41  0   66  1   41  0   66  1   43  0   66  1   43  0   66  1   45  0   
                                           66  1   45  0   66  1   46  0   67  1   46  0   67  1   47  0   69  1   47  0   69  1   47  0   70  1   7   255 35  0   70  1   51  0   70  1   7   255 43  0   62  1   43  0   79  1   7   255 47  0   124 1   47  0   126 1   47  0   126 1   46  0   127 1   
                                           46  0   127 1   45  0   128 1   45  0   128 1   43  0   128 1   43  0   128 1   41  0   128 1   41  0   128 1   40  0   127 1   40  0   127 1   39  0   126 1   39  0   126 1   39  0   124 1   39  0   124 1   39  0   123 1   39  0   123 1   40  0   121 1   
                                           40  0   121 1   41  0   120 1   41  0   120 1   43  0   120 1   43  0   120 1   45  0   120 1   45  0   120 1   46  0   121 1   46  0   121 1   47  0   123 1   47  0   123 1   47  0   124 1   7   255 35  0   124 1   51  0   124 1   7   255 43  0   116 1   
                                           43  0   132 1   7   255 3   1   178 1   2   1   180 1   2   1   180 1   1   1   181 1   1   1   181 1   0   1   182 1   0   1   182 1   254 0   182 1   254 0   182 1   253 0   182 1   253 0   182 1   252 0   181 1   252 0   181 1   251 0   180 1   251 0   
                                           180 1   250 0   178 1   250 0   178 1   251 0   176 1   251 0   176 1   252 0   175 1   252 0   175 1   253 0   174 1   253 0   174 1   254 0   174 1   254 0   174 1   0   1   174 1   0   1   174 1   1   1   175 1   1   1   175 1   2   1   176 1   2   1   
                                           176 1   3   1   178 1   7   255 246 0   178 1   7   1   178 1   7   255 254 0   170 1   254 0   186 1   7   255 3   1   124 1   2   1   126 1   2   1   126 1   1   1   127 1   1   1   127 1   0   1   128 1   0   1   128 1   254 0   128 1   254 0   128 1   
                                           253 0   128 1   253 0   128 1   252 0   127 1   252 0   127 1   251 0   126 1   251 0   126 1   250 0   124 1   250 0   124 1   251 0   123 1   251 0   123 1   252 0   121 1   252 0   121 1   253 0   120 1   253 0   120 1   254 0   120 1   254 0   120 1   
                                           )) "a")
 (_WriteStream FILE (vl-list->string (list 0   1   120 1   0   1   120 1   1   1   121 1   1   1   121 1   2   1   123 1   2   1   123 1   3   1   124 1   7   255 246 0   124 1   7   1   124 1   7   255 254 0   116 1   254 0   132 1   7   255 3   1   70  1   2   1   72  1   2   1   72  1   1   1   
                                           73  1   1   1   73  1   0   1   74  1   0   1   74  1   254 0   74  1   254 0   74  1   253 0   74  1   253 0   74  1   252 0   73  1   252 0   73  1   251 0   72  1   251 0   72  1   250 0   70  1   250 0   70  1   251 0   69  1   251 0   69  1   252 0   
                                           67  1   252 0   67  1   253 0   66  1   253 0   66  1   254 0   66  1   254 0   66  1   0   1   66  1   0   1   66  1   1   1   67  1   1   1   67  1   2   1   69  1   2   1   69  1   3   1   70  1   7   255 246 0   70  1   7   1   70  1   7   255 254 0   
                                           62  1   254 0   79  1   0   252 65  117 116 111 67  65  68  32  83  108 105 100 101 13  10  26  0   86  2   73  6   247 2   97  120 67  1   2   0   52  18  7   255 7   255 93  4   58  1   31  6   58  1   31  6   58  1   31  6   193 1   31  6   193 1   93  
                                           4   193 1   93  4   193 1   93  4   58  1   7   255 93  4   58  1   93  4   58  1   7   255 93  4   58  1   93  4   58  1   7   255 93  4   58  1   93  4   58  1   7   255 141 4   126 1   139 4   132 1   139 4   132 1   132 4   134 1   132 4   134 1   126 
                                           4   132 1   126 4   132 1   123 4   126 1   123 4   126 1   126 4   119 1   126 4   119 1   132 4   117 1   132 4   117 1   139 4   119 1   139 4   119 1   141 4   126 1   7   255 213 5   85  1   213 5   93  1   213 5   93  1   220 5   95  1   220 5   95  
                                           1   2   6   95  1   2   6   95  1   10  6   93  1   10  6   93  1   10  6   85  1   10  6   85  1   2   6   82  1   2   6   82  1   220 5   82  1   220 5   82  1   213 5   85  1   7   255 213 5   61  1   213 5   69  1   213 5   69  1   220 5   72  1   220 
                                           5   72  1   2   6   72  1   2   6   72  1   10  6   69  1   10  6   69  1   10  6   61  1   10  6   61  1   2   6   58  1   2   6   58  1   220 5   58  1   220 5   58  1   213 5   61  1   7   255 213 5   158 1   213 5   166 1   213 5   166 1   220 5   169 
                                           1   220 5   169 1   2   6   169 1   2   6   169 1   10  6   166 1   10  6   166 1   10  6   158 1   10  6   158 1   2   6   156 1   2   6   156 1   220 5   156 1   220 5   156 1   213 5   158 1   7   255 213 5   182 1   213 5   190 1   213 5   190 1   220 
                                           5   193 1   220 5   193 1   2   6   193 1   2   6   193 1   10  6   190 1   10  6   190 1   10  6   182 1   10  6   182 1   2   6   179 1   2   6   179 1   220 5   179 1   220 5   179 1   213 5   182 1   7   255 94  4   58  1   94  4   60  1   94  4   60  
                                           1   93  4   60  1   93  4   60  1   92  4   60  1   92  4   60  1   91  4   58  1   91  4   58  1   92  4   57  1   92  4   57  1   93  4   57  1   93  4   57  1   94  4   57  1   94  4   57  1   94  4   58  1   7   255 90  4   58  1   96  4   58  1   7   
                                           255 93  4   55  1   93  4   62  1   7   255 241 5   58  1   240 5   60  1   240 5   60  1   239 5   60  1   239 5   60  1   238 5   60  1   238 5   60  1   238 5   58  1   238 5   58  1   238 5   57  1   238 5   57  1   239 5   57  1   239 5   57  1   240 
                                           5   57  1   240 5   57  1   241 5   58  1   7   255 236 5   58  1   243 5   58  1   7   255 239 5   55  1   239 5   62  1   7   255 32  6   58  1   32  6   60  1   32  6   60  1   31  6   60  1   31  6   60  1   30  6   60  1   30  6   60  1   29  6   58  
                                           1   29  6   58  1   30  6   57  1   30  6   57  1   31  6   57  1   31  6   57  1   32  6   57  1   32  6   57  1   32  6   58  1   7   255 28  6   58  1   34  6   58  1   7   255 31  6   55  1   31  6   62  1   7   255 32  6   193 1   32  6   194 1   32  
                                           6   194 1   31  6   194 1   31  6   194 1   30  6   194 1   30  6   194 1   29  6   193 1   29  6   193 1   30  6   191 1   30  6   191 1   31  6   191 1   31  6   191 1   32  6   191 1   32  6   191 1   32  6   193 1   7   255 28  6   193 1   34  6   193 
                                           1   7   255 31  6   189 1   31  6   196 1   7   255 241 5   193 1   240 5   194 1   240 5   194 1   239 5   194 1   239 5   194 1   238 5   194 1   238 5   194 1   238 5   193 1   238 5   193 1   238 5   191 1   238 5   191 1   239 5   191 1   239 5   191 
                                           1   240 5   191 1   240 5   191 1   241 5   193 1   7   255 236 5   193 1   243 5   193 1   7   255 239 5   189 1   239 5   196 1   7   255 94  4   193 1   94  4   194 1   94  4   194 1   93  4   194 1   93  4   194 1   92  4   194 1   92  4   194 1   91  
                                           4   193 1   91  4   193 1   92  4   191 1   92  4   191 1   93  4   191 1   93  4   191 1   94  4   191 1   94  4   191 1   94  4   193 1   7   255 90  4   193 1   96  4   193 1   7   255 93  4   189 1   93  4   196 1   7   255 134 4   126 1   133 4   127 
                                           1   133 4   127 1   132 4   127 1   132 4   127 1   131 4   127 1   131 4   127 1   131 4   126 1   131 4   126 1   131 4   124 1   131 4   124 1   132 4   124 1   132 4   124 1   133 4   124 1   133 4   124 1   134 4   126 1   7   255 129 4   126 1   135 
                                           4   126 1   7   255 132 4   122 1   132 4   129 1   7   255 22  4   126 1   132 4   126 1   7   255 31  4   126 1   28  4   132 1   28  4   132 1   22  4   134 1   22  4   134 1   15  4   132 1   15  4   132 1   13  4   126 1   13  4   126 1   15  4   119 
                                           1   15  4   119 1   22  4   117 1   22  4   117 1   28  4   119 1   28  4   119 1   31  4   126 1   7   255 106 4   85  1   106 4   93  1   106 4   93  1   113 4   95  1   113 4   95  1   151 4   95  1   151 4   95  1   159 4   93  1   159 4   93  1   159 
                                           4   85  1   159 4   85  1   151 4   82  1   151 4   82  1   113 4   82  1   113 4   82  1   106 4   85  1   7   255 106 4   61  1   106 4   69  1   106 4   69  1   113 4   72  1   113 4   72  1   151 4   72  1   151 4   72  1   159 4   69  1   159 4   69  
                                           1   159 4   61  1   159 4   61  1   151 4   58  1   151 4   58  1   113 4   58  1   113 4   58  1   106 4   61  1   7   255 106 4   158 1   106 4   166 1   106 4   166 1   113 4   169 1   113 4   169 1   151 4   169 1   151 4   169 1   159 4   166 1   159 
                                           4   166 1   159 4   158 1   159 4   158 1   151 4   156 1   151 4   156 1   113 4   156 1   113 4   156 1   106 4   158 1   7   255 106 4   182 1   106 4   190 1   106 4   190 1   113 4   193 1   113 4   193 1   151 4   193 1   151 4   193 1   159 4   190 
                                           1   159 4   190 1   159 4   182 1   159 4   182 1   151 4   179 1   151 4   179 1   113 4   179 1   113 4   179 1   106 4   182 1   7   255 23  4   126 1   23  4   127 1   23  4   127 1   22  4   127 1   22  4   127 1   21  4   127 1   21  4   127 1   20  
                                           4   126 1   20  4   126 1   21  4   124 1   21  4   124 1   22  4   124 1   22  4   124 1   23  4   124 1   23  4   124 1   23  4   126 1   7   255 19  4   126 1   25  4   126 1   7   255 22  4   122 1   22  4   129 1   7   255 134 4   58  1   133 4   60  
                                           1   133 4   60  1   132 4   60  1   132 4   60  1   131 4   60  1   131 4   60  1   131 4   58  1   131 4   58  1   131 4   57  1   131 4   57  1   132 4   57  1   132 4   57  1   133 4   57  1   133 4   57  1   134 4   58  1   7   255 129 4   58  1   135 
                                           4   58  1   7   255 132 4   55  1   132 4   62  1   7   255 134 4   193 1   133 4   194 1   133 4   194 1   132 4   194 1   132 4   194 1   131 4   194 1   131 4   194 1   131 4   193 1   131 4   193 1   131 4   191 1   131 4   191 1   132 4   191 1   132 
                                           4   191 1   133 4   191 1   133 4   191 1   134 4   193 1   7   255 129 4   193 1   135 4   193 1   7   255 132 4   189 1   132 4   196 1   7   255 134 4   126 1   133 4   127 1   133 4   127 1   132 4   127 1   132 4   127 1   131 4   127 1   131 4   127 
                                           1   131 4   126 1   131 4   126 1   131 4   124 1   131 4   124 1   132 4   124 1   132 4   124 1   133 4   124 1   133 4   124 1   134 4   126 1   7   255 129 4   126 1   135 4   126 1   7   255 132 4   122 1   132 4   129 1   7   255 32  1   58  1   22  
                                           4   58  1   22  4   58  1   22  4   193 1   22  4   193 1   32  1   193 1   32  1   193 1   32  1   58  1   7   255 32  1   58  1   32  1   58  1   7   255 32  1   58  1   32  1   58  1   7   255 32  1   58  1   32  1   58  1   7   255 22  4   126 1   22  
                                           4   126 1   7   255 27  4   126 1   26  4   129 1   26  4   129 1   22  4   131 1   22  4   131 1   18  4   129 1   18  4   129 1   17  4   126 1   17  4   126 1   18  4   122 1   18  4   122 1   22  4   120 1   22  4   120 1   26  4   122 1   26  4   122 
                                           1   27  4   126 1   7   255 85  1   126 1   83  1   129 1   83  1   129 1   80  1   131 1   80  1   131 1   76  1   129 1   76  1   129 1   74  1   126 1   74  1   126 1   76  1   122 1   76  1   122 1   80  1   120 1   80  1   120 1   83  1   122 1   83  
                                           1   122 1   85  1   126 1   7   255 148 3   85  1   148 3   93  1   148 3   93  1   155 3   95  1   155 3   95  1   193 3   95  1   193 3   95  1   200 3   93  1   200 3   93  1   200 3   85  1   200 3   85  1   193 3   82  1   193 3   82  1   155 3   82  
                                           1   155 3   82  1   148 3   85  1   7   255 148 3   61  1   148 3   69  1   148 3   69  1   155 3   72  1   155 3   72  1   193 3   72  1   193 3   72  1   200 3   69  1   200 3   69  1   200 3   61  1   200 3   61  1   193 3   58  1   193 3   58  1   155 
                                           3   58  1   155 3   58  1   148 3   61  1   7   255 148 3   158 1   148 3   166 1   148 3   166 1   155 3   169 1   155 3   169 1   193 3   169 1   193 3   169 1   200 3   166 1   200 3   166 1   200 3   158 1   200 3   158 1   193 3   156 1   193 3   156 
                                           1   155 3   156 1   155 3   156 1   148 3   158 1   7   255 148 3   182 1   148 3   190 1   148 3   190 1   155 3   193 1   155 3   193 1   193 3   193 1   193 3   193 1   200 3   190 1   200 3   190 1   200 3   182 1   200 3   182 1   193 3   179 1   193 
                                           3   179 1   155 3   179 1   155 3   179 1   148 3   182 1   7   255 213 3   85  1   213 3   93  1   213 3   93  1   221 3   95  1   221 3   95  1   3   4   95  1   3   4   95  1   10  4   93  1   10  4   93  1   10  4   85  1   10  4   85  1   3   4   82  
                                           1   3   4   82  1   221 3   82  1   221 3   82  1   213 3   85  1   7   255 213 3   61  1   213 3   69  1   213 3   69  1   221 3   72  1   221 3   72  1   3   4   72  1   3   4   72  1   10  4   69  1   10  4   69  1   10  4   61  1   10  4   61  1   3   
                                           4   58  1   3   4   58  1   221 3   58  1   221 3   58  1   213 3   61  1   7   255 213 3   158 1   213 3   166 1   213 3   166 1   221 3   169 1   221 3   169 1   3   4   169 1   3   4   169 1   10  4   166 1   10  4   166 1   10  4   158 1   10  4   158 
                                           1   3   4   156 1   3   4   156 1   221 3   156 1   221 3   156 1   213 3   158 1   7   255 213 3   182 1   213 3   190 1   213 3   190 1   221 3   193 1   221 3   193 1   3   4   193 1   3   4   193 1   10  4   190 1   10  4   190 1   10  4   182 1   10  
                                           4   182 1   3   4   179 1   3   4   179 1   221 3   179 1   221 3   179 1   213 3   182 1   7   255 81  1   126 1   81  1   127 1   81  1   127 1   80  1   127 1   80  1   127 1   78  1   127 1   78  1   127 1   78  1   126 1   78  1   126 1   78  1   124 
                                           1   78  1   124 1   80  1   124 1   80  1   124 1   81  1   124 1   81  1   124 1   81  1   126 1   7   255 76  1   126 1   83  1   126 1   7   255 80  1   122 1   80  1   129 1   7   255 23  4   126 1   23  4   127 1   23  4   127 1   22  4   127 1   22  
                                           4   127 1   21  4   127 1   21  4   127 1   20  4   126 1   20  4   126 1   21  4   124 1   21  4   124 1   22  4   124 1   22  4   124 1   23  4   124 1   23  4   124 1   23  4   126 1   7   255 19  4   126 1   25  4   126 1   7   255 22  4   122 1   22  
                                           4   129 1   7   255 208 3   193 1   208 3   194 1   208 3   194 1   207 3   194 1   207 3   194 1   206 3   194 1   206 3   194 1   205 3   193 1   205 3   193 1   206 3   191 1   206 3   191 1   207 3   191 1   207 3   191 1   208 3   191 1   208 3   191 
                                           1   208 3   193 1   7   255 204 3   193 1   210 3   193 1   7   255 207 3   189 1   207 3   196 1   7   255 208 3   58  1   208 3   60  1   208 3   60  1   207 3   60  1   207 3   60  1   206 3   60  1   206 3   60  1   205 3   58  1   205 3   58  1   206 
                                           3   57  1   206 3   57  1   207 3   57  1   207 3   57  1   208 3   57  1   208 3   57  1   208 3   58  1   7   255 204 3   58  1   210 3   58  1   7   255 207 3   55  1   207 3   62  1   7   255 34  1   58  1   33  1   60  1   33  1   60  1   32  1   60  
                                           1   32  1   60  1   31  1   60  1   31  1   60  1   31  1   58  1   31  1   58  1   31  1   57  1   31  1   57  1   32  1   57  1   32  1   57  1   33  1   57  1   33  1   57  1   34  1   58  1   7   255 29  1   58  1   35  1   58  1   7   255 32  1   55  
                                           1   32  1   62  1   7   255 34  1   193 1   33  1   194 1   33  1   194 1   32  1   194 1   32  1   194 1   31  1   194 1   31  1   194 1   31  1   193 1   31  1   193 1   31  1   191 1   31  1   191 1   32  1   191 1   32  1   191 1   33  1   191 1   33  
                                           1   191 1   34  1   193 1   7   255 29  1   193 1   35  1   193 1   7   255 32  1   189 1   32  1   196 1   7   255 23  4   193 1   23  4   194 1   23  4   194 1   22  4   194 1   22  4   194 1   21  4   194 1   21  4   194 1   20  4   193 1   20  4   193 
                                           1   21  4   191 1   21  4   191 1   22  4   191 1   22  4   191 1   23  4   191 1   23  4   191 1   23  4   193 1   7   255 19  4   193 1   25  4   193 1   7   255 22  4   189 1   22  4   196 1   7   255 23  4   58  1   23  4   60  1   23  4   60  1   22  
                                           4   60  1   22  4   60  1   21  4   60  1   21  4   60  1   20  4   58  1   20  4   58  1   21  4   57  1   21  4   57  1   22  4   57  1   22  4   57  1   23  4   57  1   23  4   57  1   23  4   58  1   7   255 19  4   58  1   25  4   58  1   7   255 22  
                                           4   55  1   22  4   62  1   7   255 31  0   62  1   181 0   62  1   181 0   62  1   181 0   99  1   181 0   99  1   121 1   99  1   121 1   99  1   121 1   152 1   121 1   152 1   181 0   152 1   181 0   152 1   181 0   189 1   181 0   189 1   31  0   189 
                                           1   31  0   189 1   31  0   62  1   7   255 31  0   62  1   31  0   62  1   7   255 31  0   62  1   31  0   62  1   7   255 31  0   62  1   31  0   62  1   7   255 92  1   138 1   84  1   143 1   84  1   143 1   75  1   143 1   75  1   143 1   67  1   138 
                                           1   67  1   138 1   62  1   130 1   62  1   130 1   62  1   121 1   62  1   121 1   67  1   113 1   67  1   113 1   75  1   108 1   75  1   108 1   84  1   108 1   84  1   108 1   92  1   113 1   7   255 92  1   113 1   92  1   138 1   7   255 28  1   89  
                                           1   28  1   97  1   28  1   97  1   35  1   99  1   35  1   99  1   73  1   99  1   73  1   99  1   81  1   97  1   81  1   97  1   81  1   89  1   81  1   89  1   73  1   86  1   73  1   86  1   35  1   86  1   35  1   86  1   28  1   89  1   7   255 28  
                                           1   65  1   28  1   73  1   28  1   73  1   35  1   76  1   35  1   76  1   73  1   76  1   73  1   76  1   81  1   73  1   81  1   73  1   81  1   65  1   81  1   65  1   73  1   62  1   73  1   62  1   35  1   62  1   35  1   62  1   28  1   65  1   7   
                                           255 28  1   154 1   28  1   162 1   28  1   162 1   35  1   165 1   35  1   165 1   73  1   165 1   73  1   165 1   81  1   162 1   81  1   162 1   81  1   154 1   81  1   154 1   73  1   152 1   73  1   152 1   35  1   152 1   35  1   152 1   28  1   154 
                                           1   7   255 28  1   178 1   28  1   186 1   28  1   186 1   35  1   189 1   35  1   189 1   73  1   189 1   73  1   189 1   81  1   186 1   81  1   186 1   81  1   178 1   81  1   178 1   73  1   175 1   73  1   175 1   35  1   175 1   35  1   175 1   28  
                                           1   178 1   7   255 94  1   89  1   94  1   97  1   94  1   97  1   102 1   99  1   102 1   99  1   140 1   99  1   140 1   99  1   147 1   97  1   147 1   97  1   147 1   89  1   147 1   89  1   140 1   86  1   140 1   86  1   102 1   86  1   102 1   86  
                                           1   94  1   89  1   7   255 94  1   65  1   94  1   73  1   94  1   73  1   102 1   76  1   102 1   76  1   140 1   76  1   140 1   76  1   147 1   73  1   147 1   73  1   147 1   65  1   147 1   65  1   140 1   62  1   140 1   62  1   102 1   62  1   102 
                                           1   62  1   94  1   65  1   7   255 94  1   154 1   94  1   162 1   94  1   162 1   102 1   165 1   102 1   165 1   140 1   165 1   140 1   165 1   147 1   162 1   147 1   162 1   147 1   154 1   147 1   154 1   140 1   152 1   140 1   152 1   102 1   152 
                                           1   102 1   152 1   94  1   154 1   7   255 94  1   178 1   94  1   186 1   94  1   186 1   102 1   189 1   102 1   189 1   140 1   189 1   140 1   189 1   147 1   186 1   147 1   186 1   147 1   178 1   147 1   178 1   140 1   175 1   140 1   175 1   102 
                                           1   175 1   102 1   175 1   94  1   178 1   7   255 32  0   62  1   32  0   64  1   32  0   64  1   31  0   64  1   31  0   64  1   30  0   64  1   30  0   64  1   29  0   62  1   29  0   62  1   30  0   61  1   30  0   61  1   31  0   61  1   31  0   61  
                                           )) "a")
 (_WriteStream FILE (vl-list->string (list 1   32  0   61  1   32  0   61  1   32  0   62  1   7   255 28  0   62  1   34  0   62  1   7   255 31  0   59  1   31  0   66  1   7   255 69  0   62  1   68  0   64  1   68  0   64  1   67  0   64  1   67  0   64  1   66  0   64  1   66  0   64  1   66  
                                           0   62  1   66  0   62  1   66  0   61  1   66  0   61  1   67  0   61  1   67  0   61  1   68  0   61  1   68  0   61  1   69  0   62  1   7   255 64  0   62  1   70  0   62  1   7   255 67  0   59  1   67  0   66  1   7   255 32  0   189 1   32  0   190 
                                           1   32  0   190 1   31  0   190 1   31  0   190 1   30  0   190 1   30  0   190 1   29  0   189 1   29  0   189 1   30  0   187 1   30  0   187 1   31  0   187 1   31  0   187 1   32  0   187 1   32  0   187 1   32  0   189 1   7   255 28  0   189 1   34  
                                           0   189 1   7   255 31  0   185 1   31  0   192 1   7   255 69  0   189 1   68  0   190 1   68  0   190 1   67  0   190 1   67  0   190 1   66  0   190 1   66  0   190 1   66  0   189 1   66  0   189 1   66  0   187 1   66  0   187 1   67  0   187 1   67  
                                           0   187 1   68  0   187 1   68  0   187 1   69  0   189 1   7   255 64  0   189 1   70  0   189 1   7   255 67  0   185 1   67  0   192 1   7   255 81  1   126 1   81  1   127 1   81  1   127 1   80  1   127 1   80  1   127 1   78  1   127 1   78  1   127 
                                           1   78  1   126 1   78  1   126 1   78  1   124 1   78  1   124 1   80  1   124 1   80  1   124 1   81  1   124 1   81  1   124 1   81  1   126 1   7   255 76  1   126 1   83  1   126 1   7   255 80  1   122 1   80  1   129 1   7   255 89  1   189 1   89  
                                           1   190 1   89  1   190 1   87  1   190 1   87  1   190 1   86  1   190 1   86  1   190 1   86  1   189 1   86  1   189 1   86  1   187 1   86  1   187 1   87  1   187 1   87  1   187 1   89  1   187 1   89  1   187 1   89  1   189 1   7   255 84  1   189 
                                           1   91  1   189 1   7   255 87  1   185 1   87  1   192 1   7   255 89  1   62  1   89  1   64  1   89  1   64  1   87  1   64  1   87  1   64  1   86  1   64  1   86  1   64  1   86  1   62  1   86  1   62  1   86  1   61  1   86  1   61  1   87  1   61  
                                           1   87  1   61  1   89  1   61  1   89  1   61  1   89  1   62  1   7   255 84  1   62  1   91  1   62  1   7   255 87  1   59  1   87  1   66  1   7   255 69  0   126 1   68  0   127 1   68  0   127 1   67  0   127 1   67  0   127 1   66  0   127 1   66  
                                           0   127 1   66  0   126 1   66  0   126 1   66  0   124 1   66  0   124 1   67  0   124 1   67  0   124 1   68  0   124 1   68  0   124 1   69  0   126 1   7   255 64  0   126 1   70  0   126 1   7   255 67  0   122 1   67  0   129 1   7   255 41  0   65  
                                           1   41  0   73  1   41  0   73  1   48  0   76  1   48  0   76  1   86  0   76  1   86  0   76  1   94  0   73  1   94  0   73  1   94  0   65  1   94  0   65  1   86  0   62  1   86  0   62  1   48  0   62  1   48  0   62  1   41  0   65  1   7   255 41  
                                           0   178 1   41  0   186 1   41  0   186 1   48  0   189 1   48  0   189 1   86  0   189 1   86  0   189 1   94  0   186 1   94  0   186 1   94  0   178 1   94  0   178 1   86  0   175 1   86  0   175 1   48  0   175 1   48  0   175 1   41  0   178 1   0   
                                           252 65  117 116 111 67  65  68  32  83  108 105 100 101 13  10  26  0   86  2   73  6   247 2   97  120 67  1   2   0   52  18  51  255 51  255 96  0   175 0   217 5   175 0   217 5   175 0   217 5   63  2   217 5   63  2   96  0   63  2   96  0   63  2   
                                           96  0   175 0   7   255 7   255 96  0   175 0   217 5   175 0   217 5   175 0   217 5   63  2   7   255 217 5   63  2   96  0   63  2   7   255 96  0   63  2   96  0   175 0   7   255 96  0   175 0   96  0   175 0   7   255 96  0   175 0   96  0   175 0   
                                           7   255 96  0   175 0   96  0   175 0   7   255 118 4   252 0   118 4   21  1   118 4   21  1   140 4   28  1   140 4   28  1   252 4   28  1   252 4   28  1   18  5   21  1   18  5   21  1   18  5   252 0   18  5   252 0   252 4   245 0   252 4   245 0   
                                           140 4   245 0   140 4   245 0   118 4   252 0   7   255 118 4   182 0   118 4   206 0   118 4   206 0   140 4   214 0   140 4   214 0   252 4   214 0   252 4   214 0   18  5   206 0   18  5   206 0   18  5   182 0   18  5   182 0   252 4   175 0   252 4   
                                           175 0   140 4   175 0   140 4   175 0   118 4   182 0   7   255 118 4   217 1   118 4   241 1   118 4   241 1   140 4   248 1   140 4   248 1   252 4   248 1   252 4   248 1   18  5   241 1   18  5   241 1   18  5   217 1   18  5   217 1   252 4   209 1   
                                           252 4   209 1   140 4   209 1   140 4   209 1   118 4   217 1   7   255 118 4   31  2   118 4   55  2   118 4   55  2   140 4   63  2   140 4   63  2   252 4   63  2   252 4   63  2   18  5   55  2   18  5   55  2   18  5   31  2   18  5   31  2   252 4   
                                           24  2   252 4   24  2   140 4   24  2   140 4   24  2   118 4   31  2   7   255 202 0   31  2   202 0   55  2   202 0   55  2   224 0   63  2   224 0   63  2   81  1   63  2   81  1   63  2   103 1   55  2   103 1   55  2   103 1   31  2   103 1   31  2   
                                           81  1   24  2   81  1   24  2   224 0   24  2   224 0   24  2   202 0   31  2   7   255 202 0   182 0   202 0   206 0   202 0   206 0   224 0   214 0   224 0   214 0   81  1   214 0   81  1   214 0   103 1   206 0   103 1   206 0   103 1   182 0   103 1   
                                           182 0   81  1   175 0   81  1   175 0   224 0   175 0   224 0   175 0   202 0   182 0   7   255 40  1   119 1   39  1   125 1   39  1   125 1   36  1   130 1   36  1   130 1   31  1   133 1   31  1   133 1   25  1   134 1   25  1   134 1   19  1   133 1   
                                           19  1   133 1   14  1   130 1   14  1   130 1   10  1   125 1   10  1   125 1   9   1   119 1   9   1   119 1   10  1   113 1   10  1   113 1   14  1   108 1   14  1   108 1   19  1   105 1   19  1   105 1   25  1   103 1   25  1   103 1   31  1   105 1   
                                           31  1   105 1   36  1   108 1   36  1   108 1   39  1   113 1   39  1   113 1   40  1   119 1   7   255 250 0   119 1   55  1   119 1   7   255 25  1   88  1   25  1   150 1   7   255 111 0   175 0   110 0   181 0   110 0   181 0   107 0   186 0   107 0   
                                           186 0   102 0   189 0   102 0   189 0   96  0   190 0   96  0   190 0   90  0   189 0   90  0   189 0   85  0   186 0   85  0   186 0   82  0   181 0   82  0   181 0   80  0   175 0   80  0   175 0   82  0   169 0   82  0   169 0   85  0   164 0   85  0   
                                           164 0   90  0   161 0   90  0   161 0   96  0   159 0   96  0   159 0   102 0   161 0   102 0   161 0   107 0   164 0   107 0   164 0   110 0   169 0   110 0   169 0   111 0   175 0   7   255 65  0   175 0   127 0   175 0   7   255 96  0   144 0   96  0   
                                           206 0   7   255 111 0   63  2   110 0   69  2   110 0   69  2   107 0   74  2   107 0   74  2   102 0   77  2   102 0   77  2   96  0   78  2   96  0   78  2   90  0   77  2   90  0   77  2   85  0   74  2   85  0   74  2   82  0   69  2   82  0   69  2   
                                           80  0   63  2   80  0   63  2   82  0   57  2   82  0   57  2   85  0   52  2   85  0   52  2   90  0   49  2   90  0   49  2   96  0   47  2   96  0   47  2   102 0   49  2   102 0   49  2   107 0   52  2   107 0   52  2   110 0   57  2   110 0   57  2   
                                           111 0   63  2   7   255 65  0   63  2   127 0   63  2   7   255 96  0   32  2   96  0   94  2   7   255 232 5   63  2   231 5   69  2   231 5   69  2   228 5   74  2   228 5   74  2   223 5   77  2   223 5   77  2   217 5   78  2   217 5   78  2   211 5   
                                           77  2   211 5   77  2   206 5   74  2   206 5   74  2   203 5   69  2   203 5   69  2   202 5   63  2   202 5   63  2   203 5   57  2   203 5   57  2   206 5   52  2   206 5   52  2   211 5   49  2   211 5   49  2   217 5   47  2   217 5   47  2   223 5   
                                           49  2   223 5   49  2   228 5   52  2   228 5   52  2   231 5   57  2   231 5   57  2   232 5   63  2   7   255 186 5   63  2   248 5   63  2   7   255 217 5   32  2   217 5   94  2   7   255 232 5   175 0   231 5   181 0   231 5   181 0   228 5   186 0   
                                           228 5   186 0   223 5   189 0   223 5   189 0   217 5   190 0   217 5   190 0   211 5   189 0   211 5   189 0   206 5   186 0   206 5   186 0   203 5   181 0   203 5   181 0   202 5   175 0   202 5   175 0   203 5   169 0   203 5   169 0   206 5   164 0   
                                           206 5   164 0   211 5   161 0   211 5   161 0   217 5   159 0   217 5   159 0   223 5   161 0   223 5   161 0   228 5   164 0   228 5   164 0   231 5   169 0   231 5   169 0   232 5   175 0   7   255 186 5   175 0   248 5   175 0   7   255 217 5   144 0   
                                           217 5   206 0   7   255 40  1   175 0   39  1   181 0   39  1   181 0   36  1   186 0   36  1   186 0   31  1   189 0   31  1   189 0   25  1   190 0   25  1   190 0   19  1   189 0   19  1   189 0   14  1   186 0   14  1   186 0   10  1   181 0   10  1   
                                           181 0   9   1   175 0   9   1   175 0   10  1   169 0   10  1   169 0   14  1   164 0   14  1   164 0   19  1   161 0   19  1   161 0   25  1   159 0   25  1   159 0   31  1   161 0   31  1   161 0   36  1   164 0   36  1   164 0   39  1   169 0   39  1   
                                           169 0   40  1   175 0   7   255 250 0   175 0   55  1   175 0   7   255 25  1   144 0   25  1   206 0   7   255 40  1   63  2   39  1   69  2   39  1   69  2   36  1   74  2   36  1   74  2   31  1   77  2   31  1   77  2   25  1   78  2   25  1   78  2   
                                           19  1   77  2   19  1   77  2   14  1   74  2   14  1   74  2   10  1   69  2   10  1   69  2   9   1   63  2   9   1   63  2   10  1   57  2   10  1   57  2   14  1   52  2   14  1   52  2   19  1   49  2   19  1   49  2   25  1   47  2   25  1   47  2   
                                           31  1   49  2   31  1   49  2   36  1   52  2   36  1   52  2   39  1   57  2   39  1   57  2   40  1   63  2   7   255 250 0   63  2   55  1   63  2   7   255 25  1   32  2   25  1   94  2   7   255 211 4   63  2   210 4   69  2   210 4   69  2   207 4   
                                           74  2   207 4   74  2   202 4   77  2   202 4   77  2   196 4   78  2   196 4   78  2   190 4   77  2   190 4   77  2   185 4   74  2   185 4   74  2   182 4   69  2   182 4   69  2   180 4   63  2   180 4   63  2   182 4   57  2   182 4   57  2   185 4   
                                           52  2   185 4   52  2   190 4   49  2   190 4   49  2   196 4   47  2   196 4   47  2   202 4   49  2   202 4   49  2   207 4   52  2   207 4   52  2   210 4   57  2   210 4   57  2   211 4   63  2   7   255 165 4   63  2   227 4   63  2   7   255 196 4   
                                           32  2   196 4   94  2   7   255 211 4   175 0   210 4   181 0   210 4   181 0   207 4   186 0   207 4   186 0   202 4   189 0   202 4   189 0   196 4   190 0   196 4   190 0   190 4   189 0   190 4   189 0   185 4   186 0   185 4   186 0   182 4   181 0   
                                           182 4   181 0   180 4   175 0   180 4   175 0   182 4   169 0   182 4   169 0   185 4   164 0   185 4   164 0   190 4   161 0   190 4   161 0   196 4   159 0   196 4   159 0   202 4   161 0   202 4   161 0   207 4   164 0   207 4   164 0   210 4   169 0   
                                           210 4   169 0   211 4   175 0   7   255 165 4   175 0   227 4   175 0   7   255 196 4   144 0   196 4   206 0   0   252 65  117 116 111 67  65  68  32  83  108 105 100 101 13  10  26  0   86  2   73  6   247 2   97  120 67  1   2   0   52  18  51  255 51  
                                           255 115 0   35  1   137 2   35  1   137 2   35  1   137 2   231 1   137 2   231 1   115 0   231 1   115 0   231 1   115 0   35  1   7   255 7   255 115 0   35  1   137 2   35  1   137 2   35  1   137 2   231 1   137 2   231 1   115 0   231 1   115 0   231 
                                           1   115 0   35  1   7   255 115 0   35  1   115 0   35  1   7   255 115 0   35  1   115 0   35  1   7   255 115 0   35  1   115 0   35  1   7   255 224 1   52  1   224 1   61  1   224 1   61  1   232 1   64  1   232 1   64  1   18  2   64  1   18  2   64  
                                           1   26  2   61  1   26  2   61  1   26  2   52  1   26  2   52  1   18  2   49  1   18  2   49  1   232 1   49  1   232 1   49  1   224 1   52  1   7   255 224 1   206 1   224 1   215 1   224 1   215 1   232 1   217 1   232 1   217 1   18  2   217 1   18  
                                           2   217 1   26  2   215 1   26  2   215 1   26  2   206 1   26  2   206 1   18  2   203 1   18  2   203 1   232 1   203 1   232 1   203 1   224 1   206 1   7   255 203 0   133 1   202 0   135 1   202 0   135 1   201 0   136 1   201 0   136 1   200 0   136 
                                           1   200 0   136 1   198 0   136 1   198 0   136 1   197 0   135 1   197 0   135 1   197 0   133 1   197 0   133 1   197 0   132 1   197 0   132 1   198 0   131 1   198 0   131 1   200 0   130 1   200 0   130 1   201 0   131 1   201 0   131 1   202 0   132 
                                           1   202 0   132 1   203 0   133 1   7   255 194 0   133 1   205 0   133 1   7   255 200 0   128 1   200 0   139 1   7   255 203 0   217 1   202 0   219 1   202 0   219 1   201 0   220 1   201 0   220 1   200 0   220 1   200 0   220 1   198 0   220 1   198 
                                           0   220 1   197 0   219 1   197 0   219 1   197 0   217 1   197 0   217 1   197 0   216 1   197 0   216 1   198 0   215 1   198 0   215 1   200 0   215 1   200 0   215 1   201 0   215 1   201 0   215 1   202 0   216 1   202 0   216 1   203 0   217 1   7   
                                           255 194 0   217 1   205 0   217 1   7   255 200 0   212 1   200 0   223 1   7   255 203 0   49  1   202 0   50  1   202 0   50  1   201 0   51  1   201 0   51  1   200 0   52  1   200 0   52  1   198 0   51  1   198 0   51  1   197 0   50  1   197 0   50  
                                           1   197 0   49  1   197 0   49  1   197 0   47  1   197 0   47  1   198 0   46  1   198 0   46  1   200 0   46  1   200 0   46  1   201 0   46  1   201 0   46  1   202 0   47  1   202 0   47  1   203 0   49  1   7   255 194 0   49  1   205 0   49  1   7   
                                           255 200 0   43  1   200 0   55  1   7   255 118 0   231 1   118 0   233 1   118 0   233 1   117 0   234 1   117 0   234 1   115 0   234 1   115 0   234 1   114 0   234 1   114 0   234 1   113 0   233 1   113 0   233 1   113 0   231 1   113 0   231 1   113 
                                           0   230 1   113 0   230 1   114 0   229 1   114 0   229 1   115 0   229 1   115 0   229 1   117 0   229 1   117 0   229 1   118 0   230 1   118 0   230 1   118 0   231 1   7   255 110 0   231 1   121 0   231 1   7   255 115 0   226 1   115 0   237 1   7   
                                           255 118 0   35  1   118 0   36  1   118 0   36  1   117 0   37  1   117 0   37  1   115 0   38  1   115 0   38  1   114 0   37  1   114 0   37  1   113 0   36  1   113 0   36  1   113 0   35  1   113 0   35  1   113 0   33  1   113 0   33  1   114 0   32  
                                           1   114 0   32  1   115 0   32  1   115 0   32  1   117 0   32  1   117 0   32  1   118 0   33  1   118 0   33  1   118 0   35  1   7   255 110 0   35  1   121 0   35  1   7   255 115 0   29  1   115 0   40  1   7   255 0   2   49  1   255 1   50  1   255 
                                           1   50  1   254 1   51  1   254 1   51  1   253 1   52  1   253 1   52  1   252 1   51  1   252 1   51  1   251 1   50  1   251 1   50  1   250 1   49  1   250 1   49  1   251 1   47  1   251 1   47  1   252 1   46  1   252 1   46  1   253 1   46  1   253 
                                           1   46  1   254 1   46  1   254 1   46  1   255 1   47  1   255 1   47  1   0   2   49  1   7   255 247 1   49  1   3   2   49  1   7   255 253 1   43  1   253 1   55  1   7   255 0   2   217 1   255 1   219 1   255 1   219 1   254 1   220 1   254 1   220 
                                           1   253 1   220 1   253 1   220 1   252 1   220 1   252 1   220 1   251 1   219 1   251 1   219 1   250 1   217 1   250 1   217 1   251 1   216 1   251 1   216 1   252 1   215 1   252 1   215 1   253 1   215 1   253 1   215 1   254 1   215 1   254 1   215 
                                           1   255 1   216 1   255 1   216 1   0   2   217 1   7   255 247 1   217 1   3   2   217 1   7   255 253 1   212 1   253 1   223 1   7   255 140 2   231 1   140 2   233 1   140 2   233 1   139 2   234 1   139 2   234 1   137 2   234 1   137 2   234 1   136 
                                           2   234 1   136 2   234 1   135 2   233 1   135 2   233 1   135 2   231 1   135 2   231 1   135 2   230 1   135 2   230 1   136 2   229 1   136 2   229 1   137 2   229 1   137 2   229 1   139 2   229 1   139 2   229 1   140 2   230 1   140 2   230 1   140 
                                           2   231 1   7   255 132 2   231 1   143 2   231 1   7   255 137 2   226 1   137 2   237 1   7   255 140 2   35  1   140 2   36  1   140 2   36  1   139 2   37  1   139 2   37  1   137 2   38  1   137 2   38  1   136 2   37  1   136 2   37  1   135 2   36  
                                           1   135 2   36  1   135 2   35  1   135 2   35  1   135 2   33  1   135 2   33  1   136 2   32  1   136 2   32  1   137 2   32  1   137 2   32  1   139 2   32  1   139 2   32  1   140 2   33  1   140 2   33  1   140 2   35  1   7   255 132 2   35  1   143 
                                           2   35  1   7   255 137 2   29  1   137 2   40  1   7   255 140 2   133 1   140 2   135 1   140 2   135 1   139 2   136 1   139 2   136 1   137 2   136 1   137 2   136 1   136 2   136 1   136 2   136 1   135 2   135 1   135 2   135 1   135 2   133 1   135 
                                           2   133 1   135 2   132 1   135 2   132 1   136 2   131 1   136 2   131 1   137 2   130 1   137 2   130 1   139 2   131 1   139 2   131 1   140 2   132 1   140 2   132 1   140 2   133 1   7   255 132 2   133 1   143 2   133 1   7   255 137 2   128 1   137 
                                           )) "a")
 (_WriteStream FILE (vl-list->string (list 2   139 1   7   255 171 0   52  1   171 0   61  1   171 0   61  1   179 0   64  1   179 0   64  1   221 0   64  1   221 0   64  1   229 0   61  1   229 0   61  1   229 0   52  1   229 0   52  1   221 0   49  1   221 0   49  1   179 0   49  1   179 0   49  
                                           1   171 0   52  1   7   255 171 0   206 1   171 0   215 1   171 0   215 1   179 0   217 1   179 0   217 1   221 0   217 1   221 0   217 1   229 0   215 1   229 0   215 1   229 0   206 1   229 0   206 1   221 0   203 1   221 0   203 1   179 0   203 1   179 
                                           0   203 1   171 0   206 1   51  255 51  255 137 2   133 1   222 2   245 1   222 2   245 1   204 5   245 1   204 5   245 1   204 5   21  1   204 5   21  1   222 2   21  1   222 2   21  1   137 2   133 1   7   255 7   255 222 2   21  1   204 5   21  1   204 
                                           5   21  1   204 5   245 1   204 5   245 1   222 2   245 1   222 2   245 1   222 2   21  1   7   255 222 2   21  1   222 2   21  1   7   255 222 2   21  1   222 2   21  1   7   255 222 2   21  1   222 2   21  1   7   255 137 2   133 1   222 2   133 1   7   
                                           255 152 2   133 1   152 2   138 1   152 2   138 1   150 2   142 1   150 2   142 1   146 2   145 1   146 2   145 1   142 2   147 1   142 2   147 1   137 2   148 1   137 2   148 1   133 2   147 1   133 2   147 1   129 2   145 1   129 2   145 1   125 2   142 
                                           1   125 2   142 1   123 2   138 1   123 2   138 1   122 2   133 1   122 2   133 1   123 2   129 1   123 2   129 1   125 2   124 1   125 2   124 1   129 2   121 1   129 2   121 1   133 2   119 1   133 2   119 1   137 2   118 1   137 2   118 1   142 2   119 
                                           1   142 2   119 1   146 2   121 1   146 2   121 1   150 2   124 1   150 2   124 1   152 2   129 1   152 2   129 1   152 2   133 1   7   255 32  4   24  1   32  4   33  1   32  4   33  1   41  4   35  1   41  4   35  1   88  4   35  1   88  4   35  1   97  
                                           4   33  1   97  4   33  1   97  4   24  1   97  4   24  1   88  4   21  1   88  4   21  1   41  4   21  1   41  4   21  1   32  4   24  1   7   255 32  4   234 1   32  4   243 1   32  4   243 1   41  4   245 1   41  4   245 1   88  4   245 1   88  4   245 
                                           1   97  4   243 1   97  4   243 1   97  4   234 1   97  4   234 1   88  4   231 1   88  4   231 1   41  4   231 1   41  4   231 1   32  4   234 1   7   255 149 4   24  1   149 4   33  1   149 4   33  1   158 4   35  1   158 4   35  1   205 4   35  1   205 
                                           4   35  1   214 4   33  1   214 4   33  1   214 4   24  1   214 4   24  1   205 4   21  1   205 4   21  1   158 4   21  1   158 4   21  1   149 4   24  1   7   255 149 4   234 1   149 4   243 1   149 4   243 1   158 4   245 1   158 4   245 1   205 4   245 
                                           1   205 4   245 1   214 4   243 1   214 4   243 1   214 4   234 1   214 4   234 1   205 4   231 1   205 4   231 1   158 4   231 1   158 4   231 1   149 4   234 1   7   255 140 2   133 1   139 2   135 1   139 2   135 1   137 2   136 1   137 2   136 1   135 
                                           2   135 1   135 2   135 1   135 2   133 1   135 2   133 1   135 2   131 1   135 2   131 1   137 2   130 1   137 2   130 1   139 2   131 1   139 2   131 1   140 2   133 1   7   255 132 2   133 1   143 2   133 1   7   255 137 2   128 1   137 2   139 1   7   
                                           255 225 2   21  1   224 2   23  1   224 2   23  1   222 2   24  1   222 2   24  1   220 2   23  1   220 2   23  1   219 2   21  1   219 2   21  1   220 2   19  1   220 2   19  1   222 2   18  1   222 2   18  1   224 2   19  1   224 2   19  1   225 2   21  
                                           1   7   255 216 2   21  1   227 2   21  1   7   255 222 2   15  1   222 2   26  1   7   255 225 2   245 1   224 2   247 1   224 2   247 1   222 2   248 1   222 2   248 1   220 2   247 1   220 2   247 1   219 2   245 1   219 2   245 1   220 2   244 1   220 
                                           2   244 1   222 2   243 1   222 2   243 1   224 2   244 1   224 2   244 1   225 2   245 1   7   255 216 2   245 1   227 2   245 1   7   255 222 2   240 1   222 2   251 1   7   255 207 5   245 1   206 5   247 1   206 5   247 1   204 5   248 1   204 5   248 
                                           1   202 5   247 1   202 5   247 1   201 5   245 1   201 5   245 1   202 5   244 1   202 5   244 1   204 5   243 1   204 5   243 1   206 5   244 1   206 5   244 1   207 5   245 1   7   255 199 5   245 1   210 5   245 1   7   255 204 5   240 1   204 5   251 
                                           1   7   255 207 5   21  1   206 5   23  1   206 5   23  1   204 5   24  1   204 5   24  1   202 5   23  1   202 5   23  1   201 5   21  1   201 5   21  1   202 5   19  1   202 5   19  1   204 5   18  1   204 5   18  1   206 5   19  1   206 5   19  1   207 
                                           5   21  1   7   255 199 5   21  1   210 5   21  1   7   255 204 5   15  1   204 5   26  1   7   255 126 4   21  1   125 4   23  1   125 4   23  1   123 4   24  1   123 4   24  1   121 4   23  1   121 4   23  1   120 4   21  1   120 4   21  1   121 4   19  
                                           1   121 4   19  1   123 4   18  1   123 4   18  1   125 4   19  1   125 4   19  1   126 4   21  1   7   255 117 4   21  1   129 4   21  1   7   255 123 4   15  1   123 4   26  1   7   255 126 4   245 1   125 4   247 1   125 4   247 1   123 4   248 1   123 
                                           4   248 1   121 4   247 1   121 4   247 1   120 4   245 1   120 4   245 1   121 4   244 1   121 4   244 1   123 4   243 1   123 4   243 1   125 4   244 1   125 4   244 1   126 4   245 1   7   255 117 4   245 1   129 4   245 1   7   255 123 4   240 1   123 
                                           4   251 1   0   252 65  117 116 111 67  65  68  32  83  108 105 100 101 13  10  26  0   86  2   73  6   247 2   97  120 67  1   2   0   52  18  7   255 7   255 249 1   240 0   19  6   240 0   19  6   240 0   19  6   241 1   19  6   241 1   249 1   241 1   
                                           249 1   241 1   249 1   240 0   7   255 249 1   240 0   249 1   240 0   7   255 249 1   240 0   249 1   240 0   7   255 249 1   240 0   249 1   240 0   7   255 178 4   39  1   178 4   56  1   178 4   56  1   194 4   62  1   194 4   62  1   17  5   62  1   
                                           17  5   62  1   33  5   56  1   33  5   56  1   33  5   39  1   33  5   39  1   17  5   34  1   17  5   34  1   194 4   34  1   194 4   34  1   178 4   39  1   7   255 178 4   245 0   178 4   7   1   178 4   7   1   194 4   12  1   194 4   12  1   17  5   
                                           12  1   17  5   12  1   33  5   7   1   33  5   7   1   33  5   245 0   33  5   245 0   17  5   240 0   17  5   240 0   194 4   240 0   194 4   240 0   178 4   245 0   7   255 178 4   169 1   178 4   186 1   178 4   186 1   194 4   192 1   194 4   192 1   
                                           17  5   192 1   17  5   192 1   33  5   186 1   33  5   186 1   33  5   169 1   33  5   169 1   17  5   164 1   17  5   164 1   194 4   164 1   194 4   164 1   178 4   169 1   7   255 178 4   219 1   178 4   236 1   178 4   236 1   194 4   241 1   194 4   
                                           241 1   17  5   241 1   17  5   241 1   33  5   236 1   33  5   236 1   33  5   219 1   33  5   219 1   17  5   214 1   17  5   214 1   194 4   214 1   194 4   214 1   178 4   219 1   7   255 41  5   39  1   41  5   56  1   41  5   56  1   56  5   62  1   
                                           56  5   62  1   136 5   62  1   136 5   62  1   152 5   56  1   152 5   56  1   152 5   39  1   152 5   39  1   136 5   34  1   136 5   34  1   56  5   34  1   56  5   34  1   41  5   39  1   7   255 41  5   245 0   41  5   7   1   41  5   7   1   56  5   
                                           12  1   56  5   12  1   136 5   12  1   136 5   12  1   152 5   7   1   152 5   7   1   152 5   245 0   152 5   245 0   136 5   240 0   136 5   240 0   56  5   240 0   56  5   240 0   41  5   245 0   7   255 41  5   169 1   41  5   186 1   41  5   186 1   
                                           56  5   192 1   56  5   192 1   136 5   192 1   136 5   192 1   152 5   186 1   152 5   186 1   152 5   169 1   152 5   169 1   136 5   164 1   136 5   164 1   56  5   164 1   56  5   164 1   41  5   169 1   7   255 41  5   219 1   41  5   236 1   41  5   
                                           236 1   56  5   241 1   56  5   241 1   136 5   241 1   136 5   241 1   152 5   236 1   152 5   236 1   152 5   219 1   152 5   219 1   136 5   214 1   136 5   214 1   56  5   214 1   56  5   214 1   41  5   219 1   7   255 62  2   113 1   61  2   118 1   
                                           61  2   118 1   57  2   121 1   57  2   121 1   52  2   123 1   52  2   123 1   47  2   121 1   47  2   121 1   44  2   118 1   44  2   118 1   42  2   113 1   42  2   113 1   44  2   108 1   44  2   108 1   47  2   104 1   47  2   104 1   52  2   103 1   
                                           52  2   103 1   57  2   104 1   57  2   104 1   61  2   108 1   61  2   108 1   62  2   113 1   7   255 32  2   113 1   72  2   113 1   7   255 52  2   93  1   52  2   133 1   7   255 47  5   241 1   45  5   246 1   45  5   246 1   42  5   250 1   42  5   
                                           250 1   37  5   251 1   37  5   251 1   32  5   250 1   32  5   250 1   28  5   246 1   28  5   246 1   27  5   241 1   27  5   241 1   28  5   236 1   28  5   236 1   32  5   233 1   32  5   233 1   37  5   232 1   37  5   232 1   42  5   233 1   42  5   
                                           233 1   45  5   236 1   45  5   236 1   47  5   241 1   7   255 17  5   241 1   57  5   241 1   7   255 37  5   222 1   37  5   5   2   7   255 47  5   240 0   45  5   245 0   45  5   245 0   42  5   249 0   42  5   249 0   37  5   250 0   37  5   250 0   
                                           32  5   249 0   32  5   249 0   28  5   245 0   28  5   245 0   27  5   240 0   27  5   240 0   28  5   235 0   28  5   235 0   32  5   232 0   32  5   232 0   37  5   230 0   37  5   230 0   42  5   232 0   42  5   232 0   45  5   235 0   45  5   235 0   
                                           47  5   240 0   7   255 17  5   240 0   57  5   240 0   7   255 37  5   220 0   37  5   4   1   7   255 28  6   240 0   27  6   245 0   27  6   245 0   23  6   249 0   23  6   249 0   19  6   250 0   19  6   250 0   14  6   249 0   14  6   249 0   10  6   
                                           245 0   10  6   245 0   9   6   240 0   9   6   240 0   10  6   235 0   10  6   235 0   14  6   232 0   14  6   232 0   19  6   230 0   19  6   230 0   23  6   232 0   23  6   232 0   27  6   235 0   27  6   235 0   28  6   240 0   7   255 255 5   240 0   
                                           38  6   240 0   7   255 19  6   220 0   19  6   4   1   7   255 28  6   241 1   27  6   246 1   27  6   246 1   23  6   250 1   23  6   250 1   19  6   251 1   19  6   251 1   14  6   250 1   14  6   250 1   10  6   246 1   10  6   246 1   9   6   241 1   
                                           9   6   241 1   10  6   236 1   10  6   236 1   14  6   233 1   14  6   233 1   19  6   232 1   19  6   232 1   23  6   233 1   23  6   233 1   27  6   236 1   27  6   236 1   28  6   241 1   7   255 255 5   241 1   38  6   241 1   7   255 19  6   222 1   
                                           19  6   5   2   7   255 3   2   240 0   1   2   245 0   1   2   245 0   254 1   249 0   254 1   249 0   249 1   250 0   249 1   250 0   244 1   249 0   244 1   249 0   240 1   245 0   240 1   245 0   239 1   240 0   239 1   240 0   240 1   235 0   240 1   
                                           235 0   244 1   232 0   244 1   232 0   249 1   230 0   249 1   230 0   254 1   232 0   254 1   232 0   1   2   235 0   1   2   235 0   3   2   240 0   7   255 229 1   240 0   13  2   240 0   7   255 249 1   220 0   249 1   4   1   7   255 3   2   241 1   
                                           1   2   246 1   1   2   246 1   254 1   250 1   254 1   250 1   249 1   251 1   249 1   251 1   244 1   250 1   244 1   250 1   240 1   246 1   240 1   246 1   239 1   241 1   239 1   241 1   240 1   236 1   240 1   236 1   244 1   233 1   244 1   233 1   
                                           249 1   232 1   249 1   232 1   254 1   233 1   254 1   233 1   1   2   236 1   1   2   236 1   3   2   241 1   7   255 229 1   241 1   13  2   241 1   7   255 249 1   222 1   249 1   5   2   7   255 49  0   240 0   90  1   240 0   90  1   240 0   90  1   
                                           62  1   90  1   62  1   52  2   62  1   52  2   62  1   52  2   164 1   52  2   164 1   90  1   164 1   90  1   164 1   90  1   241 1   90  1   241 1   49  0   241 1   49  0   241 1   49  0   240 0   7   255 49  0   240 0   49  0   240 0   7   255 49  0   
                                           240 0   49  0   240 0   7   255 49  0   240 0   49  0   240 0   7   255 78  2   139 1   76  2   141 1   76  2   141 1   74  2   143 1   74  2   143 1   71  2   144 1   71  2   144 1   68  2   146 1   68  2   146 1   66  2   147 1   66  2   147 1   63  2   
                                           148 1   63  2   148 1   60  2   149 1   60  2   149 1   57  2   149 1   57  2   149 1   54  2   150 1   54  2   150 1   51  2   150 1   51  2   150 1   48  2   149 1   48  2   149 1   45  2   149 1   45  2   149 1   42  2   148 1   42  2   148 1   39  2   
                                           147 1   39  2   147 1   36  2   146 1   36  2   146 1   33  2   144 1   33  2   144 1   31  2   143 1   31  2   143 1   28  2   141 1   28  2   141 1   26  2   139 1   26  2   139 1   24  2   137 1   24  2   137 1   22  2   134 1   22  2   134 1   21  2   
                                           132 1   21  2   132 1   19  2   129 1   19  2   129 1   18  2   126 1   18  2   126 1   17  2   123 1   17  2   123 1   16  2   120 1   16  2   120 1   16  2   117 1   16  2   117 1   15  2   114 1   15  2   114 1   15  2   111 1   15  2   111 1   16  2   
                                           108 1   16  2   108 1   16  2   105 1   16  2   105 1   17  2   102 1   17  2   102 1   18  2   99  1   18  2   99  1   19  2   97  1   19  2   97  1   21  2   94  1   21  2   94  1   22  2   91  1   22  2   91  1   24  2   89  1   24  2   89  1   26  2   
                                           87  1   26  2   87  1   28  2   85  1   28  2   85  1   31  2   83  1   31  2   83  1   33  2   81  1   33  2   81  1   36  2   80  1   36  2   80  1   39  2   79  1   39  2   79  1   42  2   78  1   42  2   78  1   45  2   77  1   45  2   77  1   48  2   
                                           76  1   48  2   76  1   51  2   76  1   51  2   76  1   54  2   76  1   54  2   76  1   57  2   76  1   57  2   76  1   60  2   77  1   60  2   77  1   63  2   78  1   63  2   78  1   66  2   79  1   66  2   79  1   68  2   80  1   68  2   80  1   71  2   
                                           81  1   71  2   81  1   74  2   83  1   74  2   83  1   76  2   85  1   76  2   85  1   78  2   87  1   7   255 78  2   87  1   78  2   139 1   7   255 253 1   39  1   253 1   56  1   253 1   56  1   12  2   62  1   12  2   62  1   92  2   62  1   92  2   
                                           62  1   107 2   56  1   107 2   56  1   107 2   39  1   107 2   39  1   92  2   34  1   92  2   34  1   12  2   34  1   12  2   34  1   253 1   39  1   7   255 253 1   245 0   253 1   7   1   253 1   7   1   12  2   12  1   12  2   12  1   92  2   12  1   
                                           92  2   12  1   107 2   7   1   107 2   7   1   107 2   245 0   107 2   245 0   92  2   240 0   92  2   240 0   12  2   240 0   12  2   240 0   253 1   245 0   7   255 253 1   169 1   253 1   186 1   253 1   186 1   12  2   192 1   12  2   192 1   92  2   
                                           192 1   92  2   192 1   107 2   186 1   107 2   186 1   107 2   169 1   107 2   169 1   92  2   164 1   92  2   164 1   12  2   164 1   12  2   164 1   253 1   169 1   7   255 253 1   219 1   253 1   236 1   253 1   236 1   12  2   241 1   12  2   241 1   
                                           92  2   241 1   92  2   241 1   107 2   236 1   107 2   236 1   107 2   219 1   107 2   219 1   92  2   214 1   92  2   214 1   12  2   214 1   12  2   214 1   253 1   219 1   7   255 62  2   113 1   62  2   114 1   62  2   114 1   62  2   116 1   62  2   
                                           116 1   61  2   117 1   61  2   117 1   60  2   119 1   60  2   119 1   59  2   120 1   59  2   120 1   58  2   121 1   58  2   121 1   57  2   122 1   57  2   122 1   55  2   122 1   55  2   122 1   54  2   123 1   54  2   123 1   52  2   123 1   52  2   
                                           123 1   51  2   123 1   51  2   123 1   49  2   122 1   49  2   122 1   48  2   122 1   48  2   122 1   46  2   121 1   46  2   121 1   45  2   120 1   45  2   120 1   44  2   119 1   44  2   119 1   43  2   117 1   43  2   117 1   43  2   116 1   43  2   
                                           116 1   42  2   114 1   42  2   114 1   42  2   113 1   42  2   113 1   42  2   111 1   42  2   111 1   43  2   110 1   43  2   110 1   43  2   108 1   43  2   108 1   44  2   107 1   44  2   107 1   45  2   106 1   45  2   106 1   46  2   105 1   46  2   
                                           105 1   48  2   104 1   48  2   104 1   49  2   103 1   49  2   103 1   51  2   103 1   51  2   103 1   52  2   103 1   52  2   103 1   54  2   103 1   54  2   103 1   55  2   103 1   55  2   103 1   57  2   104 1   57  2   104 1   58  2   105 1   58  2   
                                           105 1   59  2   106 1   59  2   106 1   60  2   107 1   60  2   107 1   61  2   108 1   61  2   108 1   62  2   110 1   62  2   110 1   62  2   111 1   62  2   111 1   62  2   113 1   7   255 32  2   113 1   72  2   113 1   7   255 52  2   93  1   52  2   
                                           133 1   7   255 62  2   241 1   62  2   243 1   62  2   243 1   62  2   244 1   62  2   244 1   61  2   246 1   61  2   246 1   60  2   247 1   60  2   247 1   59  2   248 1   59  2   248 1   58  2   249 1   58  2   249 1   57  2   250 1   57  2   250 1   
                                           55  2   251 1   55  2   251 1   54  2   251 1   54  2   251 1   52  2   251 1   52  2   251 1   51  2   251 1   51  2   251 1   49  2   251 1   49  2   251 1   48  2   250 1   48  2   250 1   46  2   249 1   46  2   249 1   45  2   248 1   45  2   248 1   
                                           44  2   247 1   44  2   247 1   43  2   246 1   43  2   246 1   43  2   244 1   43  2   244 1   42  2   243 1   42  2   243 1   42  2   241 1   42  2   241 1   42  2   240 1   42  2   240 1   43  2   238 1   43  2   238 1   43  2   237 1   43  2   237 1   
                                           )) "a")
 (_WriteStream FILE (vl-list->string (list 44  2   236 1   44  2   236 1   45  2   234 1   45  2   234 1   46  2   233 1   46  2   233 1   48  2   233 1   48  2   233 1   49  2   232 1   49  2   232 1   51  2   232 1   51  2   232 1   52  2   232 1   52  2   232 1   54  2   232 1   54  2   232 1   
                                           55  2   232 1   55  2   232 1   57  2   233 1   57  2   233 1   58  2   233 1   58  2   233 1   59  2   234 1   59  2   234 1   60  2   236 1   60  2   236 1   61  2   237 1   61  2   237 1   62  2   238 1   62  2   238 1   62  2   240 1   62  2   240 1   
                                           62  2   241 1   7   255 32  2   241 1   72  2   241 1   7   255 52  2   222 1   52  2   5   2   7   255 62  2   240 0   62  2   242 0   62  2   242 0   62  2   243 0   62  2   243 0   61  2   245 0   61  2   245 0   60  2   246 0   60  2   246 0   59  2   
                                           247 0   59  2   247 0   58  2   248 0   58  2   248 0   57  2   249 0   57  2   249 0   55  2   250 0   55  2   250 0   54  2   250 0   54  2   250 0   52  2   250 0   52  2   250 0   51  2   250 0   51  2   250 0   49  2   250 0   49  2   250 0   48  2   
                                           249 0   48  2   249 0   46  2   248 0   46  2   248 0   45  2   247 0   45  2   247 0   44  2   246 0   44  2   246 0   43  2   245 0   43  2   245 0   43  2   243 0   43  2   243 0   42  2   242 0   42  2   242 0   42  2   240 0   42  2   240 0   42  2   
                                           239 0   42  2   239 0   43  2   237 0   43  2   237 0   43  2   236 0   43  2   236 0   44  2   234 0   44  2   234 0   45  2   233 0   45  2   233 0   46  2   232 0   46  2   232 0   48  2   231 0   48  2   231 0   49  2   231 0   49  2   231 0   51  2   
                                           230 0   51  2   230 0   52  2   230 0   52  2   230 0   54  2   230 0   54  2   230 0   55  2   231 0   55  2   231 0   57  2   231 0   57  2   231 0   58  2   232 0   58  2   232 0   59  2   233 0   59  2   233 0   60  2   234 0   60  2   234 0   61  2   
                                           236 0   61  2   236 0   62  2   237 0   62  2   237 0   62  2   239 0   62  2   239 0   62  2   240 0   7   255 32  2   240 0   72  2   240 0   7   255 52  2   220 0   52  2   4   1   7   255 59  0   240 0   59  0   242 0   59  0   242 0   59  0   243 0   
                                           59  0   243 0   58  0   245 0   58  0   245 0   57  0   246 0   57  0   246 0   56  0   247 0   56  0   247 0   55  0   248 0   55  0   248 0   54  0   249 0   54  0   249 0   52  0   250 0   52  0   250 0   51  0   250 0   51  0   250 0   49  0   250 0   
                                           49  0   250 0   48  0   250 0   48  0   250 0   46  0   250 0   46  0   250 0   45  0   249 0   45  0   249 0   43  0   248 0   43  0   248 0   42  0   247 0   42  0   247 0   41  0   246 0   41  0   246 0   40  0   245 0   40  0   245 0   40  0   243 0   
                                           40  0   243 0   39  0   242 0   39  0   242 0   39  0   240 0   39  0   240 0   39  0   239 0   39  0   239 0   40  0   237 0   40  0   237 0   40  0   236 0   40  0   236 0   41  0   234 0   41  0   234 0   42  0   233 0   42  0   233 0   43  0   232 0   
                                           43  0   232 0   45  0   231 0   45  0   231 0   46  0   231 0   46  0   231 0   48  0   230 0   48  0   230 0   49  0   230 0   49  0   230 0   51  0   230 0   51  0   230 0   52  0   231 0   52  0   231 0   54  0   231 0   54  0   231 0   55  0   232 0   
                                           55  0   232 0   56  0   233 0   56  0   233 0   57  0   234 0   57  0   234 0   58  0   236 0   58  0   236 0   59  0   237 0   59  0   237 0   59  0   239 0   59  0   239 0   59  0   240 0   7   255 29  0   240 0   69  0   240 0   7   255 49  0   220 0   
                                           49  0   4   1   7   255 59  0   241 1   59  0   243 1   59  0   243 1   59  0   244 1   59  0   244 1   58  0   246 1   58  0   246 1   57  0   247 1   57  0   247 1   56  0   248 1   56  0   248 1   55  0   249 1   55  0   249 1   54  0   250 1   54  0   
                                           250 1   52  0   251 1   52  0   251 1   51  0   251 1   51  0   251 1   49  0   251 1   49  0   251 1   48  0   251 1   48  0   251 1   46  0   251 1   46  0   251 1   45  0   250 1   45  0   250 1   43  0   249 1   43  0   249 1   42  0   248 1   42  0   
                                           248 1   41  0   247 1   41  0   247 1   40  0   246 1   40  0   246 1   40  0   244 1   40  0   244 1   39  0   243 1   39  0   243 1   39  0   241 1   39  0   241 1   39  0   240 1   39  0   240 1   40  0   238 1   40  0   238 1   40  0   237 1   40  0   
                                           237 1   41  0   236 1   41  0   236 1   42  0   234 1   42  0   234 1   43  0   233 1   43  0   233 1   45  0   233 1   45  0   233 1   46  0   232 1   46  0   232 1   48  0   232 1   48  0   232 1   49  0   232 1   49  0   232 1   51  0   232 1   51  0   
                                           232 1   52  0   232 1   52  0   232 1   54  0   233 1   54  0   233 1   55  0   233 1   55  0   233 1   56  0   234 1   56  0   234 1   57  0   236 1   57  0   236 1   58  0   237 1   58  0   237 1   59  0   238 1   59  0   238 1   59  0   240 1   59  0   
                                           240 1   59  0   241 1   7   255 29  0   241 1   69  0   241 1   7   255 49  0   222 1   49  0   5   2   7   255 178 0   113 1   178 0   114 1   178 0   114 1   177 0   116 1   177 0   116 1   177 0   117 1   177 0   117 1   176 0   119 1   176 0   119 1   
                                           175 0   120 1   175 0   120 1   174 0   121 1   174 0   121 1   173 0   122 1   173 0   122 1   171 0   122 1   171 0   122 1   170 0   123 1   170 0   123 1   168 0   123 1   168 0   123 1   166 0   123 1   166 0   123 1   165 0   122 1   165 0   122 1   
                                           164 0   122 1   164 0   122 1   162 0   121 1   162 0   121 1   161 0   120 1   161 0   120 1   160 0   119 1   160 0   119 1   159 0   117 1   159 0   117 1   159 0   116 1   159 0   116 1   158 0   114 1   158 0   114 1   158 0   113 1   158 0   113 1   
                                           158 0   111 1   158 0   111 1   159 0   110 1   159 0   110 1   159 0   108 1   159 0   108 1   160 0   107 1   160 0   107 1   161 0   106 1   161 0   106 1   162 0   105 1   162 0   105 1   164 0   104 1   164 0   104 1   165 0   103 1   165 0   103 1   
                                           166 0   103 1   166 0   103 1   168 0   103 1   168 0   103 1   170 0   103 1   170 0   103 1   171 0   103 1   171 0   103 1   173 0   104 1   173 0   104 1   174 0   105 1   174 0   105 1   175 0   106 1   175 0   106 1   176 0   107 1   176 0   107 1   
                                           177 0   108 1   177 0   108 1   177 0   110 1   177 0   110 1   178 0   111 1   178 0   111 1   178 0   113 1   7   255 148 0   113 1   188 0   113 1   7   255 168 0   93  1   168 0   133 1   7   255 113 0   219 1   113 0   236 1   113 0   236 1   128 0   
                                           241 1   128 0   241 1   208 0   241 1   208 0   241 1   223 0   236 1   223 0   236 1   223 0   219 1   223 0   219 1   208 0   214 1   208 0   214 1   128 0   214 1   128 0   214 1   113 0   219 1   7   255 113 0   245 0   113 0   7   1   113 0   7   1   
                                           128 0   12  1   128 0   12  1   208 0   12  1   208 0   12  1   223 0   7   1   223 0   7   1   223 0   245 0   223 0   245 0   208 0   240 0   208 0   240 0   128 0   240 0   128 0   240 0   113 0   245 0   7   255 178 0   241 1   178 0   243 1   178 0   
                                           243 1   177 0   244 1   177 0   244 1   177 0   246 1   177 0   246 1   176 0   247 1   176 0   247 1   175 0   248 1   175 0   248 1   174 0   249 1   174 0   249 1   173 0   250 1   173 0   250 1   171 0   251 1   171 0   251 1   170 0   251 1   170 0   
                                           251 1   168 0   251 1   168 0   251 1   166 0   251 1   166 0   251 1   165 0   251 1   165 0   251 1   164 0   250 1   164 0   250 1   162 0   249 1   162 0   249 1   161 0   248 1   161 0   248 1   160 0   247 1   160 0   247 1   159 0   246 1   159 0   
                                           246 1   159 0   244 1   159 0   244 1   158 0   243 1   158 0   243 1   158 0   241 1   158 0   241 1   158 0   240 1   158 0   240 1   159 0   238 1   159 0   238 1   159 0   237 1   159 0   237 1   160 0   236 1   160 0   236 1   161 0   234 1   161 0   
                                           234 1   162 0   233 1   162 0   233 1   164 0   233 1   164 0   233 1   165 0   232 1   165 0   232 1   166 0   232 1   166 0   232 1   168 0   232 1   168 0   232 1   170 0   232 1   170 0   232 1   171 0   232 1   171 0   232 1   173 0   233 1   173 0   
                                           233 1   174 0   233 1   174 0   233 1   175 0   234 1   175 0   234 1   176 0   236 1   176 0   236 1   177 0   237 1   177 0   237 1   177 0   238 1   177 0   238 1   178 0   240 1   178 0   240 1   178 0   241 1   7   255 148 0   241 1   188 0   241 1   
                                           7   255 168 0   222 1   168 0   5   2   7   255 178 0   240 0   178 0   242 0   178 0   242 0   177 0   243 0   177 0   243 0   177 0   245 0   177 0   245 0   176 0   246 0   176 0   246 0   175 0   247 0   175 0   247 0   174 0   248 0   174 0   248 0   
                                           173 0   249 0   173 0   249 0   171 0   250 0   171 0   250 0   170 0   250 0   170 0   250 0   168 0   250 0   168 0   250 0   166 0   250 0   166 0   250 0   165 0   250 0   165 0   250 0   164 0   249 0   164 0   249 0   162 0   248 0   162 0   248 0   
                                           161 0   247 0   161 0   247 0   160 0   246 0   160 0   246 0   159 0   245 0   159 0   245 0   159 0   243 0   159 0   243 0   158 0   242 0   158 0   242 0   158 0   240 0   158 0   240 0   158 0   239 0   158 0   239 0   159 0   237 0   159 0   237 0   
                                           159 0   236 0   159 0   236 0   160 0   234 0   160 0   234 0   161 0   233 0   161 0   233 0   162 0   232 0   162 0   232 0   164 0   231 0   164 0   231 0   165 0   231 0   165 0   231 0   166 0   230 0   166 0   230 0   168 0   230 0   168 0   230 0   
                                           170 0   230 0   170 0   230 0   171 0   231 0   171 0   231 0   173 0   231 0   173 0   231 0   174 0   232 0   174 0   232 0   175 0   233 0   175 0   233 0   176 0   234 0   176 0   234 0   177 0   236 0   177 0   236 0   177 0   237 0   177 0   237 0   
                                           178 0   239 0   178 0   239 0   178 0   240 0   7   255 148 0   240 0   188 0   240 0   7   255 168 0   220 0   168 0   4   1   0   252 65  117 116 111 67  65  68  32  83  108 105 100 101 13  10  26  0   86  2   73  6   247 2   97  120 67  1   2   0   52  
                                           18  7   255 7   255 194 3   34  1   16  6   34  1   16  6   34  1   16  6   210 1   16  6   210 1   194 3   210 1   194 3   210 1   194 3   34  1   7   255 194 3   34  1   194 3   34  1   7   255 194 3   34  1   194 3   34  1   7   255 194 3   34  1   194 
                                           3   34  1   7   255 2   4   122 1   254 3   130 1   254 3   130 1   246 3   134 1   246 3   134 1   238 3   130 1   238 3   130 1   234 3   122 1   234 3   122 1   238 3   114 1   238 3   114 1   246 3   110 1   246 3   110 1   254 3   114 1   254 3   114 
                                           1   2   4   122 1   7   255 175 5   68  1   175 5   79  1   175 5   79  1   185 5   82  1   185 5   82  1   235 5   82  1   235 5   82  1   244 5   79  1   244 5   79  1   244 5   68  1   244 5   68  1   235 5   65  1   235 5   65  1   185 5   65  1   185 
                                           5   65  1   175 5   68  1   7   255 175 5   37  1   175 5   48  1   175 5   48  1   185 5   51  1   185 5   51  1   235 5   51  1   235 5   51  1   244 5   48  1   244 5   48  1   244 5   37  1   244 5   37  1   235 5   34  1   235 5   34  1   185 5   34  
                                           1   185 5   34  1   175 5   37  1   7   255 175 5   165 1   175 5   176 1   175 5   176 1   185 5   179 1   185 5   179 1   235 5   179 1   235 5   179 1   244 5   176 1   244 5   176 1   244 5   165 1   244 5   165 1   235 5   162 1   235 5   162 1   185 
                                           5   162 1   185 5   162 1   175 5   165 1   7   255 175 5   196 1   175 5   207 1   175 5   207 1   185 5   210 1   185 5   210 1   235 5   210 1   235 5   210 1   244 5   207 1   244 5   207 1   244 5   196 1   244 5   196 1   235 5   193 1   235 5   193 
                                           1   185 5   193 1   185 5   193 1   175 5   196 1   7   255 248 3   122 1   248 3   123 1   248 3   123 1   246 3   124 1   246 3   124 1   245 3   123 1   245 3   123 1   244 3   122 1   244 3   122 1   245 3   120 1   245 3   120 1   246 3   120 1   246 
                                           3   120 1   248 3   120 1   248 3   120 1   248 3   122 1   7   255 242 3   122 1   250 3   122 1   7   255 246 3   118 1   246 3   126 1   7   255 197 3   34  1   196 3   36  1   196 3   36  1   194 3   36  1   194 3   36  1   193 3   36  1   193 3   36  
                                           1   192 3   34  1   192 3   34  1   193 3   33  1   193 3   33  1   194 3   32  1   194 3   32  1   196 3   33  1   196 3   33  1   197 3   34  1   7   255 190 3   34  1   199 3   34  1   7   255 194 3   30  1   194 3   38  1   7   255 197 3   210 1   196 
                                           3   211 1   196 3   211 1   194 3   212 1   194 3   212 1   193 3   211 1   193 3   211 1   192 3   210 1   192 3   210 1   193 3   208 1   193 3   208 1   194 3   208 1   194 3   208 1   196 3   208 1   196 3   208 1   197 3   210 1   7   255 190 3   210 
                                           1   199 3   210 1   7   255 194 3   206 1   194 3   214 1   7   255 212 5   210 1   211 5   211 1   211 5   211 1   210 5   212 1   210 5   212 1   208 5   211 1   208 5   211 1   208 5   210 1   208 5   210 1   208 5   208 1   208 5   208 1   210 5   208 
                                           1   210 5   208 1   211 5   208 1   211 5   208 1   212 5   210 1   7   255 206 5   210 1   214 5   210 1   7   255 210 5   206 1   210 5   214 1   7   255 18  6   210 1   17  6   211 1   17  6   211 1   16  6   212 1   16  6   212 1   14  6   211 1   14  
                                           6   211 1   14  6   210 1   14  6   210 1   14  6   208 1   14  6   208 1   16  6   208 1   16  6   208 1   17  6   208 1   17  6   208 1   18  6   210 1   7   255 12  6   210 1   20  6   210 1   7   255 16  6   206 1   16  6   214 1   7   255 18  6   34  
                                           1   17  6   36  1   17  6   36  1   16  6   36  1   16  6   36  1   14  6   36  1   14  6   36  1   14  6   34  1   14  6   34  1   14  6   33  1   14  6   33  1   16  6   32  1   16  6   32  1   17  6   33  1   17  6   33  1   18  6   34  1   7   255 12  
                                           6   34  1   20  6   34  1   7   255 16  6   30  1   16  6   38  1   7   255 212 5   34  1   211 5   36  1   211 5   36  1   210 5   36  1   210 5   36  1   208 5   36  1   208 5   36  1   208 5   34  1   208 5   34  1   208 5   33  1   208 5   33  1   210 
                                           5   32  1   210 5   32  1   211 5   33  1   211 5   33  1   212 5   34  1   7   255 206 5   34  1   214 5   34  1   7   255 210 5   30  1   210 5   38  1   7   255 101 3   122 1   246 3   122 1   7   255 113 3   122 1   110 3   130 1   110 3   130 1   101 
                                           3   134 1   101 3   134 1   93  3   130 1   93  3   130 1   90  3   122 1   90  3   122 1   93  3   114 1   93  3   114 1   101 3   110 1   101 3   110 1   110 3   114 1   110 3   114 1   113 3   122 1   7   255 212 3   68  1   212 3   79  1   212 3   79  
                                           1   221 3   82  1   221 3   82  1   15  4   82  1   15  4   82  1   25  4   79  1   25  4   79  1   25  4   68  1   25  4   68  1   15  4   65  1   15  4   65  1   221 3   65  1   221 3   65  1   212 3   68  1   7   255 212 3   37  1   212 3   48  1   212 
                                           3   48  1   221 3   51  1   221 3   51  1   15  4   51  1   15  4   51  1   25  4   48  1   25  4   48  1   25  4   37  1   25  4   37  1   15  4   34  1   15  4   34  1   221 3   34  1   221 3   34  1   212 3   37  1   7   255 212 3   165 1   212 3   176 
                                           1   212 3   176 1   221 3   179 1   221 3   179 1   15  4   179 1   15  4   179 1   25  4   176 1   25  4   176 1   25  4   165 1   25  4   165 1   15  4   162 1   15  4   162 1   221 3   162 1   221 3   162 1   212 3   165 1   7   255 212 3   196 1   212 
                                           3   207 1   212 3   207 1   221 3   210 1   221 3   210 1   15  4   210 1   15  4   210 1   25  4   207 1   25  4   207 1   25  4   196 1   25  4   196 1   15  4   193 1   15  4   193 1   221 3   193 1   221 3   193 1   212 3   196 1   7   255 103 3   122 
                                           1   103 3   123 1   103 3   123 1   101 3   124 1   101 3   124 1   100 3   123 1   100 3   123 1   99  3   122 1   99  3   122 1   100 3   120 1   100 3   120 1   101 3   120 1   101 3   120 1   103 3   120 1   103 3   120 1   103 3   122 1   7   255 97  
                                           3   122 1   106 3   122 1   7   255 101 3   118 1   101 3   126 1   7   255 248 3   122 1   248 3   123 1   248 3   123 1   246 3   124 1   246 3   124 1   245 3   123 1   245 3   123 1   244 3   122 1   244 3   122 1   245 3   120 1   245 3   120 1   246 
                                           3   120 1   246 3   120 1   248 3   120 1   248 3   120 1   248 3   122 1   7   255 242 3   122 1   250 3   122 1   7   255 246 3   118 1   246 3   126 1   7   255 248 3   34  1   248 3   36  1   248 3   36  1   246 3   36  1   246 3   36  1   245 3   36  
                                           1   245 3   36  1   244 3   34  1   244 3   34  1   245 3   33  1   245 3   33  1   246 3   32  1   246 3   32  1   248 3   33  1   248 3   33  1   248 3   34  1   7   255 242 3   34  1   250 3   34  1   7   255 246 3   30  1   246 3   38  1   7   255 248 
                                           3   210 1   248 3   211 1   248 3   211 1   246 3   212 1   246 3   212 1   245 3   211 1   245 3   211 1   244 3   210 1   244 3   210 1   245 3   208 1   245 3   208 1   246 3   208 1   246 3   208 1   248 3   208 1   248 3   208 1   248 3   210 1   7   
                                           255 242 3   210 1   250 3   210 1   7   255 246 3   206 1   246 3   214 1   7   255 24  1   34  1   101 3   34  1   101 3   34  1   101 3   210 1   101 3   210 1   24  1   210 1   24  1   210 1   24  1   34  1   7   255 24  1   34  1   24  1   34  1   7   
                                           )) "a")
 (_WriteStream FILE (vl-list->string (list 255 24  1   34  1   24  1   34  1   7   255 24  1   34  1   24  1   34  1   7   255 83  1   122 1   81  1   127 1   81  1   127 1   76  1   129 1   76  1   129 1   71  1   127 1   71  1   127 1   69  1   122 1   69  1   122 1   71  1   117 1   71  1   117 
                                           1   76  1   115 1   76  1   115 1   81  1   117 1   81  1   117 1   83  1   122 1   7   255 5   3   68  1   5   3   79  1   5   3   79  1   15  3   82  1   15  3   82  1   64  3   82  1   64  3   82  1   74  3   79  1   74  3   79  1   74  3   68  1   74  
                                           3   68  1   64  3   65  1   64  3   65  1   15  3   65  1   15  3   65  1   5   3   68  1   7   255 5   3   37  1   5   3   48  1   5   3   48  1   15  3   51  1   15  3   51  1   64  3   51  1   64  3   51  1   74  3   48  1   74  3   48  1   74  3   37  
                                           1   74  3   37  1   64  3   34  1   64  3   34  1   15  3   34  1   15  3   34  1   5   3   37  1   7   255 5   3   165 1   5   3   176 1   5   3   176 1   15  3   179 1   15  3   179 1   64  3   179 1   64  3   179 1   74  3   176 1   74  3   176 1   74  
                                           3   165 1   74  3   165 1   64  3   162 1   64  3   162 1   15  3   162 1   15  3   162 1   5   3   165 1   7   255 5   3   196 1   5   3   207 1   5   3   207 1   15  3   210 1   15  3   210 1   64  3   210 1   64  3   210 1   74  3   207 1   74  3   207 
                                           1   74  3   196 1   74  3   196 1   64  3   193 1   64  3   193 1   15  3   193 1   15  3   193 1   5   3   196 1   7   255 78  1   122 1   77  1   123 1   77  1   123 1   76  1   124 1   76  1   124 1   74  1   123 1   74  1   123 1   74  1   122 1   74  
                                           1   122 1   74  1   120 1   74  1   120 1   76  1   120 1   76  1   120 1   77  1   120 1   77  1   120 1   78  1   122 1   7   255 72  1   122 1   80  1   122 1   7   255 76  1   118 1   76  1   126 1   7   255 26  1   34  1   26  1   36  1   26  1   36  
                                           1   24  1   36  1   24  1   36  1   23  1   36  1   23  1   36  1   22  1   34  1   22  1   34  1   23  1   33  1   23  1   33  1   24  1   32  1   24  1   32  1   26  1   33  1   26  1   33  1   26  1   34  1   7   255 20  1   34  1   28  1   34  1   7   
                                           255 24  1   30  1   24  1   38  1   7   255 26  1   210 1   26  1   211 1   26  1   211 1   24  1   212 1   24  1   212 1   23  1   211 1   23  1   211 1   22  1   210 1   22  1   210 1   23  1   208 1   23  1   208 1   24  1   208 1   24  1   208 1   26  
                                           1   208 1   26  1   208 1   26  1   210 1   7   255 20  1   210 1   28  1   210 1   7   255 24  1   206 1   24  1   214 1   7   255 41  3   210 1   41  3   211 1   41  3   211 1   39  3   212 1   39  3   212 1   38  3   211 1   38  3   211 1   37  3   210 
                                           1   37  3   210 1   38  3   208 1   38  3   208 1   39  3   208 1   39  3   208 1   41  3   208 1   41  3   208 1   41  3   210 1   7   255 35  3   210 1   44  3   210 1   7   255 39  3   206 1   39  3   214 1   7   255 103 3   210 1   103 3   211 1   103 
                                           3   211 1   101 3   212 1   101 3   212 1   100 3   211 1   100 3   211 1   99  3   210 1   99  3   210 1   100 3   208 1   100 3   208 1   101 3   208 1   101 3   208 1   103 3   208 1   103 3   208 1   103 3   210 1   7   255 97  3   210 1   106 3   210 
                                           1   7   255 101 3   206 1   101 3   214 1   7   255 41  3   34  1   41  3   36  1   41  3   36  1   39  3   36  1   39  3   36  1   38  3   36  1   38  3   36  1   37  3   34  1   37  3   34  1   38  3   33  1   38  3   33  1   39  3   32  1   39  3   32  
                                           1   41  3   33  1   41  3   33  1   41  3   34  1   7   255 35  3   34  1   44  3   34  1   7   255 39  3   30  1   39  3   38  1   7   255 103 3   34  1   103 3   36  1   103 3   36  1   101 3   36  1   101 3   36  1   100 3   36  1   100 3   36  1   99  
                                           3   34  1   99  3   34  1   100 3   33  1   100 3   33  1   101 3   32  1   101 3   32  1   103 3   33  1   103 3   33  1   103 3   34  1   7   255 97  3   34  1   106 3   34  1   7   255 101 3   30  1   101 3   38  1   7   255 103 3   122 1   103 3   123 
                                           1   103 3   123 1   101 3   124 1   101 3   124 1   100 3   123 1   100 3   123 1   99  3   122 1   99  3   122 1   100 3   120 1   100 3   120 1   101 3   120 1   101 3   120 1   103 3   120 1   103 3   120 1   103 3   122 1   7   255 97  3   122 1   106 
                                           3   122 1   7   255 101 3   118 1   101 3   126 1   7   255 57  0   39  1   191 0   39  1   191 0   39  1   191 0   88  1   191 0   88  1   76  1   88  1   76  1   88  1   76  1   156 1   76  1   156 1   191 0   156 1   191 0   156 1   191 0   205 1   191 
                                           0   205 1   57  0   205 1   57  0   205 1   57  0   39  1   7   255 57  0   39  1   57  0   39  1   7   255 57  0   39  1   57  0   39  1   7   255 57  0   39  1   57  0   39  1   7   255 92  1   139 1   82  1   145 1   82  1   145 1   70  1   145 1   70  
                                           1   145 1   59  1   139 1   59  1   139 1   53  1   128 1   53  1   128 1   53  1   116 1   53  1   116 1   59  1   105 1   59  1   105 1   70  1   99  1   70  1   99  1   82  1   99  1   82  1   99  1   92  1   105 1   7   255 92  1   105 1   92  1   139 
                                           1   7   255 41  1   74  1   41  1   84  1   41  1   84  1   51  1   88  1   51  1   88  1   101 1   88  1   101 1   88  1   110 1   84  1   110 1   84  1   110 1   74  1   110 1   74  1   101 1   70  1   101 1   70  1   51  1   70  1   51  1   70  1   41  
                                           1   74  1   7   255 41  1   43  1   41  1   53  1   41  1   53  1   51  1   57  1   51  1   57  1   101 1   57  1   101 1   57  1   110 1   53  1   110 1   53  1   110 1   43  1   110 1   43  1   101 1   39  1   101 1   39  1   51  1   39  1   51  1   39  
                                           1   41  1   43  1   7   255 41  1   160 1   41  1   170 1   41  1   170 1   51  1   174 1   51  1   174 1   101 1   174 1   101 1   174 1   110 1   170 1   110 1   170 1   110 1   160 1   110 1   160 1   101 1   156 1   101 1   156 1   51  1   156 1   51  
                                           1   156 1   41  1   160 1   7   255 41  1   191 1   41  1   201 1   41  1   201 1   51  1   205 1   51  1   205 1   101 1   205 1   101 1   205 1   110 1   201 1   110 1   201 1   110 1   191 1   110 1   191 1   101 1   187 1   101 1   187 1   51  1   187 
                                           1   51  1   187 1   41  1   191 1   7   255 106 0   122 1   106 0   123 1   106 0   123 1   104 0   124 1   104 0   124 1   103 0   123 1   103 0   123 1   102 0   122 1   102 0   122 1   103 0   120 1   103 0   120 1   104 0   120 1   104 0   120 1   106 
                                           0   120 1   106 0   120 1   106 0   122 1   7   255 100 0   122 1   108 0   122 1   7   255 104 0   118 1   104 0   126 1   7   255 78  1   122 1   77  1   123 1   77  1   123 1   76  1   124 1   76  1   124 1   74  1   123 1   74  1   123 1   74  1   122 
                                           1   74  1   122 1   74  1   120 1   74  1   120 1   76  1   120 1   76  1   120 1   77  1   120 1   77  1   120 1   78  1   122 1   7   255 72  1   122 1   80  1   122 1   7   255 76  1   118 1   76  1   126 1   7   255 106 0   39  1   106 0   41  1   106 
                                           0   41  1   104 0   41  1   104 0   41  1   103 0   41  1   103 0   41  1   102 0   39  1   102 0   39  1   103 0   38  1   103 0   38  1   104 0   37  1   104 0   37  1   106 0   38  1   106 0   38  1   106 0   39  1   7   255 100 0   39  1   108 0   39  
                                           1   7   255 104 0   35  1   104 0   43  1   7   255 78  1   39  1   77  1   41  1   77  1   41  1   76  1   41  1   76  1   41  1   74  1   41  1   74  1   41  1   74  1   39  1   74  1   39  1   74  1   38  1   74  1   38  1   76  1   37  1   76  1   37  
                                           1   77  1   38  1   77  1   38  1   78  1   39  1   7   255 72  1   39  1   80  1   39  1   7   255 76  1   35  1   76  1   43  1   7   255 78  1   205 1   77  1   206 1   77  1   206 1   76  1   207 1   76  1   207 1   74  1   206 1   74  1   206 1   74  
                                           1   205 1   74  1   205 1   74  1   203 1   74  1   203 1   76  1   203 1   76  1   203 1   77  1   203 1   77  1   203 1   78  1   205 1   7   255 72  1   205 1   80  1   205 1   7   255 76  1   200 1   76  1   209 1   7   255 106 0   205 1   106 0   206 
                                           1   106 0   206 1   104 0   207 1   104 0   207 1   103 0   206 1   103 0   206 1   102 0   205 1   102 0   205 1   103 0   203 1   103 0   203 1   104 0   203 1   104 0   203 1   106 0   203 1   106 0   203 1   106 0   205 1   7   255 100 0   205 1   108 
                                           0   205 1   7   255 104 0   200 1   104 0   209 1   7   255 59  0   205 1   58  0   206 1   58  0   206 1   57  0   207 1   57  0   207 1   55  0   206 1   55  0   206 1   55  0   205 1   55  0   205 1   55  0   203 1   55  0   203 1   57  0   203 1   57  
                                           0   203 1   58  0   203 1   58  0   203 1   59  0   205 1   7   255 53  0   205 1   61  0   205 1   7   255 57  0   200 1   57  0   209 1   7   255 59  0   39  1   58  0   41  1   58  0   41  1   57  0   41  1   57  0   41  1   55  0   41  1   55  0   41  
                                           1   55  0   39  1   55  0   39  1   55  0   38  1   55  0   38  1   57  0   37  1   57  0   37  1   58  0   38  1   58  0   38  1   59  0   39  1   7   255 53  0   39  1   61  0   39  1   7   255 57  0   35  1   57  0   43  1   7   255 70  0   191 1   70  
                                           0   201 1   70  0   201 1   79  0   205 1   79  0   205 1   129 0   205 1   129 0   205 1   139 0   201 1   139 0   201 1   139 0   191 1   139 0   191 1   129 0   187 1   129 0   187 1   79  0   187 1   79  0   187 1   70  0   191 1   7   255 70  0   43  
                                           1   70  0   53  1   70  0   53  1   79  0   57  1   79  0   57  1   129 0   57  1   129 0   57  1   139 0   53  1   139 0   53  1   139 0   43  1   139 0   43  1   129 0   39  1   129 0   39  1   79  0   39  1   79  0   39  1   70  0   43  1   0   252 65  
                                           117 116 111 67  65  68  32  83  108 105 100 101 13  10  26  0   86  2   73  6   247 2   97  120 67  1   2   0   52  18  51  255 51  255 118 0   184 1   138 3   184 1   138 3   184 1   184 3   87  1   184 3   87  1   138 3   247 0   138 3   247 0   118 0   
                                           247 0   118 0   247 0   118 0   184 1   7   255 7   255 118 0   247 0   138 3   247 0   138 3   247 0   138 3   184 1   138 3   184 1   118 0   184 1   118 0   184 1   118 0   247 0   7   255 118 0   247 0   118 0   247 0   7   255 118 0   247 0   118 0   
                                           247 0   7   255 118 0   247 0   118 0   247 0   7   255 138 3   87  1   184 3   87  1   7   255 191 3   87  1   189 3   93  1   189 3   93  1   184 3   95  1   184 3   95  1   178 3   93  1   178 3   93  1   176 3   87  1   176 3   87  1   178 3   82  1   
                                           178 3   82  1   184 3   80  1   184 3   80  1   189 3   82  1   189 3   82  1   191 3   87  1   7   255 5   3   251 0   5   3   6   1   5   3   6   1   16  3   10  1   16  3   10  1   70  3   10  1   70  3   10  1   81  3   6   1   81  3   6   1   81  3   
                                           251 0   81  3   251 0   70  3   247 0   70  3   247 0   16  3   247 0   16  3   247 0   5   3   251 0   7   255 5   3   168 1   5   3   180 1   5   3   180 1   16  3   184 1   16  3   184 1   70  3   184 1   70  3   184 1   81  3   180 1   81  3   180 1   
                                           81  3   168 1   81  3   168 1   70  3   165 1   70  3   165 1   16  3   165 1   16  3   165 1   5   3   168 1   7   255 59  1   87  1   58  1   89  1   58  1   89  1   57  1   90  1   57  1   90  1   55  1   89  1   55  1   89  1   54  1   87  1   54  1   
                                           87  1   55  1   86  1   55  1   86  1   57  1   85  1   57  1   85  1   58  1   86  1   58  1   86  1   59  1   87  1   7   255 52  1   87  1   61  1   87  1   7   255 57  1   83  1   57  1   92  1   7   255 120 0   247 0   119 0   249 0   119 0   249 0   
                                           118 0   249 0   118 0   249 0   116 0   249 0   116 0   249 0   116 0   247 0   116 0   247 0   116 0   246 0   116 0   246 0   118 0   245 0   118 0   245 0   119 0   246 0   119 0   246 0   120 0   247 0   7   255 113 0   247 0   122 0   247 0   7   255 
                                           118 0   243 0   118 0   252 0   7   255 120 0   184 1   119 0   185 1   119 0   185 1   118 0   186 1   118 0   186 1   116 0   185 1   116 0   185 1   116 0   184 1   116 0   184 1   116 0   182 1   116 0   182 1   118 0   181 1   118 0   181 1   119 0   
                                           182 1   119 0   182 1   120 0   184 1   7   255 113 0   184 1   122 0   184 1   7   255 118 0   179 1   118 0   188 1   7   255 45  3   184 1   45  3   185 1   45  3   185 1   43  3   186 1   43  3   186 1   42  3   185 1   42  3   185 1   41  3   184 1   
                                           41  3   184 1   42  3   182 1   42  3   182 1   43  3   181 1   43  3   181 1   45  3   182 1   45  3   182 1   45  3   184 1   7   255 39  3   184 1   48  3   184 1   7   255 43  3   179 1   43  3   188 1   7   255 45  3   247 0   45  3   249 0   45  3   
                                           249 0   43  3   249 0   43  3   249 0   42  3   249 0   42  3   249 0   41  3   247 0   41  3   247 0   42  3   246 0   42  3   246 0   43  3   245 0   43  3   245 0   45  3   246 0   45  3   246 0   45  3   247 0   7   255 39  3   247 0   48  3   247 0   
                                           7   255 43  3   243 0   43  3   252 0   7   255 59  1   247 0   58  1   249 0   58  1   249 0   57  1   249 0   57  1   249 0   55  1   249 0   55  1   249 0   54  1   247 0   54  1   247 0   55  1   246 0   55  1   246 0   57  1   245 0   57  1   245 0   
                                           58  1   246 0   58  1   246 0   59  1   247 0   7   255 52  1   247 0   61  1   247 0   7   255 57  1   243 0   57  1   252 0   7   255 59  1   184 1   58  1   185 1   58  1   185 1   57  1   186 1   57  1   186 1   55  1   185 1   55  1   185 1   54  1   
                                           184 1   54  1   184 1   55  1   182 1   55  1   182 1   57  1   181 1   57  1   181 1   58  1   182 1   58  1   182 1   59  1   184 1   7   255 52  1   184 1   61  1   184 1   7   255 57  1   179 1   57  1   188 1   7   255 186 3   87  1   185 3   89  1   
                                           185 3   89  1   184 3   90  1   184 3   90  1   182 3   89  1   182 3   89  1   181 3   87  1   181 3   87  1   182 3   86  1   182 3   86  1   184 3   85  1   184 3   85  1   185 3   86  1   185 3   86  1   186 3   87  1   7   255 179 3   87  1   188 3   
                                           87  1   7   255 184 3   83  1   184 3   92  1   7   255 19  1   251 0   19  1   6   1   19  1   6   1   30  1   10  1   30  1   10  1   84  1   10  1   84  1   10  1   95  1   6   1   95  1   6   1   95  1   251 0   95  1   251 0   84  1   247 0   84  1   
                                           247 0   30  1   247 0   30  1   247 0   19  1   251 0   7   255 19  1   168 1   19  1   180 1   19  1   180 1   30  1   184 1   30  1   184 1   84  1   184 1   84  1   184 1   95  1   180 1   95  1   180 1   95  1   168 1   95  1   168 1   84  1   165 1   
                                           84  1   165 1   30  1   165 1   30  1   165 1   19  1   168 1   51  255 51  255 184 3   87  1   229 3   184 1   229 3   184 1   197 5   184 1   197 5   184 1   197 5   247 0   197 5   247 0   229 3   247 0   229 3   247 0   184 3   87  1   7   255 7   255 
                                           229 3   247 0   197 5   247 0   197 5   247 0   197 5   184 1   197 5   184 1   229 3   184 1   229 3   184 1   229 3   247 0   7   255 229 3   247 0   229 3   247 0   7   255 229 3   247 0   229 3   247 0   7   255 229 3   247 0   229 3   247 0   7   255 
                                           184 3   87  1   229 3   87  1   7   255 197 3   87  1   193 3   96  1   193 3   96  1   184 3   100 1   184 3   100 1   175 3   96  1   175 3   96  1   171 3   87  1   171 3   87  1   175 3   78  1   175 3   78  1   184 3   75  1   184 3   75  1   193 3   
                                           78  1   193 3   78  1   197 3   87  1   7   255 189 4   251 0   189 4   6   1   189 4   6   1   200 4   10  1   200 4   10  1   254 4   10  1   254 4   10  1   9   5   6   1   9   5   6   1   9   5   251 0   9   5   251 0   254 4   247 0   254 4   247 0   
                                           200 4   247 0   200 4   247 0   189 4   251 0   7   255 189 4   168 1   189 4   180 1   189 4   180 1   200 4   184 1   200 4   184 1   254 4   184 1   254 4   184 1   9   5   180 1   9   5   180 1   9   5   168 1   9   5   168 1   254 4   165 1   254 4   
                                           165 1   200 4   165 1   200 4   165 1   189 4   168 1   7   255 186 3   87  1   185 3   89  1   185 3   89  1   184 3   90  1   184 3   90  1   182 3   89  1   182 3   89  1   181 3   87  1   181 3   87  1   182 3   86  1   182 3   86  1   184 3   85  1   
                                           184 3   85  1   185 3   86  1   185 3   86  1   186 3   87  1   7   255 179 3   87  1   188 3   87  1   7   255 184 3   83  1   184 3   92  1   7   255 229 4   247 0   228 4   249 0   228 4   249 0   227 4   249 0   227 4   249 0   225 4   249 0   225 4   
                                           249 0   225 4   247 0   225 4   247 0   225 4   246 0   225 4   246 0   227 4   245 0   227 4   245 0   228 4   246 0   228 4   246 0   229 4   247 0   7   255 222 4   247 0   231 4   247 0   7   255 227 4   243 0   227 4   252 0   7   255 229 4   184 1   
                                           228 4   185 1   228 4   185 1   227 4   186 1   227 4   186 1   225 4   185 1   225 4   185 1   225 4   184 1   225 4   184 1   225 4   182 1   225 4   182 1   227 4   181 1   227 4   181 1   228 4   182 1   228 4   182 1   229 4   184 1   7   255 222 4   
                                           184 1   231 4   184 1   7   255 227 4   179 1   227 4   188 1   7   255 231 3   184 1   231 3   185 1   231 3   185 1   229 3   186 1   229 3   186 1   227 3   185 1   227 3   185 1   227 3   184 1   227 3   184 1   227 3   182 1   227 3   182 1   229 3   
                                           )) "a")
 (_WriteStream FILE (vl-list->string (list 181 1   229 3   181 1   231 3   182 1   231 3   182 1   231 3   184 1   7   255 224 3   184 1   234 3   184 1   7   255 229 3   179 1   229 3   188 1   7   255 200 5   184 1   199 5   185 1   199 5   185 1   197 5   186 1   197 5   186 1   196 5   185 1   
                                           196 5   185 1   195 5   184 1   195 5   184 1   196 5   182 1   196 5   182 1   197 5   181 1   197 5   181 1   199 5   182 1   199 5   182 1   200 5   184 1   7   255 193 5   184 1   202 5   184 1   7   255 197 5   179 1   197 5   188 1   7   255 200 5   
                                           247 0   199 5   249 0   199 5   249 0   197 5   249 0   197 5   249 0   196 5   249 0   196 5   249 0   195 5   247 0   195 5   247 0   196 5   246 0   196 5   246 0   197 5   245 0   197 5   245 0   199 5   246 0   199 5   246 0   200 5   247 0   7   255 
                                           193 5   247 0   202 5   247 0   7   255 197 5   243 0   197 5   252 0   7   255 231 3   247 0   231 3   249 0   231 3   249 0   229 3   249 0   229 3   249 0   227 3   249 0   227 3   249 0   227 3   247 0   227 3   247 0   227 3   246 0   227 3   246 0   
                                           229 3   245 0   229 3   245 0   231 3   246 0   231 3   246 0   231 3   247 0   7   255 224 3   247 0   234 3   247 0   7   255 229 3   243 0   229 3   252 0   0   252 65  117 116 111 67  65  68  32  83  108 105 100 101 13  10  26  0   86  2   106 6   234 
                                           2   99  219 79  1   2   0   52  18  51  255 51  255 89  0   109 0   13  6   109 0   13  6   109 0   13  6   125 2   13  6   125 2   89  0   125 2   89  0   125 2   89  0   109 0   7   255 7   255 89  0   109 0   13  6   109 0   13  6   109 0   13  6   125 
                                           2   13  6   125 2   89  0   125 2   89  0   125 2   89  0   109 0   7   255 89  0   109 0   89  0   109 0   7   255 89  0   109 0   89  0   109 0   7   255 61  4   117 0   61  4   144 0   61  4   144 0   86  4   152 0   86  4   152 0   210 4   152 0   210 
                                           4   152 0   234 4   144 0   234 4   144 0   234 4   117 0   234 4   117 0   210 4   109 0   210 4   109 0   86  4   109 0   86  4   109 0   61  4   117 0   7   255 61  4   90  2   61  4   117 2   61  4   117 2   86  4   125 2   86  4   125 2   210 4   125 
                                           2   210 4   125 2   234 4   117 2   234 4   117 2   234 4   90  2   234 4   90  2   210 4   82  2   210 4   82  2   86  4   82  2   86  4   82  2   61  4   90  2   7   255 230 0   90  2   230 0   117 2   230 0   117 2   254 0   125 2   254 0   125 2   122 
                                           1   125 2   122 1   125 2   146 1   117 2   146 1   117 2   146 1   90  2   146 1   90  2   122 1   82  2   122 1   82  2   254 0   82  2   254 0   82  2   230 0   90  2   7   255 230 0   117 0   230 0   144 0   230 0   144 0   254 0   152 0   254 0   152 
                                           0   122 1   152 0   122 1   152 0   146 1   144 0   146 1   144 0   146 1   117 0   146 1   117 0   122 1   109 0   122 1   109 0   254 0   109 0   254 0   109 0   230 0   117 0   7   255 115 0   109 0   113 0   119 0   113 0   119 0   107 0   127 0   107 
                                           0   127 0   99  0   132 0   99  0   132 0   89  0   134 0   89  0   134 0   80  0   132 0   80  0   132 0   72  0   127 0   72  0   127 0   66  0   119 0   66  0   119 0   64  0   109 0   64  0   109 0   66  0   99  0   66  0   99  0   72  0   91  0   72  
                                           0   91  0   80  0   86  0   80  0   86  0   89  0   84  0   89  0   84  0   99  0   86  0   99  0   86  0   107 0   91  0   107 0   91  0   113 0   99  0   113 0   99  0   115 0   109 0   7   255 39  0   109 0   140 0   109 0   7   255 89  0   59  0   89  
                                           0   159 0   7   255 38  6   109 0   36  6   119 0   36  6   119 0   31  6   127 0   31  6   127 0   23  6   132 0   23  6   132 0   13  6   134 0   13  6   134 0   4   6   132 0   4   6   132 0   251 5   127 0   251 5   127 0   246 5   119 0   246 5   119 
                                           0   244 5   109 0   244 5   109 0   246 5   99  0   246 5   99  0   251 5   91  0   251 5   91  0   4   6   86  0   4   6   86  0   13  6   84  0   13  6   84  0   23  6   86  0   23  6   86  0   31  6   91  0   31  6   91  0   36  6   99  0   36  6   99  
                                           0   38  6   109 0   7   255 219 5   109 0   64  6   109 0   7   255 13  6   59  0   13  6   159 0   7   255 38  6   125 2   36  6   135 2   36  6   135 2   31  6   143 2   31  6   143 2   23  6   148 2   23  6   148 2   13  6   150 2   13  6   150 2   4   
                                           6   148 2   4   6   148 2   251 5   143 2   251 5   143 2   246 5   135 2   246 5   135 2   244 5   125 2   244 5   125 2   246 5   115 2   246 5   115 2   251 5   107 2   251 5   107 2   4   6   102 2   4   6   102 2   13  6   100 2   13  6   100 2   23  
                                           6   102 2   23  6   102 2   31  6   107 2   31  6   107 2   36  6   115 2   36  6   115 2   38  6   125 2   7   255 219 5   125 2   64  6   125 2   7   255 13  6   75  2   13  6   175 2   7   255 115 0   125 2   113 0   135 2   113 0   135 2   107 0   143 
                                           2   107 0   143 2   99  0   148 2   99  0   148 2   89  0   150 2   89  0   150 2   80  0   148 2   80  0   148 2   72  0   143 2   72  0   143 2   66  0   135 2   66  0   135 2   64  0   125 2   64  0   125 2   66  0   115 2   66  0   115 2   72  0   107 
                                           2   72  0   107 2   80  0   102 2   80  0   102 2   89  0   100 2   89  0   100 2   99  0   102 2   99  0   102 2   107 0   107 2   107 0   107 2   113 0   115 2   113 0   115 2   115 0   125 2   7   255 39  0   125 2   140 0   125 2   7   255 89  0   75  
                                           2   89  0   175 2   7   255 85  1   125 2   83  1   135 2   83  1   135 2   78  1   143 2   78  1   143 2   70  1   148 2   70  1   148 2   60  1   150 2   60  1   150 2   50  1   148 2   50  1   148 2   42  1   143 2   42  1   143 2   37  1   135 2   37  
                                           1   135 2   35  1   125 2   35  1   125 2   37  1   115 2   37  1   115 2   42  1   107 2   42  1   107 2   50  1   102 2   50  1   102 2   60  1   100 2   60  1   100 2   70  1   102 2   70  1   102 2   78  1   107 2   78  1   107 2   83  1   115 2   83  
                                           1   115 2   85  1   125 2   7   255 10  1   125 2   110 1   125 2   7   255 60  1   75  2   60  1   175 2   7   255 173 4   125 2   171 4   135 2   171 4   135 2   165 4   143 2   165 4   143 2   157 4   148 2   157 4   148 2   148 4   150 2   148 4   150 
                                           2   138 4   148 2   138 4   148 2   130 4   143 2   130 4   143 2   124 4   135 2   124 4   135 2   122 4   125 2   122 4   125 2   124 4   115 2   124 4   115 2   130 4   107 2   130 4   107 2   138 4   102 2   138 4   102 2   148 4   100 2   148 4   100 
                                           2   157 4   102 2   157 4   102 2   165 4   107 2   165 4   107 2   171 4   115 2   171 4   115 2   173 4   125 2   7   255 97  4   125 2   198 4   125 2   7   255 148 4   75  2   148 4   175 2   7   255 85  1   109 0   83  1   119 0   83  1   119 0   78  
                                           1   127 0   78  1   127 0   70  1   132 0   70  1   132 0   60  1   134 0   60  1   134 0   50  1   132 0   50  1   132 0   42  1   127 0   42  1   127 0   37  1   119 0   37  1   119 0   35  1   109 0   35  1   109 0   37  1   99  0   37  1   99  0   42  
                                           1   91  0   42  1   91  0   50  1   86  0   50  1   86  0   60  1   84  0   60  1   84  0   70  1   86  0   70  1   86  0   78  1   91  0   78  1   91  0   83  1   99  0   83  1   99  0   85  1   109 0   7   255 10  1   109 0   110 1   109 0   7   255 60  
                                           1   59  0   60  1   159 0   7   255 173 4   109 0   171 4   119 0   171 4   119 0   165 4   127 0   165 4   127 0   157 4   132 0   157 4   132 0   148 4   134 0   148 4   134 0   138 4   132 0   138 4   132 0   130 4   127 0   130 4   127 0   124 4   119 
                                           0   124 4   119 0   122 4   109 0   122 4   109 0   124 4   99  0   124 4   99  0   130 4   91  0   130 4   91  0   138 4   86  0   138 4   86  0   148 4   84  0   148 4   84  0   157 4   86  0   157 4   86  0   165 4   91  0   165 4   91  0   171 4   99  
                                           0   171 4   99  0   173 4   109 0   7   255 97  4   109 0   198 4   109 0   7   255 148 4   59  0   148 4   159 0   7   255 85  1   117 1   83  1   127 1   83  1   127 1   78  1   135 1   78  1   135 1   70  1   140 1   70  1   140 1   60  1   142 1   60  
                                           1   142 1   50  1   140 1   50  1   140 1   42  1   135 1   42  1   135 1   37  1   127 1   37  1   127 1   35  1   117 1   35  1   117 1   37  1   107 1   37  1   107 1   42  1   99  1   42  1   99  1   50  1   94  1   50  1   94  1   60  1   92  1   60  
                                           1   92  1   70  1   94  1   70  1   94  1   78  1   99  1   78  1   99  1   83  1   107 1   83  1   107 1   85  1   117 1   7   255 10  1   117 1   110 1   117 1   7   255 60  1   67  1   60  1   167 1   0   252 65  117 116 111 67  65  68  32  83  108 105 
                                           100 101 13  10  26  0   86  2   106 6   234 2   99  219 79  1   2   0   52  18  7   255 7   255 44  0   5   1   136 2   5   1   136 2   5   1   136 2   224 1   136 2   224 1   44  0   224 1   44  0   224 1   44  0   5   1   7   255 44  0   5   1   44  0   
                                           5   1   7   255 44  0   5   1   44  0   5   1   7   255 200 1   9   1   200 1   20  1   200 1   20  1   210 1   23  1   210 1   23  1   5   2   23  1   5   2   23  1   15  2   20  1   15  2   20  1   15  2   9   1   15  2   9   1   5   2   5   1   5   2   
                                           5   1   210 1   5   1   210 1   5   1   200 1   9   1   7   255 200 1   209 1   200 1   220 1   200 1   220 1   210 1   224 1   210 1   224 1   5   2   224 1   5   2   224 1   15  2   220 1   15  2   220 1   15  2   209 1   15  2   209 1   5   2   206 1   
                                           5   2   206 1   210 1   206 1   210 1   206 1   200 1   209 1   7   255 102 0   209 1   102 0   220 1   102 0   220 1   112 0   224 1   112 0   224 1   164 0   224 1   164 0   224 1   174 0   220 1   174 0   220 1   174 0   209 1   174 0   209 1   164 0   
                                           206 1   164 0   206 1   112 0   206 1   112 0   206 1   102 0   209 1   7   255 102 0   9   1   102 0   20  1   102 0   20  1   112 0   23  1   112 0   23  1   164 0   23  1   164 0   23  1   174 0   20  1   174 0   20  1   174 0   9   1   174 0   9   1   
                                           164 0   5   1   164 0   5   1   112 0   5   1   112 0   5   1   102 0   9   1   7   255 55  0   5   1   54  0   9   1   54  0   9   1   52  0   13  1   52  0   13  1   48  0   15  1   48  0   15  1   44  0   16  1   44  0   16  1   41  0   15  1   41  0   
                                           15  1   37  0   13  1   37  0   13  1   35  0   9   1   35  0   9   1   34  0   5   1   34  0   5   1   35  0   1   1   35  0   1   1   37  0   254 0   37  0   254 0   41  0   252 0   41  0   252 0   44  0   251 0   44  0   251 0   48  0   252 0   48  0   
                                           252 0   52  0   254 0   52  0   254 0   54  0   1   1   54  0   1   1   55  0   5   1   7   255 24  0   5   1   65  0   5   1   7   255 44  0   241 0   44  0   26  1   7   255 146 2   5   1   145 2   9   1   145 2   9   1   143 2   13  1   143 2   13  1   
                                           140 2   15  1   140 2   15  1   136 2   16  1   136 2   16  1   132 2   15  1   132 2   15  1   128 2   13  1   128 2   13  1   126 2   9   1   126 2   9   1   125 2   5   1   125 2   5   1   126 2   1   1   126 2   1   1   128 2   254 0   128 2   254 0   
                                           132 2   252 0   132 2   252 0   136 2   251 0   136 2   251 0   140 2   252 0   140 2   252 0   143 2   254 0   143 2   254 0   145 2   1   1   145 2   1   1   146 2   5   1   7   255 115 2   5   1   157 2   5   1   7   255 136 2   241 0   136 2   26  1   
                                           7   255 146 2   224 1   145 2   228 1   145 2   228 1   143 2   231 1   143 2   231 1   140 2   233 1   140 2   233 1   136 2   234 1   136 2   234 1   132 2   233 1   132 2   233 1   128 2   231 1   128 2   231 1   126 2   228 1   126 2   228 1   125 2   
                                           224 1   125 2   224 1   126 2   220 1   126 2   220 1   128 2   216 1   128 2   216 1   132 2   214 1   132 2   214 1   136 2   213 1   136 2   213 1   140 2   214 1   140 2   214 1   143 2   216 1   143 2   216 1   145 2   220 1   145 2   220 1   146 2   
                                           224 1   7   255 115 2   224 1   157 2   224 1   7   255 136 2   203 1   136 2   244 1   7   255 55  0   224 1   54  0   228 1   54  0   228 1   52  0   231 1   52  0   231 1   48  0   233 1   48  0   233 1   44  0   234 1   44  0   234 1   41  0   233 1   
                                           41  0   233 1   37  0   231 1   37  0   231 1   35  0   228 1   35  0   228 1   34  0   224 1   34  0   224 1   35  0   220 1   35  0   220 1   37  0   216 1   37  0   216 1   41  0   214 1   41  0   214 1   44  0   213 1   44  0   213 1   48  0   214 1   
                                           48  0   214 1   52  0   216 1   52  0   216 1   54  0   220 1   54  0   220 1   55  0   224 1   7   255 24  0   224 1   65  0   224 1   7   255 44  0   203 1   44  0   244 1   7   255 148 0   224 1   148 0   228 1   148 0   228 1   145 0   231 1   145 0   
                                           231 1   142 0   233 1   142 0   233 1   138 0   234 1   138 0   234 1   134 0   233 1   134 0   233 1   131 0   231 1   131 0   231 1   128 0   228 1   128 0   228 1   128 0   224 1   128 0   224 1   128 0   220 1   128 0   220 1   131 0   216 1   131 0   
                                           216 1   134 0   214 1   134 0   214 1   138 0   213 1   138 0   213 1   142 0   214 1   142 0   214 1   145 0   216 1   145 0   216 1   148 0   220 1   148 0   220 1   148 0   224 1   7   255 117 0   224 1   159 0   224 1   7   255 138 0   203 1   138 0   
                                           244 1   7   255 246 1   224 1   245 1   228 1   245 1   228 1   243 1   231 1   243 1   231 1   240 1   233 1   240 1   233 1   236 1   234 1   236 1   234 1   232 1   233 1   232 1   233 1   228 1   231 1   228 1   231 1   226 1   228 1   226 1   228 1   
                                           225 1   224 1   225 1   224 1   226 1   220 1   226 1   220 1   228 1   216 1   228 1   216 1   232 1   214 1   232 1   214 1   236 1   213 1   236 1   213 1   240 1   214 1   240 1   214 1   243 1   216 1   243 1   216 1   245 1   220 1   245 1   220 1   
                                           246 1   224 1   7   255 215 1   224 1   1   2   224 1   7   255 236 1   203 1   236 1   244 1   7   255 148 0   5   1   148 0   9   1   148 0   9   1   145 0   13  1   145 0   13  1   142 0   15  1   142 0   15  1   138 0   16  1   138 0   16  1   134 0   
                                           15  1   134 0   15  1   131 0   13  1   131 0   13  1   128 0   9   1   128 0   9   1   128 0   5   1   128 0   5   1   128 0   1   1   128 0   1   1   131 0   254 0   131 0   254 0   134 0   252 0   134 0   252 0   138 0   251 0   138 0   251 0   142 0   
                                           252 0   142 0   252 0   145 0   254 0   145 0   254 0   148 0   1   1   148 0   1   1   148 0   5   1   7   255 117 0   5   1   159 0   5   1   7   255 138 0   241 0   138 0   26  1   7   255 246 1   5   1   245 1   9   1   245 1   9   1   243 1   13  1   
                                           243 1   13  1   240 1   15  1   240 1   15  1   236 1   16  1   236 1   16  1   232 1   15  1   232 1   15  1   228 1   13  1   228 1   13  1   226 1   9   1   226 1   9   1   225 1   5   1   225 1   5   1   226 1   1   1   226 1   1   1   228 1   254 0   
                                           228 1   254 0   232 1   252 0   232 1   252 0   236 1   251 0   236 1   251 0   240 1   252 0   240 1   252 0   243 1   254 0   243 1   254 0   245 1   1   1   245 1   1   1   246 1   5   1   7   255 215 1   5   1   1   2   5   1   7   255 236 1   241 0   
                                           236 1   26  1   7   255 148 0   115 1   148 0   118 1   148 0   118 1   145 0   122 1   145 0   122 1   142 0   124 1   142 0   124 1   138 0   125 1   138 0   125 1   134 0   124 1   134 0   124 1   131 0   122 1   131 0   122 1   128 0   118 1   128 0   
                                           118 1   128 0   115 1   128 0   115 1   128 0   111 1   128 0   111 1   131 0   107 1   131 0   107 1   134 0   105 1   134 0   105 1   138 0   104 1   138 0   104 1   142 0   105 1   142 0   105 1   145 0   107 1   145 0   107 1   148 0   111 1   148 0   
                                           111 1   148 0   115 1   7   255 117 0   115 1   159 0   115 1   7   255 138 0   94  1   138 0   135 1   7   255 146 2   115 1   145 2   118 1   145 2   118 1   143 2   122 1   143 2   122 1   140 2   124 1   140 2   124 1   136 2   125 1   136 2   125 1   
                                           132 2   124 1   132 2   124 1   128 2   122 1   128 2   122 1   126 2   118 1   126 2   118 1   125 2   115 1   125 2   115 1   126 2   111 1   126 2   111 1   128 2   107 1   128 2   107 1   132 2   105 1   132 2   105 1   136 2   104 1   136 2   104 1   
                                           140 2   105 1   140 2   105 1   143 2   107 1   143 2   107 1   145 2   111 1   145 2   111 1   146 2   115 1   7   255 115 2   115 1   157 2   115 1   7   255 136 2   94  1   136 2   135 1   7   255 229 2   246 0   58  6   246 0   58  6   246 0   58  6   
                                           239 1   58  6   239 1   229 2   239 1   229 2   239 1   229 2   246 0   7   255 229 2   246 0   229 2   246 0   7   255 229 2   246 0   229 2   246 0   7   255 136 2   115 1   229 2   115 1   7   255 152 2   115 1   152 2   120 1   152 2   120 1   149 2   
                                           124 1   149 2   124 1   146 2   128 1   146 2   128 1   141 2   130 1   141 2   130 1   136 2   131 1   136 2   131 1   131 2   130 1   131 2   130 1   126 2   128 1   126 2   128 1   122 2   124 1   122 2   124 1   120 2   120 1   120 2   120 1   119 2   
                                           115 1   119 2   115 1   120 2   109 1   120 2   109 1   122 2   105 1   122 2   105 1   126 2   101 1   126 2   101 1   131 2   99  1   131 2   99  1   136 2   98  1   136 2   98  1   141 2   99  1   141 2   99  1   146 2   101 1   146 2   101 1   149 2   
                                           )) "a")
 (_WriteStream FILE (vl-list->string (list 105 1   149 2   105 1   152 2   109 1   152 2   109 1   152 2   115 1   7   255 105 4   249 0   105 4   3   1   105 4   3   1   115 4   6   1   115 4   6   1   162 4   6   1   162 4   6   1   171 4   3   1   171 4   3   1   171 4   249 0   171 4   249 0   
                                           162 4   246 0   162 4   246 0   115 4   246 0   115 4   246 0   105 4   249 0   7   255 105 4   226 1   105 4   236 1   105 4   236 1   115 4   239 1   115 4   239 1   162 4   239 1   162 4   239 1   171 4   236 1   171 4   236 1   171 4   226 1   171 4   
                                           226 1   162 4   223 1   162 4   223 1   115 4   223 1   115 4   223 1   105 4   226 1   7   255 237 4   249 0   237 4   3   1   237 4   3   1   247 4   6   1   247 4   6   1   38  5   6   1   38  5   6   1   48  5   3   1   48  5   3   1   48  5   249 0   
                                           48  5   249 0   38  5   246 0   38  5   246 0   247 4   246 0   247 4   246 0   237 4   249 0   7   255 237 4   226 1   237 4   236 1   237 4   236 1   247 4   239 1   247 4   239 1   38  5   239 1   38  5   239 1   48  5   236 1   48  5   236 1   48  5   
                                           226 1   48  5   226 1   38  5   223 1   38  5   223 1   247 4   223 1   247 4   223 1   237 4   226 1   7   255 146 2   115 1   145 2   118 1   145 2   118 1   143 2   122 1   143 2   122 1   140 2   124 1   140 2   124 1   136 2   125 1   136 2   125 1   
                                           132 2   124 1   132 2   124 1   128 2   122 1   128 2   122 1   126 2   118 1   126 2   118 1   125 2   115 1   125 2   115 1   126 2   111 1   126 2   111 1   128 2   107 1   128 2   107 1   132 2   105 1   132 2   105 1   136 2   104 1   136 2   104 1   
                                           140 2   105 1   140 2   105 1   143 2   107 1   143 2   107 1   145 2   111 1   145 2   111 1   146 2   115 1   7   255 115 2   115 1   157 2   115 1   7   255 136 2   94  1   136 2   135 1   7   255 240 2   239 1   239 2   243 1   239 2   243 1   237 2   
                                           247 1   237 2   247 1   233 2   249 1   233 2   249 1   229 2   250 1   229 2   250 1   225 2   249 1   225 2   249 1   222 2   247 1   222 2   247 1   220 2   243 1   220 2   243 1   219 2   239 1   219 2   239 1   220 2   235 1   220 2   235 1   222 2   
                                           232 1   222 2   232 1   225 2   230 1   225 2   230 1   229 2   229 1   229 2   229 1   233 2   230 1   233 2   230 1   237 2   232 1   237 2   232 1   239 2   235 1   239 2   235 1   240 2   239 1   7   255 209 2   239 1   250 2   239 1   7   255 229 2   
                                           218 1   229 2   4   2   7   255 240 2   246 0   239 2   250 0   239 2   250 0   237 2   253 0   237 2   253 0   233 2   255 0   233 2   255 0   229 2   0   1   229 2   0   1   225 2   255 0   225 2   255 0   222 2   253 0   222 2   253 0   220 2   250 0   
                                           220 2   250 0   219 2   246 0   219 2   246 0   220 2   242 0   220 2   242 0   222 2   238 0   222 2   238 0   225 2   236 0   225 2   236 0   229 2   235 0   229 2   235 0   233 2   236 0   233 2   236 0   237 2   238 0   237 2   238 0   239 2   242 0   
                                           239 2   242 0   240 2   246 0   7   255 209 2   246 0   250 2   246 0   7   255 229 2   225 0   229 2   11  1   7   255 69  6   246 0   68  6   250 0   68  6   250 0   66  6   253 0   66  6   253 0   62  6   255 0   62  6   255 0   58  6   0   1   58  6   
                                           0   1   54  6   255 0   54  6   255 0   51  6   253 0   51  6   253 0   49  6   250 0   49  6   250 0   48  6   246 0   48  6   246 0   49  6   242 0   49  6   242 0   51  6   238 0   51  6   238 0   54  6   236 0   54  6   236 0   58  6   235 0   58  6   
                                           235 0   62  6   236 0   62  6   236 0   66  6   238 0   66  6   238 0   68  6   242 0   68  6   242 0   69  6   246 0   7   255 38  6   246 0   79  6   246 0   7   255 58  6   225 0   58  6   11  1   7   255 69  6   239 1   68  6   243 1   68  6   243 1   
                                           66  6   247 1   66  6   247 1   62  6   249 1   62  6   249 1   58  6   250 1   58  6   250 1   54  6   249 1   54  6   249 1   51  6   247 1   51  6   247 1   49  6   243 1   49  6   243 1   48  6   239 1   48  6   239 1   49  6   235 1   49  6   235 1   
                                           51  6   232 1   51  6   232 1   54  6   230 1   54  6   230 1   58  6   229 1   58  6   229 1   62  6   230 1   62  6   230 1   66  6   232 1   66  6   232 1   68  6   235 1   68  6   235 1   69  6   239 1   7   255 38  6   239 1   79  6   239 1   7   255 
                                           58  6   218 1   58  6   4   2   7   255 217 4   239 1   216 4   243 1   216 4   243 1   214 4   247 1   214 4   247 1   210 4   249 1   210 4   249 1   206 4   250 1   206 4   250 1   202 4   249 1   202 4   249 1   199 4   247 1   199 4   247 1   197 4   
                                           243 1   197 4   243 1   196 4   239 1   196 4   239 1   197 4   235 1   197 4   235 1   199 4   232 1   199 4   232 1   202 4   230 1   202 4   230 1   206 4   229 1   206 4   229 1   210 4   230 1   210 4   230 1   214 4   232 1   214 4   232 1   216 4   
                                           235 1   216 4   235 1   217 4   239 1   7   255 185 4   239 1   227 4   239 1   7   255 206 4   218 1   206 4   4   2   7   255 217 4   246 0   216 4   250 0   216 4   250 0   214 4   253 0   214 4   253 0   210 4   255 0   210 4   255 0   206 4   0   1   
                                           206 4   0   1   202 4   255 0   202 4   255 0   199 4   253 0   199 4   253 0   197 4   250 0   197 4   250 0   196 4   246 0   196 4   246 0   197 4   242 0   197 4   242 0   199 4   238 0   199 4   238 0   202 4   236 0   202 4   236 0   206 4   235 0   
                                           206 4   235 0   210 4   236 0   210 4   236 0   214 4   238 0   214 4   238 0   216 4   242 0   216 4   242 0   217 4   246 0   7   255 185 4   246 0   227 4   246 0   7   255 206 4   225 0   206 4   11  1   0   252 65  117 116 111 67  65  68  32  83  108 
                                           105 100 101 13  10  26  0   86  2   73  6   247 2   97  120 67  1   2   0   52  18  51  255 51  255 88  0   235 0   232 5   235 0   232 5   235 0   232 5   41  2   232 5   41  2   88  0   41  2   88  0   41  2   88  0   235 0   7   255 7   255 88  0   235 
                                           0   232 5   235 0   232 5   235 0   232 5   41  2   232 5   41  2   88  0   41  2   88  0   41  2   88  0   235 0   7   255 88  0   235 0   88  0   235 0   7   255 88  0   235 0   88  0   235 0   7   255 88  0   235 0   88  0   235 0   7   255 200 3   45  
                                           1   200 3   66  1   200 3   66  1   219 3   72  1   219 3   72  1   58  4   72  1   58  4   72  1   77  4   66  1   77  4   66  1   77  4   45  1   77  4   45  1   58  4   39  1   58  4   39  1   219 3   39  1   219 3   39  1   200 3   45  1   7   255 200 
                                           3   242 0   200 3   6   1   200 3   6   1   219 3   13  1   219 3   13  1   58  4   13  1   58  4   13  1   77  4   6   1   77  4   6   1   77  4   242 0   77  4   242 0   58  4   235 0   58  4   235 0   219 3   235 0   219 3   235 0   200 3   242 0   7   
                                           255 200 3   211 1   200 3   232 1   200 3   232 1   219 3   238 1   219 3   238 1   58  4   238 1   58  4   238 1   77  4   232 1   77  4   232 1   77  4   211 1   77  4   211 1   58  4   205 1   58  4   205 1   219 3   205 1   219 3   205 1   200 3   211 
                                           1   7   255 200 3   14  2   200 3   35  2   200 3   35  2   219 3   41  2   219 3   41  2   58  4   41  2   58  4   41  2   77  4   35  2   77  4   35  2   77  4   14  2   77  4   14  2   58  4   8   2   58  4   8   2   219 3   8   2   219 3   8   2   200 
                                           3   14  2   7   255 92  0   235 0   91  0   238 0   91  0   238 0   88  0   239 0   88  0   239 0   86  0   238 0   86  0   238 0   84  0   235 0   84  0   235 0   86  0   233 0   86  0   233 0   88  0   232 0   88  0   232 0   91  0   233 0   91  0   233 
                                           0   92  0   235 0   7   255 80  0   235 0   96  0   235 0   7   255 88  0   228 0   88  0   243 0   7   255 92  0   41  2   91  0   44  2   91  0   44  2   88  0   45  2   88  0   45  2   86  0   44  2   86  0   44  2   84  0   41  2   84  0   41  2   86  
                                           0   39  2   86  0   39  2   88  0   37  2   88  0   37  2   91  0   39  2   91  0   39  2   92  0   41  2   7   255 80  0   41  2   96  0   41  2   7   255 88  0   33  2   88  0   49  2   7   255 236 5   41  2   235 5   44  2   235 5   44  2   232 5   45  
                                           2   232 5   45  2   229 5   44  2   229 5   44  2   228 5   41  2   228 5   41  2   229 5   39  2   229 5   39  2   232 5   37  2   232 5   37  2   235 5   39  2   235 5   39  2   236 5   41  2   7   255 224 5   41  2   240 5   41  2   7   255 232 5   33  
                                           2   232 5   49  2   7   255 236 5   235 0   235 5   238 0   235 5   238 0   232 5   239 0   232 5   239 0   229 5   238 0   229 5   238 0   228 5   235 0   228 5   235 0   229 5   233 0   229 5   233 0   232 5   232 0   232 5   232 0   235 5   233 0   235 
                                           5   233 0   236 5   235 0   7   255 224 5   235 0   240 5   235 0   7   255 232 5   228 0   232 5   243 0   7   255 15  4   235 0   13  4   238 0   13  4   238 0   11  4   239 0   11  4   239 0   8   4   238 0   8   4   238 0   7   4   235 0   7   4   235 
                                           0   8   4   233 0   8   4   233 0   11  4   232 0   11  4   232 0   13  4   233 0   13  4   233 0   15  4   235 0   7   255 3   4   235 0   19  4   235 0   7   255 11  4   228 0   11  4   243 0   7   255 15  4   41  2   13  4   44  2   13  4   44  2   11  
                                           4   45  2   11  4   45  2   8   4   44  2   8   4   44  2   7   4   41  2   7   4   41  2   8   4   39  2   8   4   39  2   11  4   37  2   11  4   37  2   13  4   39  2   13  4   39  2   15  4   41  2   7   255 3   4   41  2   19  4   41  2   7   255 11  
                                           4   33  2   11  4   49  2   7   255 192 0   138 1   191 0   141 1   191 0   141 1   188 0   142 1   188 0   142 1   185 0   141 1   185 0   141 1   184 0   138 1   184 0   138 1   185 0   136 1   185 0   136 1   188 0   134 1   188 0   134 1   191 0   136 
                                           1   191 0   136 1   192 0   138 1   7   255 180 0   138 1   196 0   138 1   7   255 188 0   130 1   188 0   146 1   7   255 192 0   235 0   191 0   238 0   191 0   238 0   188 0   239 0   188 0   239 0   185 0   238 0   185 0   238 0   184 0   235 0   184 
                                           0   235 0   185 0   233 0   185 0   233 0   188 0   232 0   188 0   232 0   191 0   233 0   191 0   233 0   192 0   235 0   7   255 180 0   235 0   196 0   235 0   7   255 188 0   228 0   188 0   243 0   7   255 192 0   41  2   191 0   44  2   191 0   44  
                                           2   188 0   45  2   188 0   45  2   185 0   44  2   185 0   44  2   184 0   41  2   184 0   41  2   185 0   39  2   185 0   39  2   188 0   37  2   188 0   37  2   191 0   39  2   191 0   39  2   192 0   41  2   7   255 180 0   41  2   196 0   41  2   7   
                                           255 188 0   33  2   188 0   49  2   7   255 122 0   14  2   122 0   35  2   122 0   35  2   140 0   41  2   140 0   41  2   236 0   41  2   236 0   41  2   254 0   35  2   254 0   35  2   254 0   14  2   254 0   14  2   236 0   8   2   236 0   8   2   140 
                                           0   8   2   140 0   8   2   122 0   14  2   7   255 122 0   242 0   122 0   6   1   122 0   6   1   140 0   13  1   140 0   13  1   236 0   13  1   236 0   13  1   254 0   6   1   254 0   6   1   254 0   242 0   254 0   242 0   236 0   235 0   236 0   235 
                                           0   140 0   235 0   140 0   235 0   122 0   242 0   0   252 65  117 116 111 67  65  68  32  83  108 105 100 101 13  10  26  0   86  2   130 13  236 6   48  197 41  1   2   0   52  18  7   255 7   255 44  8   172 2   90  13  172 2   90  13  172 2   90  13  
                                           55  4   90  13  55  4   44  8   55  4   44  8   55  4   44  8   172 2   7   255 44  8   172 2   44  8   172 2   7   255 44  8   172 2   44  8   172 2   7   255 187 8   113 3   186 8   120 3   186 8   120 3   183 8   127 3   183 8   127 3   179 8   132 3   
                                           179 8   132 3   173 8   136 3   173 8   136 3   167 8   139 3   167 8   139 3   160 8   140 3   160 8   140 3   153 8   139 3   153 8   139 3   147 8   136 3   147 8   136 3   141 8   132 3   141 8   132 3   137 8   127 3   137 8   127 3   135 8   120 3   
                                           135 8   120 3   134 8   113 3   134 8   113 3   135 8   107 3   135 8   107 3   137 8   100 3   137 8   100 3   141 8   95  3   141 8   95  3   147 8   91  3   147 8   91  3   153 8   88  3   153 8   88  3   160 8   87  3   160 8   87  3   167 8   88  3   
                                           167 8   88  3   173 8   91  3   173 8   91  3   179 8   95  3   179 8   95  3   183 8   100 3   183 8   100 3   186 8   107 3   186 8   107 3   187 8   113 3   7   255 129 12  249 2   129 12  17  3   129 12  17  3   150 12  24  3   150 12  24  3   6   13  
                                           24  3   6   13  24  3   28  13  17  3   28  13  17  3   28  13  249 2   28  13  249 2   6   13  242 2   6   13  242 2   150 12  242 2   150 12  242 2   129 12  249 2   7   255 129 12  179 2   129 12  203 2   129 12  203 2   150 12  211 2   150 12  211 2   
                                           6   13  211 2   6   13  211 2   28  13  203 2   28  13  203 2   28  13  179 2   28  13  179 2   6   13  172 2   6   13  172 2   150 12  172 2   150 12  172 2   129 12  179 2   7   255 129 12  210 3   129 12  234 3   129 12  234 3   150 12  241 3   150 12  
                                           241 3   6   13  241 3   6   13  241 3   28  13  234 3   28  13  234 3   28  13  210 3   28  13  210 3   6   13  203 3   6   13  203 3   150 12  203 3   150 12  203 3   129 12  210 3   7   255 129 12  24  4   129 12  48  4   129 12  48  4   150 12  55  4   
                                           150 12  55  4   6   13  55  4   6   13  55  4   28  13  48  4   28  13  48  4   28  13  24  4   28  13  24  4   6   13  16  4   6   13  16  4   150 12  16  4   150 12  16  4   129 12  24  4   7   255 165 8   113 3   164 8   116 3   164 8   116 3   162 8   
                                           117 3   162 8   117 3   160 8   118 3   160 8   118 3   158 8   117 3   158 8   117 3   156 8   116 3   156 8   116 3   155 8   113 3   155 8   113 3   156 8   111 3   156 8   111 3   158 8   109 3   158 8   109 3   160 8   109 3   160 8   109 3   162 8   
                                           109 3   162 8   109 3   164 8   111 3   164 8   111 3   165 8   113 3   7   255 151 8   113 3   169 8   113 3   7   255 160 8   104 3   160 8   123 3   7   255 48  8   172 2   48  8   174 2   48  8   174 2   46  8   176 2   46  8   176 2   44  8   176 2   
                                           44  8   176 2   42  8   176 2   42  8   176 2   40  8   174 2   40  8   174 2   39  8   172 2   39  8   172 2   40  8   169 2   40  8   169 2   42  8   168 2   42  8   168 2   44  8   167 2   44  8   167 2   46  8   168 2   46  8   168 2   48  8   169 2   
                                           48  8   169 2   48  8   172 2   7   255 35  8   172 2   53  8   172 2   7   255 44  8   162 2   44  8   181 2   7   255 48  8   55  4   48  8   57  4   48  8   57  4   46  8   59  4   46  8   59  4   44  8   60  4   44  8   60  4   42  8   59  4   42  8   
                                           59  4   40  8   57  4   40  8   57  4   39  8   55  4   39  8   55  4   40  8   53  4   40  8   53  4   42  8   51  4   42  8   51  4   44  8   50  4   44  8   50  4   46  8   51  4   46  8   51  4   48  8   53  4   48  8   53  4   48  8   55  4   7   255 
                                           35  8   55  4   53  8   55  4   7   255 44  8   46  4   44  8   64  4   7   255 211 12  55  4   210 12  57  4   210 12  57  4   209 12  59  4   209 12  59  4   206 12  60  4   206 12  60  4   204 12  59  4   204 12  59  4   202 12  57  4   202 12  57  4   
                                           202 12  55  4   202 12  55  4   202 12  53  4   202 12  53  4   204 12  51  4   204 12  51  4   206 12  50  4   206 12  50  4   209 12  51  4   209 12  51  4   210 12  53  4   210 12  53  4   211 12  55  4   7   255 197 12  55  4   215 12  55  4   7   255 
                                           206 12  46  4   206 12  64  4   7   255 94  13  55  4   94  13  57  4   94  13  57  4   92  13  59  4   92  13  59  4   90  13  60  4   90  13  60  4   87  13  59  4   87  13  59  4   86  13  57  4   86  13  57  4   85  13  55  4   85  13  55  4   86  13  
                                           53  4   86  13  53  4   87  13  51  4   87  13  51  4   90  13  50  4   90  13  50  4   92  13  51  4   92  13  51  4   94  13  53  4   94  13  53  4   94  13  55  4   7   255 80  13  55  4   99  13  55  4   7   255 90  13  46  4   90  13  64  4   7   255 
                                           94  13  172 2   94  13  174 2   94  13  174 2   92  13  176 2   92  13  176 2   90  13  176 2   90  13  176 2   87  13  176 2   87  13  176 2   86  13  174 2   86  13  174 2   85  13  172 2   85  13  172 2   86  13  169 2   86  13  169 2   87  13  168 2   
                                           87  13  168 2   90  13  167 2   90  13  167 2   92  13  168 2   92  13  168 2   94  13  169 2   94  13  169 2   94  13  172 2   7   255 80  13  172 2   99  13  172 2   7   255 90  13  162 2   90  13  181 2   7   255 211 12  172 2   210 12  174 2   210 12  
                                           174 2   209 12  176 2   209 12  176 2   206 12  176 2   206 12  176 2   204 12  176 2   204 12  176 2   202 12  174 2   202 12  174 2   202 12  172 2   202 12  172 2   202 12  169 2   202 12  169 2   204 12  168 2   204 12  168 2   206 12  167 2   206 12  
                                           167 2   209 12  168 2   209 12  168 2   210 12  169 2   210 12  169 2   211 12  172 2   7   255 197 12  172 2   215 12  172 2   7   255 206 12  162 2   206 12  181 2   7   255 90  7   113 3   160 8   113 3   7   255 117 7   113 3   116 7   120 3   116 7   
                                           120 3   113 7   127 3   113 7   127 3   109 7   132 3   109 7   132 3   104 7   136 3   104 7   136 3   97  7   139 3   97  7   139 3   90  7   140 3   90  7   140 3   84  7   139 3   84  7   139 3   77  7   136 3   77  7   136 3   72  7   132 3   72  7   
                                           )) "a")
 (_WriteStream FILE (vl-list->string (list 132 3   68  7   127 3   68  7   127 3   65  7   120 3   65  7   120 3   64  7   113 3   64  7   113 3   65  7   107 3   65  7   107 3   68  7   100 3   68  7   100 3   72  7   95  3   72  7   95  3   77  7   91  3   77  7   91  3   84  7   88  3   84  7   
                                           88  3   90  7   87  3   90  7   87  3   97  7   88  3   97  7   88  3   104 7   91  3   104 7   91  3   109 7   95  3   109 7   95  3   113 7   100 3   113 7   100 3   116 7   107 3   116 7   107 3   117 7   113 3   7   255 83  8   249 2   83  8   17  3   
                                           83  8   17  3   104 8   24  3   104 8   24  3   216 8   24  3   216 8   24  3   238 8   17  3   238 8   17  3   238 8   249 2   238 8   249 2   216 8   242 2   216 8   242 2   104 8   242 2   104 8   242 2   83  8   249 2   7   255 83  8   179 2   83  8   
                                           203 2   83  8   203 2   104 8   211 2   104 8   211 2   216 8   211 2   216 8   211 2   238 8   203 2   238 8   203 2   238 8   179 2   238 8   179 2   216 8   172 2   216 8   172 2   104 8   172 2   104 8   172 2   83  8   179 2   7   255 83  8   210 3   
                                           83  8   234 3   83  8   234 3   104 8   241 3   104 8   241 3   216 8   241 3   216 8   241 3   238 8   234 3   238 8   234 3   238 8   210 3   238 8   210 3   216 8   203 3   216 8   203 3   104 8   203 3   104 8   203 3   83  8   210 3   7   255 83  8   
                                           24  4   83  8   48  4   83  8   48  4   104 8   55  4   104 8   55  4   216 8   55  4   216 8   55  4   238 8   48  4   238 8   48  4   238 8   24  4   238 8   24  4   216 8   16  4   216 8   16  4   104 8   16  4   104 8   16  4   83  8   24  4   7   255 
                                           95  7   113 3   95  7   116 3   95  7   116 3   93  7   117 3   93  7   117 3   90  7   118 3   90  7   118 3   88  7   117 3   88  7   117 3   86  7   116 3   86  7   116 3   86  7   113 3   86  7   113 3   86  7   111 3   86  7   111 3   88  7   109 3   
                                           88  7   109 3   90  7   109 3   90  7   109 3   93  7   109 3   93  7   109 3   95  7   111 3   95  7   111 3   95  7   113 3   7   255 81  7   113 3   100 7   113 3   7   255 90  7   104 3   90  7   123 3   7   255 165 8   113 3   164 8   116 3   164 8   
                                           116 3   162 8   117 3   162 8   117 3   160 8   118 3   160 8   118 3   158 8   117 3   158 8   117 3   156 8   116 3   156 8   116 3   155 8   113 3   155 8   113 3   156 8   111 3   156 8   111 3   158 8   109 3   158 8   109 3   160 8   109 3   160 8   
                                           109 3   162 8   109 3   162 8   109 3   164 8   111 3   164 8   111 3   165 8   113 3   7   255 151 8   113 3   169 8   113 3   7   255 160 8   104 3   160 8   123 3   7   255 165 8   172 2   164 8   174 2   164 8   174 2   162 8   176 2   162 8   176 2   
                                           160 8   176 2   160 8   176 2   158 8   176 2   158 8   176 2   156 8   174 2   156 8   174 2   155 8   172 2   155 8   172 2   156 8   169 2   156 8   169 2   158 8   168 2   158 8   168 2   160 8   167 2   160 8   167 2   162 8   168 2   162 8   168 2   
                                           164 8   169 2   164 8   169 2   165 8   172 2   7   255 151 8   172 2   169 8   172 2   7   255 160 8   162 2   160 8   181 2   7   255 165 8   55  4   164 8   57  4   164 8   57  4   162 8   59  4   162 8   59  4   160 8   60  4   160 8   60  4   158 8   
                                           59  4   158 8   59  4   156 8   57  4   156 8   57  4   155 8   55  4   155 8   55  4   156 8   53  4   156 8   53  4   158 8   51  4   158 8   51  4   160 8   50  4   160 8   50  4   162 8   51  4   162 8   51  4   164 8   53  4   164 8   53  4   165 8   
                                           55  4   7   255 151 8   55  4   169 8   55  4   7   255 160 8   46  4   160 8   64  4   7   255 45  2   172 2   90  7   172 2   90  7   172 2   90  7   55  4   90  7   55  4   45  2   55  4   45  2   55  4   45  2   172 2   7   255 45  2   172 2   45  2   
                                           172 2   7   255 45  2   172 2   45  2   172 2   7   255 177 2   113 3   175 2   119 3   175 2   119 3   172 2   125 3   172 2   125 3   167 2   128 3   167 2   128 3   161 2   129 3   161 2   129 3   155 2   128 3   155 2   128 3   150 2   125 3   150 2   
                                           125 3   146 2   119 3   146 2   119 3   145 2   113 3   145 2   113 3   146 2   107 3   146 2   107 3   150 2   102 3   150 2   102 3   155 2   99  3   155 2   99  3   161 2   98  3   161 2   98  3   167 2   99  3   167 2   99  3   172 2   102 3   172 2   
                                           102 3   175 2   107 3   175 2   107 3   177 2   113 3   7   255 129 6   249 2   129 6   17  3   129 6   17  3   151 6   24  3   151 6   24  3   7   7   24  3   7   7   24  3   28  7   17  3   28  7   17  3   28  7   249 2   28  7   249 2   7   7   242 2   
                                           7   7   242 2   151 6   242 2   151 6   242 2   129 6   249 2   7   255 129 6   179 2   129 6   203 2   129 6   203 2   151 6   211 2   151 6   211 2   7   7   211 2   7   7   211 2   28  7   203 2   28  7   203 2   28  7   179 2   28  7   179 2   7   7   
                                           172 2   7   7   172 2   151 6   172 2   151 6   172 2   129 6   179 2   7   255 129 6   210 3   129 6   234 3   129 6   234 3   151 6   241 3   151 6   241 3   7   7   241 3   7   7   241 3   28  7   234 3   28  7   234 3   28  7   210 3   28  7   210 3   
                                           7   7   203 3   7   7   203 3   151 6   203 3   151 6   203 3   129 6   210 3   7   255 129 6   24  4   129 6   48  4   129 6   48  4   151 6   55  4   151 6   55  4   7   7   55  4   7   7   55  4   28  7   48  4   28  7   48  4   28  7   24  4   28  7   
                                           24  4   7   7   16  4   7   7   16  4   151 6   16  4   151 6   16  4   129 6   24  4   7   255 165 2   113 3   165 2   116 3   165 2   116 3   163 2   117 3   163 2   117 3   161 2   118 3   161 2   118 3   159 2   117 3   159 2   117 3   157 2   116 3   
                                           157 2   116 3   156 2   113 3   156 2   113 3   157 2   111 3   157 2   111 3   159 2   109 3   159 2   109 3   161 2   109 3   161 2   109 3   163 2   109 3   163 2   109 3   165 2   111 3   165 2   111 3   165 2   113 3   7   255 152 2   113 3   170 2   
                                           113 3   7   255 161 2   104 3   161 2   123 3   7   255 49  2   172 2   49  2   174 2   49  2   174 2   47  2   176 2   47  2   176 2   45  2   176 2   45  2   176 2   42  2   176 2   42  2   176 2   41  2   174 2   41  2   174 2   40  2   172 2   40  2   
                                           172 2   41  2   169 2   41  2   169 2   42  2   168 2   42  2   168 2   45  2   167 2   45  2   167 2   47  2   168 2   47  2   168 2   49  2   169 2   49  2   169 2   49  2   172 2   7   255 35  2   172 2   54  2   172 2   7   255 45  2   162 2   45  2   
                                           181 2   7   255 49  2   55  4   49  2   57  4   49  2   57  4   47  2   59  4   47  2   59  4   45  2   60  4   45  2   60  4   42  2   59  4   42  2   59  4   41  2   57  4   41  2   57  4   40  2   55  4   40  2   55  4   41  2   53  4   41  2   53  4   
                                           42  2   51  4   42  2   51  4   45  2   50  4   45  2   50  4   47  2   51  4   47  2   51  4   49  2   53  4   49  2   53  4   49  2   55  4   7   255 35  2   55  4   54  2   55  4   7   255 45  2   46  4   45  2   64  4   7   255 212 6   55  4   211 6   
                                           57  4   211 6   57  4   209 6   59  4   209 6   59  4   207 6   60  4   207 6   60  4   205 6   59  4   205 6   59  4   203 6   57  4   203 6   57  4   202 6   55  4   202 6   55  4   203 6   53  4   203 6   53  4   205 6   51  4   205 6   51  4   207 6   
                                           50  4   207 6   50  4   209 6   51  4   209 6   51  4   211 6   53  4   211 6   53  4   212 6   55  4   7   255 198 6   55  4   216 6   55  4   7   255 207 6   46  4   207 6   64  4   7   255 95  7   55  4   95  7   57  4   95  7   57  4   93  7   59  4   
                                           93  7   59  4   90  7   60  4   90  7   60  4   88  7   59  4   88  7   59  4   86  7   57  4   86  7   57  4   86  7   55  4   86  7   55  4   86  7   53  4   86  7   53  4   88  7   51  4   88  7   51  4   90  7   50  4   90  7   50  4   93  7   51  4   
                                           93  7   51  4   95  7   53  4   95  7   53  4   95  7   55  4   7   255 81  7   55  4   100 7   55  4   7   255 90  7   46  4   90  7   64  4   7   255 212 6   172 2   211 6   174 2   211 6   174 2   209 6   176 2   209 6   176 2   207 6   176 2   207 6   
                                           176 2   205 6   176 2   205 6   176 2   203 6   174 2   203 6   174 2   202 6   172 2   202 6   172 2   203 6   169 2   203 6   169 2   205 6   168 2   205 6   168 2   207 6   167 2   207 6   167 2   209 6   168 2   209 6   168 2   211 6   169 2   211 6   
                                           169 2   212 6   172 2   7   255 198 6   172 2   216 6   172 2   7   255 207 6   162 2   207 6   181 2   7   255 95  7   172 2   95  7   174 2   95  7   174 2   93  7   176 2   93  7   176 2   90  7   176 2   90  7   176 2   88  7   176 2   88  7   176 2   
                                           86  7   174 2   86  7   174 2   86  7   172 2   86  7   172 2   86  7   169 2   86  7   169 2   88  7   168 2   88  7   168 2   90  7   167 2   90  7   167 2   93  7   168 2   93  7   168 2   95  7   169 2   95  7   169 2   95  7   172 2   7   255 81  7   
                                           172 2   100 7   172 2   7   255 90  7   162 2   90  7   181 2   7   255 95  7   113 3   95  7   116 3   95  7   116 3   93  7   117 3   93  7   117 3   90  7   118 3   90  7   118 3   88  7   117 3   88  7   117 3   86  7   116 3   86  7   116 3   86  7   
                                           113 3   86  7   113 3   86  7   111 3   86  7   111 3   88  7   109 3   88  7   109 3   90  7   109 3   90  7   109 3   93  7   109 3   93  7   109 3   95  7   111 3   95  7   111 3   95  7   113 3   7   255 81  7   113 3   100 7   113 3   7   255 90  7   
                                           104 3   90  7   123 3   7   255 54  0   183 2   100 1   183 2   100 1   183 2   100 1   36  3   100 1   36  3   161 2   36  3   161 2   36  3   161 2   191 3   161 2   191 3   100 1   191 3   100 1   191 3   100 1   43  4   100 1   43  4   54  0   43  4   
                                           54  0   43  4   54  0   183 2   7   255 54  0   183 2   54  0   183 2   7   255 54  0   183 2   54  0   183 2   7   255 198 2   151 3   190 2   158 3   190 2   158 3   181 2   163 3   181 2   163 3   171 2   166 3   171 2   166 3   161 2   167 3   161 2   
                                           167 3   150 2   166 3   150 2   166 3   140 2   163 3   140 2   163 3   131 2   158 3   131 2   158 3   123 2   151 3   123 2   151 3   117 2   143 3   117 2   143 3   112 2   134 3   112 2   134 3   109 2   124 3   109 2   124 3   108 2   113 3   108 2   
                                           113 3   109 2   103 3   109 2   103 3   112 2   93  3   112 2   93  3   117 2   84  3   117 2   84  3   123 2   76  3   123 2   76  3   131 2   69  3   131 2   69  3   140 2   64  3   140 2   64  3   150 2   61  3   150 2   61  3   161 2   60  3   161 2   
                                           60  3   171 2   61  3   171 2   61  3   181 2   64  3   181 2   64  3   190 2   69  3   190 2   69  3   198 2   76  3   7   255 198 2   76  3   198 2   151 3   7   255 83  2   4   3   83  2   29  3   83  2   29  3   105 2   36  3   105 2   36  3   217 2   
                                           36  3   217 2   36  3   238 2   29  3   238 2   29  3   238 2   4   3   238 2   4   3   217 2   253 2   217 2   253 2   105 2   253 2   105 2   253 2   83  2   4   3   7   255 83  2   191 2   83  2   215 2   83  2   215 2   105 2   222 2   105 2   222 2   
                                           217 2   222 2   217 2   222 2   238 2   215 2   238 2   215 2   238 2   191 2   238 2   191 2   217 2   183 2   217 2   183 2   105 2   183 2   105 2   183 2   83  2   191 2   7   255 83  2   198 3   83  2   222 3   83  2   222 3   105 2   230 3   105 2   
                                           230 3   217 2   230 3   217 2   230 3   238 2   222 3   238 2   222 3   238 2   198 3   238 2   198 3   217 2   191 3   217 2   191 3   105 2   191 3   105 2   191 3   83  2   198 3   7   255 83  2   12  4   83  2   36  4   83  2   36  4   105 2   43  4   
                                           105 2   43  4   217 2   43  4   217 2   43  4   238 2   36  4   238 2   36  4   238 2   12  4   238 2   12  4   217 2   5   4   217 2   5   4   105 2   5   4   105 2   5   4   83  2   12  4   7   255 166 0   113 3   165 0   116 3   165 0   116 3   163 0   
                                           117 3   163 0   117 3   161 0   118 3   161 0   118 3   159 0   117 3   159 0   117 3   157 0   116 3   157 0   116 3   156 0   113 3   156 0   113 3   157 0   111 3   157 0   111 3   159 0   109 3   159 0   109 3   161 0   109 3   161 0   109 3   163 0   
                                           109 3   163 0   109 3   165 0   111 3   165 0   111 3   166 0   113 3   7   255 152 0   113 3   170 0   113 3   7   255 161 0   104 3   161 0   123 3   7   255 165 2   113 3   165 2   116 3   165 2   116 3   163 2   117 3   163 2   117 3   161 2   118 3   
                                           161 2   118 3   159 2   117 3   159 2   117 3   157 2   116 3   157 2   116 3   156 2   113 3   156 2   113 3   157 2   111 3   157 2   111 3   159 2   109 3   159 2   109 3   161 2   109 3   161 2   109 3   163 2   109 3   163 2   109 3   165 2   111 3   
                                           165 2   111 3   165 2   113 3   7   255 152 2   113 3   170 2   113 3   7   255 161 2   104 3   161 2   123 3   7   255 166 0   183 2   165 0   186 2   165 0   186 2   163 0   187 2   163 0   187 2   161 0   188 2   161 0   188 2   159 0   187 2   159 0   
                                           187 2   157 0   186 2   157 0   186 2   156 0   183 2   156 0   183 2   157 0   181 2   157 0   181 2   159 0   179 2   159 0   179 2   161 0   179 2   161 0   179 2   163 0   179 2   163 0   179 2   165 0   181 2   165 0   181 2   166 0   183 2   7   255 
                                           152 0   183 2   170 0   183 2   7   255 161 0   174 2   161 0   193 2   7   255 165 2   183 2   165 2   186 2   165 2   186 2   163 2   187 2   163 2   187 2   161 2   188 2   161 2   188 2   159 2   187 2   159 2   187 2   157 2   186 2   157 2   186 2   
                                           156 2   183 2   156 2   183 2   157 2   181 2   157 2   181 2   159 2   179 2   159 2   179 2   161 2   179 2   161 2   179 2   163 2   179 2   163 2   179 2   165 2   181 2   165 2   181 2   165 2   183 2   7   255 152 2   183 2   170 2   183 2   7   255 
                                           161 2   174 2   161 2   193 2   7   255 165 2   43  4   165 2   46  4   165 2   46  4   163 2   48  4   163 2   48  4   161 2   48  4   161 2   48  4   159 2   48  4   159 2   48  4   157 2   46  4   157 2   46  4   156 2   43  4   156 2   43  4   157 2   
                                           41  4   157 2   41  4   159 2   39  4   159 2   39  4   161 2   39  4   161 2   39  4   163 2   39  4   163 2   39  4   165 2   41  4   165 2   41  4   165 2   43  4   7   255 152 2   43  4   170 2   43  4   7   255 161 2   34  4   161 2   53  4   7   255 
                                           166 0   43  4   165 0   46  4   165 0   46  4   163 0   48  4   163 0   48  4   161 0   48  4   161 0   48  4   159 0   48  4   159 0   48  4   157 0   46  4   157 0   46  4   156 0   43  4   156 0   43  4   157 0   41  4   157 0   41  4   159 0   39  4   
                                           159 0   39  4   161 0   39  4   161 0   39  4   163 0   39  4   163 0   39  4   165 0   41  4   165 0   41  4   166 0   43  4   7   255 152 0   43  4   170 0   43  4   7   255 161 0   34  4   161 0   53  4   7   255 59  0   43  4   58  0   46  4   58  0   
                                           46  4   56  0   48  4   56  0   48  4   54  0   48  4   54  0   48  4   52  0   48  4   52  0   48  4   50  0   46  4   50  0   46  4   49  0   43  4   49  0   43  4   50  0   41  4   50  0   41  4   52  0   39  4   52  0   39  4   54  0   39  4   54  0   
                                           39  4   56  0   39  4   56  0   39  4   58  0   41  4   58  0   41  4   59  0   43  4   7   255 45  0   43  4   63  0   43  4   7   255 54  0   34  4   54  0   53  4   7   255 59  0   183 2   58  0   186 2   58  0   186 2   56  0   187 2   56  0   187 2   
                                           54  0   188 2   54  0   188 2   52  0   187 2   52  0   187 2   50  0   186 2   50  0   186 2   49  0   183 2   49  0   183 2   50  0   181 2   50  0   181 2   52  0   179 2   52  0   179 2   54  0   179 2   54  0   179 2   56  0   179 2   56  0   179 2   
                                           58  0   181 2   58  0   181 2   59  0   183 2   7   255 45  0   183 2   63  0   183 2   7   255 54  0   174 2   54  0   193 2   7   255 84  0   12  4   84  0   36  4   84  0   36  4   105 0   43  4   105 0   43  4   217 0   43  4   217 0   43  4   239 0   
                                           36  4   239 0   36  4   239 0   12  4   239 0   12  4   217 0   5   4   217 0   5   4   105 0   5   4   105 0   5   4   84  0   12  4   7   255 84  0   191 2   84  0   215 2   84  0   215 2   105 0   222 2   105 0   222 2   217 0   222 2   217 0   222 2   
                                           239 0   215 2   239 0   215 2   239 0   191 2   239 0   191 2   217 0   183 2   217 0   183 2   105 0   183 2   105 0   183 2   84  0   191 2   0   252 65  117 116 111 67  65  68  32  83  108 105 100 101 13  10  26  0   86  2   106 6   234 2   99  219 79  
                                           1   2   0   52  18  7   255 7   255 24  0   81  1   160 0   81  1   160 0   81  1   160 0   106 1   160 0   106 1   2   1   106 1   2   1   106 1   2   1   137 1   2   1   137 1   160 0   137 1   160 0   137 1   160 0   161 1   160 0   161 1   24  0   161 
                                           1   24  0   161 1   24  0   81  1   7   255 24  0   81  1   24  0   81  1   7   255 24  0   81  1   24  0   81  1   7   255 231 0   128 1   229 0   130 1   229 0   130 1   226 0   131 1   226 0   131 1   223 0   131 1   223 0   131 1   220 0   130 1   220 
                                           0   130 1   217 0   128 1   217 0   128 1   216 0   126 1   216 0   126 1   215 0   123 1   215 0   123 1   215 0   120 1   215 0   120 1   216 0   117 1   216 0   117 1   217 0   114 1   217 0   114 1   220 0   113 1   220 0   113 1   223 0   112 1   223 
                                           )) "a")
 (_WriteStream FILE (vl-list->string (list 0   112 1   226 0   112 1   226 0   112 1   229 0   113 1   229 0   113 1   231 0   114 1   7   255 231 0   114 1   231 0   128 1   7   255 177 0   100 1   177 0   105 1   177 0   105 1   181 0   106 1   181 0   106 1   200 0   106 1   200 0   106 1   204 
                                           0   105 1   204 0   105 1   204 0   100 1   204 0   100 1   200 0   99  1   200 0   99  1   181 0   99  1   181 0   99  1   177 0   100 1   7   255 177 0   88  1   177 0   93  1   177 0   93  1   181 0   94  1   181 0   94  1   200 0   94  1   200 0   94  
                                           1   204 0   93  1   204 0   93  1   204 0   88  1   204 0   88  1   200 0   87  1   200 0   87  1   181 0   87  1   181 0   87  1   177 0   88  1   7   255 177 0   138 1   177 0   142 1   177 0   142 1   181 0   143 1   181 0   143 1   200 0   143 1   200 
                                           0   143 1   204 0   142 1   204 0   142 1   204 0   138 1   204 0   138 1   200 0   137 1   200 0   137 1   181 0   137 1   181 0   137 1   177 0   138 1   7   255 177 0   150 1   177 0   154 1   177 0   154 1   181 0   155 1   181 0   155 1   200 0   155 
                                           1   200 0   155 1   204 0   154 1   204 0   154 1   204 0   150 1   204 0   150 1   200 0   149 1   200 0   149 1   181 0   149 1   181 0   149 1   177 0   150 1   7   255 211 0   100 1   211 0   105 1   211 0   105 1   215 0   106 1   215 0   106 1   234 
                                           0   106 1   234 0   106 1   238 0   105 1   238 0   105 1   238 0   100 1   238 0   100 1   234 0   99  1   234 0   99  1   215 0   99  1   215 0   99  1   211 0   100 1   7   255 211 0   88  1   211 0   93  1   211 0   93  1   215 0   94  1   215 0   94  
                                           1   234 0   94  1   234 0   94  1   238 0   93  1   238 0   93  1   238 0   88  1   238 0   88  1   234 0   87  1   234 0   87  1   215 0   87  1   215 0   87  1   211 0   88  1   7   255 211 0   138 1   211 0   142 1   211 0   142 1   215 0   143 1   215 
                                           0   143 1   234 0   143 1   234 0   143 1   238 0   142 1   238 0   142 1   238 0   138 1   238 0   138 1   234 0   137 1   234 0   137 1   215 0   137 1   215 0   137 1   211 0   138 1   7   255 211 0   150 1   211 0   154 1   211 0   154 1   215 0   155 
                                           1   215 0   155 1   234 0   155 1   234 0   155 1   238 0   154 1   238 0   154 1   238 0   150 1   238 0   150 1   234 0   149 1   234 0   149 1   215 0   149 1   215 0   149 1   211 0   150 1   7   255 244 0   100 1   244 0   105 1   244 0   105 1   248 
                                           0   106 1   248 0   106 1   11  1   106 1   11  1   106 1   15  1   105 1   15  1   105 1   15  1   100 1   15  1   100 1   11  1   99  1   11  1   99  1   248 0   99  1   248 0   99  1   244 0   100 1   7   255 244 0   88  1   244 0   93  1   244 0   93  
                                           1   248 0   94  1   248 0   94  1   11  1   94  1   11  1   94  1   15  1   93  1   15  1   93  1   15  1   88  1   15  1   88  1   11  1   87  1   11  1   87  1   248 0   87  1   248 0   87  1   244 0   88  1   7   255 244 0   138 1   244 0   142 1   244 
                                           0   142 1   248 0   143 1   248 0   143 1   11  1   143 1   11  1   143 1   15  1   142 1   15  1   142 1   15  1   138 1   15  1   138 1   11  1   137 1   11  1   137 1   248 0   137 1   248 0   137 1   244 0   138 1   7   255 244 0   150 1   244 0   154 
                                           1   244 0   154 1   248 0   155 1   248 0   155 1   11  1   155 1   11  1   155 1   15  1   154 1   15  1   154 1   15  1   150 1   15  1   150 1   11  1   149 1   11  1   149 1   248 0   149 1   248 0   149 1   244 0   150 1   7   255 50  0   155 1   50  
                                           0   157 1   50  0   157 1   48  0   158 1   48  0   158 1   46  0   157 1   46  0   157 1   45  0   155 1   45  0   155 1   46  0   153 1   46  0   153 1   48  0   153 1   48  0   153 1   50  0   153 1   50  0   153 1   50  0   155 1   7   255 43  0   155 
                                           1   53  0   155 1   7   255 48  0   150 1   48  0   161 1   7   255 50  0   87  1   50  0   89  1   50  0   89  1   48  0   90  1   48  0   90  1   46  0   89  1   46  0   89  1   45  0   87  1   45  0   87  1   46  0   85  1   46  0   85  1   48  0   85  
                                           1   48  0   85  1   50  0   85  1   50  0   85  1   50  0   87  1   7   255 43  0   87  1   53  0   87  1   7   255 48  0   82  1   48  0   92  1   7   255 26  0   161 1   26  0   163 1   26  0   163 1   24  0   164 1   24  0   164 1   22  0   163 1   22  
                                           0   163 1   21  0   161 1   21  0   161 1   22  0   159 1   22  0   159 1   24  0   159 1   24  0   159 1   26  0   159 1   26  0   159 1   26  0   161 1   7   255 18  0   161 1   29  0   161 1   7   255 24  0   156 1   24  0   167 1   7   255 26  0   81  
                                           1   26  0   83  1   26  0   83  1   24  0   84  1   24  0   84  1   22  0   83  1   22  0   83  1   21  0   81  1   21  0   81  1   22  0   79  1   22  0   79  1   24  0   79  1   24  0   79  1   26  0   79  1   26  0   79  1   26  0   81  1   7   255 18  
                                           0   81  1   29  0   81  1   7   255 24  0   76  1   24  0   86  1   7   255 227 0   87  1   226 0   89  1   226 0   89  1   224 0   90  1   224 0   90  1   222 0   89  1   222 0   89  1   222 0   87  1   222 0   87  1   222 0   85  1   222 0   85  1   224 
                                           0   85  1   224 0   85  1   226 0   85  1   226 0   85  1   227 0   87  1   7   255 219 0   87  1   230 0   87  1   7   255 224 0   82  1   224 0   92  1   7   255 227 0   155 1   226 0   157 1   226 0   157 1   224 0   158 1   224 0   158 1   222 0   157 
                                           1   222 0   157 1   222 0   155 1   222 0   155 1   222 0   153 1   222 0   153 1   224 0   153 1   224 0   153 1   226 0   153 1   226 0   153 1   227 0   155 1   7   255 219 0   155 1   230 0   155 1   7   255 224 0   150 1   224 0   161 1   1   255 1   
                                           255 227 0   121 1   226 0   123 1   226 0   123 1   224 0   124 1   224 0   124 1   222 0   123 1   222 0   123 1   222 0   121 1   222 0   121 1   222 0   119 1   222 0   119 1   224 0   119 1   224 0   119 1   226 0   119 1   226 0   119 1   227 0   121 
                                           1   1   255 219 0   121 1   230 0   121 1   1   255 224 0   116 1   224 0   126 1   3   255 3   255 50  0   121 1   50  0   123 1   50  0   123 1   48  0   124 1   48  0   124 1   46  0   123 1   46  0   123 1   45  0   121 1   45  0   121 1   46  0   119 
                                           1   46  0   119 1   48  0   119 1   48  0   119 1   50  0   119 1   50  0   119 1   50  0   121 1   3   255 43  0   121 1   53  0   121 1   3   255 48  0   116 1   48  0   126 1   7   255 7   255 73  0   125 1   74  0   126 1   74  0   126 1   76  0   128 
                                           1   76  0   128 1   76  0   115 1   7   255 34  0   150 1   34  0   154 1   34  0   154 1   38  0   155 1   38  0   155 1   57  0   155 1   57  0   155 1   61  0   154 1   61  0   154 1   61  0   150 1   61  0   150 1   57  0   149 1   57  0   149 1   38  
                                           0   149 1   38  0   149 1   34  0   150 1   7   255 34  0   88  1   34  0   93  1   34  0   93  1   38  0   94  1   38  0   94  1   57  0   94  1   57  0   94  1   61  0   93  1   61  0   93  1   61  0   88  1   61  0   88  1   57  0   87  1   57  0   87  
                                           1   38  0   87  1   38  0   87  1   34  0   88  1   7   255 176 0   113 1   193 1   113 1   193 1   113 1   193 1   108 1   193 1   108 1   210 1   108 1   210 1   108 1   210 1   135 1   210 1   135 1   193 1   135 1   193 1   135 1   193 1   129 1   193 
                                           1   129 1   176 0   129 1   176 0   129 1   176 0   113 1   7   255 176 0   113 1   176 0   113 1   7   255 176 0   113 1   176 0   113 1   7   255 227 0   121 1   226 0   123 1   226 0   123 1   224 0   124 1   224 0   124 1   222 0   123 1   222 0   123 
                                           1   222 0   121 1   222 0   121 1   222 0   119 1   222 0   119 1   224 0   119 1   224 0   119 1   226 0   119 1   226 0   119 1   227 0   121 1   7   255 87  1   128 1   84  1   130 1   84  1   130 1   81  1   130 1   81  1   130 1   77  1   130 1   77  
                                           1   130 1   74  1   128 1   74  1   128 1   72  1   125 1   72  1   125 1   71  1   121 1   71  1   121 1   72  1   118 1   72  1   118 1   74  1   115 1   74  1   115 1   77  1   113 1   77  1   113 1   81  1   112 1   81  1   112 1   84  1   113 1   84  
                                           1   113 1   87  1   115 1   7   255 87  1   115 1   87  1   128 1   7   255 130 1   102 1   130 1   107 1   130 1   107 1   134 1   108 1   134 1   108 1   153 1   108 1   153 1   108 1   157 1   107 1   157 1   107 1   157 1   102 1   157 1   102 1   153 
                                           1   101 1   153 1   101 1   134 1   101 1   134 1   101 1   130 1   102 1   7   255 130 1   90  1   130 1   95  1   130 1   95  1   134 1   96  1   134 1   96  1   153 1   96  1   153 1   96  1   157 1   95  1   157 1   95  1   157 1   90  1   157 1   90  
                                           1   153 1   89  1   153 1   89  1   134 1   89  1   134 1   89  1   130 1   90  1   7   255 130 1   136 1   130 1   140 1   130 1   140 1   134 1   141 1   134 1   141 1   153 1   141 1   153 1   141 1   157 1   140 1   157 1   140 1   157 1   136 1   157 
                                           1   136 1   153 1   135 1   153 1   135 1   134 1   135 1   134 1   135 1   130 1   136 1   7   255 130 1   148 1   130 1   152 1   130 1   152 1   134 1   153 1   134 1   153 1   153 1   153 1   153 1   153 1   157 1   152 1   157 1   152 1   157 1   148 
                                           1   157 1   148 1   153 1   147 1   153 1   147 1   134 1   147 1   134 1   147 1   130 1   148 1   7   255 163 1   102 1   163 1   107 1   163 1   107 1   167 1   108 1   167 1   108 1   186 1   108 1   186 1   108 1   190 1   107 1   190 1   107 1   190 
                                           1   102 1   190 1   102 1   186 1   101 1   186 1   101 1   167 1   101 1   167 1   101 1   163 1   102 1   7   255 163 1   90  1   163 1   95  1   163 1   95  1   167 1   96  1   167 1   96  1   186 1   96  1   186 1   96  1   190 1   95  1   190 1   95  
                                           1   190 1   90  1   190 1   90  1   186 1   89  1   186 1   89  1   167 1   89  1   167 1   89  1   163 1   90  1   7   255 163 1   136 1   163 1   140 1   163 1   140 1   167 1   141 1   167 1   141 1   186 1   141 1   186 1   141 1   190 1   140 1   190 
                                           1   140 1   190 1   136 1   190 1   136 1   186 1   135 1   186 1   135 1   167 1   135 1   167 1   135 1   163 1   136 1   7   255 163 1   148 1   163 1   152 1   163 1   152 1   167 1   153 1   167 1   153 1   186 1   153 1   186 1   153 1   190 1   152 
                                           1   190 1   152 1   190 1   148 1   190 1   148 1   186 1   147 1   186 1   147 1   167 1   147 1   167 1   147 1   163 1   148 1   7   255 197 1   102 1   197 1   107 1   197 1   107 1   201 1   108 1   201 1   108 1   220 1   108 1   220 1   108 1   224 
                                           1   107 1   224 1   107 1   224 1   102 1   224 1   102 1   220 1   101 1   220 1   101 1   201 1   101 1   201 1   101 1   197 1   102 1   7   255 197 1   90  1   197 1   95  1   197 1   95  1   201 1   96  1   201 1   96  1   220 1   96  1   220 1   96  
                                           1   224 1   95  1   224 1   95  1   224 1   90  1   224 1   90  1   220 1   89  1   220 1   89  1   201 1   89  1   201 1   89  1   197 1   90  1   7   255 197 1   136 1   197 1   140 1   197 1   140 1   201 1   141 1   201 1   141 1   220 1   141 1   220 
                                           1   141 1   224 1   140 1   224 1   140 1   224 1   136 1   224 1   136 1   220 1   135 1   220 1   135 1   201 1   135 1   201 1   135 1   197 1   136 1   7   255 197 1   148 1   197 1   152 1   197 1   152 1   201 1   153 1   201 1   153 1   220 1   153 
                                           1   220 1   153 1   224 1   152 1   224 1   152 1   224 1   148 1   224 1   148 1   220 1   147 1   220 1   147 1   201 1   147 1   201 1   147 1   197 1   148 1   3   255 3   255 227 0   121 1   226 0   123 1   226 0   123 1   224 0   124 1   224 0   124 
                                           1   222 0   123 1   222 0   123 1   222 0   121 1   222 0   121 1   222 0   119 1   222 0   119 1   224 0   119 1   224 0   119 1   226 0   119 1   226 0   119 1   227 0   121 1   3   255 219 0   121 1   230 0   121 1   3   255 224 0   116 1   224 0   126 
                                           1   1   255 1   255 83  1   121 1   82  1   123 1   82  1   123 1   81  1   124 1   81  1   124 1   79  1   123 1   79  1   123 1   78  1   121 1   78  1   121 1   79  1   119 1   79  1   119 1   81  1   119 1   81  1   119 1   82  1   119 1   82  1   119 
                                           1   83  1   121 1   1   255 75  1   121 1   86  1   121 1   1   255 81  1   116 1   81  1   126 1   7   255 7   255 180 1   153 1   179 1   155 1   179 1   155 1   177 1   156 1   177 1   156 1   175 1   155 1   175 1   155 1   174 1   153 1   174 1   153 
                                           1   175 1   151 1   175 1   151 1   177 1   151 1   177 1   151 1   179 1   151 1   179 1   151 1   180 1   153 1   7   255 172 1   153 1   182 1   153 1   7   255 177 1   148 1   177 1   159 1   7   255 180 1   89  1   179 1   91  1   179 1   91  1   177 
                                           1   92  1   177 1   92  1   175 1   91  1   175 1   91  1   174 1   89  1   174 1   89  1   175 1   87  1   175 1   87  1   177 1   87  1   177 1   87  1   179 1   87  1   179 1   87  1   180 1   89  1   7   255 172 1   89  1   182 1   89  1   7   255 177 
                                           1   84  1   177 1   94  1   7   255 247 0   125 1   247 0   127 1   247 0   127 1   248 0   127 1   248 0   127 1   249 0   128 1   249 0   128 1   252 0   128 1   252 0   128 1   253 0   127 1   253 0   127 1   254 0   127 1   254 0   127 1   254 0   125 
                                           1   254 0   125 1   254 0   124 1   254 0   124 1   254 0   123 1   254 0   123 1   252 0   121 1   252 0   121 1   246 0   115 1   246 0   115 1   255 0   115 1   7   255 32  1   113 1   178 2   113 1   178 2   113 1   178 2   108 1   178 2   108 1   195 
                                           2   108 1   195 2   108 1   195 2   135 1   195 2   135 1   178 2   135 1   178 2   135 1   178 2   129 1   178 2   129 1   32  1   129 1   32  1   129 1   32  1   113 1   7   255 32  1   113 1   32  1   113 1   7   255 32  1   113 1   32  1   113 1   7   
                                           255 83  1   121 1   82  1   123 1   82  1   123 1   81  1   124 1   81  1   124 1   79  1   123 1   79  1   123 1   78  1   121 1   78  1   121 1   79  1   119 1   79  1   119 1   81  1   119 1   81  1   119 1   82  1   119 1   82  1   119 1   83  1   121 
                                           1   7   255 183 1   128 1   180 1   130 1   180 1   130 1   177 1   130 1   177 1   130 1   173 1   130 1   173 1   130 1   170 1   128 1   170 1   128 1   168 1   125 1   168 1   125 1   168 1   121 1   168 1   121 1   168 1   118 1   168 1   118 1   170 
                                           1   115 1   170 1   115 1   173 1   113 1   173 1   113 1   177 1   112 1   177 1   112 1   180 1   113 1   180 1   113 1   183 1   115 1   7   255 183 1   115 1   183 1   128 1   7   255 115 2   102 1   115 2   107 1   115 2   107 1   118 2   108 1   118 
                                           2   108 1   138 2   108 1   138 2   108 1   141 2   107 1   141 2   107 1   141 2   102 1   141 2   102 1   138 2   101 1   138 2   101 1   118 2   101 1   118 2   101 1   115 2   102 1   7   255 115 2   90  1   115 2   95  1   115 2   95  1   118 2   96  
                                           1   118 2   96  1   138 2   96  1   138 2   96  1   141 2   95  1   141 2   95  1   141 2   90  1   141 2   90  1   138 2   89  1   138 2   89  1   118 2   89  1   118 2   89  1   115 2   90  1   7   255 115 2   136 1   115 2   140 1   115 2   140 1   118 
                                           2   141 1   118 2   141 1   138 2   141 1   138 2   141 1   141 2   140 1   141 2   140 1   141 2   136 1   141 2   136 1   138 2   135 1   138 2   135 1   118 2   135 1   118 2   135 1   115 2   136 1   7   255 115 2   148 1   115 2   152 1   115 2   152 
                                           1   118 2   153 1   118 2   153 1   138 2   153 1   138 2   153 1   141 2   152 1   141 2   152 1   141 2   148 1   141 2   148 1   138 2   147 1   138 2   147 1   118 2   147 1   118 2   147 1   115 2   148 1   7   255 148 2   102 1   148 2   107 1   148 
                                           2   107 1   152 2   108 1   152 2   108 1   171 2   108 1   171 2   108 1   175 2   107 1   175 2   107 1   175 2   102 1   175 2   102 1   171 2   101 1   171 2   101 1   152 2   101 1   152 2   101 1   148 2   102 1   7   255 148 2   90  1   148 2   95  
                                           1   148 2   95  1   152 2   96  1   152 2   96  1   171 2   96  1   171 2   96  1   175 2   95  1   175 2   95  1   175 2   90  1   175 2   90  1   171 2   89  1   171 2   89  1   152 2   89  1   152 2   89  1   148 2   90  1   7   255 148 2   136 1   148 
                                           2   140 1   148 2   140 1   152 2   141 1   152 2   141 1   171 2   141 1   171 2   141 1   175 2   140 1   175 2   140 1   175 2   136 1   175 2   136 1   171 2   135 1   171 2   135 1   152 2   135 1   152 2   135 1   148 2   136 1   7   255 148 2   148 
                                           1   148 2   152 1   148 2   152 1   152 2   153 1   152 2   153 1   171 2   153 1   171 2   153 1   175 2   152 1   175 2   152 1   175 2   148 1   175 2   148 1   171 2   147 1   171 2   147 1   152 2   147 1   152 2   147 1   148 2   148 1   7   255 182 
                                           2   102 1   182 2   107 1   182 2   107 1   185 2   108 1   185 2   108 1   205 2   108 1   205 2   108 1   208 2   107 1   208 2   107 1   208 2   102 1   208 2   102 1   205 2   101 1   205 2   101 1   185 2   101 1   185 2   101 1   182 2   102 1   7   
                                           255 182 2   90  1   182 2   95  1   182 2   95  1   185 2   96  1   185 2   96  1   205 2   96  1   205 2   96  1   208 2   95  1   208 2   95  1   208 2   90  1   208 2   90  1   205 2   89  1   205 2   89  1   185 2   89  1   185 2   89  1   182 2   90  
                                           )) "a")
 (_WriteStream FILE (vl-list->string (list 1   7   255 182 2   136 1   182 2   140 1   182 2   140 1   185 2   141 1   185 2   141 1   205 2   141 1   205 2   141 1   208 2   140 1   208 2   140 1   208 2   136 1   208 2   136 1   205 2   135 1   205 2   135 1   185 2   135 1   185 2   135 1   182 
                                           2   136 1   7   255 182 2   148 1   182 2   152 1   182 2   152 1   185 2   153 1   185 2   153 1   205 2   153 1   205 2   153 1   208 2   152 1   208 2   152 1   208 2   148 1   208 2   148 1   205 2   147 1   205 2   147 1   185 2   147 1   185 2   147 
                                           1   182 2   148 1   3   255 3   255 83  1   121 1   82  1   123 1   82  1   123 1   81  1   124 1   81  1   124 1   79  1   123 1   79  1   123 1   78  1   121 1   78  1   121 1   79  1   119 1   79  1   119 1   81  1   119 1   81  1   119 1   82  1   119 
                                           1   82  1   119 1   83  1   121 1   3   255 75  1   121 1   86  1   121 1   3   255 81  1   116 1   81  1   126 1   1   255 1   255 180 1   121 1   179 1   123 1   179 1   123 1   177 1   124 1   177 1   124 1   175 1   123 1   175 1   123 1   174 1   121 
                                           1   174 1   121 1   175 1   119 1   175 1   119 1   177 1   119 1   177 1   119 1   179 1   119 1   179 1   119 1   180 1   121 1   1   255 172 1   121 1   182 1   121 1   1   255 177 1   116 1   177 1   126 1   7   255 7   255 164 2   153 1   163 2   155 
                                           1   163 2   155 1   162 2   156 1   162 2   156 1   160 2   155 1   160 2   155 1   159 2   153 1   159 2   153 1   160 2   151 1   160 2   151 1   162 2   151 1   162 2   151 1   163 2   151 1   163 2   151 1   164 2   153 1   7   255 156 2   153 1   167 
                                           2   153 1   7   255 162 2   148 1   162 2   159 1   7   255 164 2   89  1   163 2   91  1   163 2   91  1   162 2   92  1   162 2   92  1   160 2   91  1   160 2   91  1   159 2   89  1   159 2   89  1   160 2   87  1   160 2   87  1   162 2   87  1   162 
                                           2   87  1   163 2   87  1   163 2   87  1   164 2   89  1   7   255 156 2   89  1   167 2   89  1   7   255 162 2   84  1   162 2   94  1   7   255 104 1   128 1   111 1   128 1   111 1   128 1   107 1   123 1   107 1   123 1   109 1   123 1   109 1   123 
                                           1   110 1   122 1   110 1   122 1   111 1   122 1   111 1   122 1   111 1   120 1   111 1   120 1   111 1   118 1   111 1   118 1   111 1   117 1   111 1   117 1   109 1   115 1   109 1   115 1   108 1   115 1   108 1   115 1   106 1   115 1   106 1   115 
                                           1   104 1   115 1   104 1   115 1   103 1   116 1   103 1   116 1   103 1   117 1   7   255 177 1   73  1   99  5   73  1   99  5   73  1   99  5   169 1   99  5   169 1   177 1   169 1   177 1   169 1   177 1   73  1   7   255 177 1   73  1   177 1   73  
                                           1   7   255 177 1   73  1   177 1   73  1   7   255 149 3   121 1   148 3   123 1   148 3   123 1   146 3   124 1   146 3   124 1   144 3   123 1   144 3   123 1   144 3   121 1   144 3   121 1   144 3   119 1   144 3   119 1   146 3   119 1   146 3   119 
                                           1   148 3   119 1   148 3   119 1   149 3   121 1   7   255 141 3   121 1   151 3   121 1   7   255 146 3   116 1   146 3   126 1   7   255 180 1   73  1   179 1   75  1   179 1   75  1   177 1   76  1   177 1   76  1   175 1   75  1   175 1   75  1   174 
                                           1   73  1   174 1   73  1   175 1   71  1   175 1   71  1   177 1   71  1   177 1   71  1   179 1   71  1   179 1   71  1   180 1   73  1   7   255 172 1   73  1   182 1   73  1   7   255 177 1   68  1   177 1   78  1   7   255 102 5   73  1   101 5   75  
                                           1   101 5   75  1   99  5   76  1   99  5   76  1   98  5   75  1   98  5   75  1   97  5   73  1   97  5   73  1   98  5   71  1   98  5   71  1   99  5   71  1   99  5   71  1   101 5   71  1   101 5   71  1   102 5   73  1   7   255 94  5   73  1   105 
                                           5   73  1   7   255 99  5   68  1   99  5   78  1   7   255 102 5   169 1   101 5   171 1   101 5   171 1   99  5   172 1   99  5   172 1   98  5   171 1   98  5   171 1   97  5   169 1   97  5   169 1   98  5   167 1   98  5   167 1   99  5   167 1   99  
                                           5   167 1   101 5   167 1   101 5   167 1   102 5   169 1   7   255 94  5   169 1   105 5   169 1   7   255 99  5   164 1   99  5   175 1   7   255 180 1   169 1   179 1   171 1   179 1   171 1   177 1   172 1   177 1   172 1   175 1   171 1   175 1   171 
                                           1   174 1   169 1   174 1   169 1   175 1   167 1   175 1   167 1   177 1   167 1   177 1   167 1   179 1   167 1   179 1   167 1   180 1   169 1   7   255 172 1   169 1   182 1   169 1   7   255 177 1   164 1   177 1   175 1   3   255 3   255 180 1   121 
                                           1   179 1   123 1   179 1   123 1   177 1   124 1   177 1   124 1   175 1   123 1   175 1   123 1   174 1   121 1   174 1   121 1   175 1   119 1   175 1   119 1   177 1   119 1   177 1   119 1   179 1   119 1   179 1   119 1   180 1   121 1   3   255 172 
                                           1   121 1   182 1   121 1   3   255 177 1   116 1   177 1   126 1   1   255 1   255 102 5   121 1   101 5   123 1   101 5   123 1   99  5   124 1   99  5   124 1   98  5   123 1   98  5   123 1   97  5   121 1   97  5   121 1   98  5   119 1   98  5   119 
                                           1   99  5   119 1   99  5   119 1   101 5   119 1   101 5   119 1   102 5   121 1   1   255 94  5   121 1   105 5   121 1   1   255 99  5   116 1   99  5   126 1   7   255 7   255 205 1   128 1   198 1   119 1   198 1   119 1   208 1   119 1   7   255 205 
                                           1   128 1   205 1   115 1   7   255 91  4   113 1   140 5   113 1   140 5   113 1   140 5   129 1   140 5   129 1   91  4   129 1   91  4   129 1   91  4   113 1   7   255 91  4   113 1   91  4   113 1   7   255 91  4   113 1   91  4   113 1   7   255 255 
                                           4   121 1   255 4   123 1   255 4   123 1   253 4   125 1   253 4   125 1   251 4   126 1   251 4   126 1   249 4   125 1   249 4   125 1   247 4   123 1   247 4   123 1   247 4   121 1   247 4   121 1   247 4   119 1   247 4   119 1   249 4   118 1   249 
                                           4   118 1   251 4   117 1   251 4   117 1   253 4   118 1   253 4   118 1   255 4   119 1   255 4   119 1   255 4   121 1   7   255 53  5   102 1   53  5   107 1   53  5   107 1   56  5   108 1   56  5   108 1   76  5   108 1   76  5   108 1   79  5   107 
                                           1   79  5   107 1   79  5   102 1   79  5   102 1   76  5   101 1   76  5   101 1   56  5   101 1   56  5   101 1   53  5   102 1   7   255 53  5   90  1   53  5   95  1   53  5   95  1   56  5   96  1   56  5   96  1   76  5   96  1   76  5   96  1   79  
                                           5   95  1   79  5   95  1   79  5   90  1   79  5   90  1   76  5   89  1   76  5   89  1   56  5   89  1   56  5   89  1   53  5   90  1   7   255 53  5   136 1   53  5   140 1   53  5   140 1   56  5   141 1   56  5   141 1   76  5   141 1   76  5   141 
                                           1   79  5   140 1   79  5   140 1   79  5   136 1   79  5   136 1   76  5   135 1   76  5   135 1   56  5   135 1   56  5   135 1   53  5   136 1   7   255 53  5   148 1   53  5   152 1   53  5   152 1   56  5   153 1   56  5   153 1   76  5   153 1   76  
                                           5   153 1   79  5   152 1   79  5   152 1   79  5   148 1   79  5   148 1   76  5   147 1   76  5   147 1   56  5   147 1   56  5   147 1   53  5   148 1   7   255 86  5   102 1   86  5   107 1   86  5   107 1   90  5   108 1   90  5   108 1   109 5   108 
                                           1   109 5   108 1   113 5   107 1   113 5   107 1   113 5   102 1   113 5   102 1   109 5   101 1   109 5   101 1   90  5   101 1   90  5   101 1   86  5   102 1   7   255 86  5   90  1   86  5   95  1   86  5   95  1   90  5   96  1   90  5   96  1   109 
                                           5   96  1   109 5   96  1   113 5   95  1   113 5   95  1   113 5   90  1   113 5   90  1   109 5   89  1   109 5   89  1   90  5   89  1   90  5   89  1   86  5   90  1   7   255 86  5   136 1   86  5   140 1   86  5   140 1   90  5   141 1   90  5   141 
                                           1   109 5   141 1   109 5   141 1   113 5   140 1   113 5   140 1   113 5   136 1   113 5   136 1   109 5   135 1   109 5   135 1   90  5   135 1   90  5   135 1   86  5   136 1   7   255 86  5   148 1   86  5   152 1   86  5   152 1   90  5   153 1   90  
                                           5   153 1   109 5   153 1   109 5   153 1   113 5   152 1   113 5   152 1   113 5   148 1   113 5   148 1   109 5   147 1   109 5   147 1   90  5   147 1   90  5   147 1   86  5   148 1   7   255 120 5   102 1   120 5   107 1   120 5   107 1   123 5   108 
                                           1   123 5   108 1   143 5   108 1   143 5   108 1   146 5   107 1   146 5   107 1   146 5   102 1   146 5   102 1   143 5   101 1   143 5   101 1   123 5   101 1   123 5   101 1   120 5   102 1   7   255 120 5   90  1   120 5   95  1   120 5   95  1   123 
                                           5   96  1   123 5   96  1   143 5   96  1   143 5   96  1   146 5   95  1   146 5   95  1   146 5   90  1   146 5   90  1   143 5   89  1   143 5   89  1   123 5   89  1   123 5   89  1   120 5   90  1   7   255 120 5   136 1   120 5   140 1   120 5   140 
                                           1   123 5   141 1   123 5   141 1   143 5   141 1   143 5   141 1   146 5   140 1   146 5   140 1   146 5   136 1   146 5   136 1   143 5   135 1   143 5   135 1   123 5   135 1   123 5   135 1   120 5   136 1   7   255 120 5   148 1   120 5   152 1   120 
                                           5   152 1   123 5   153 1   123 5   153 1   143 5   153 1   143 5   153 1   146 5   152 1   146 5   152 1   146 5   148 1   146 5   148 1   143 5   147 1   143 5   147 1   123 5   147 1   123 5   147 1   120 5   148 1   7   255 133 4   153 1   133 4   155 
                                           1   133 4   155 1   131 4   156 1   131 4   156 1   129 4   155 1   129 4   155 1   128 4   153 1   128 4   153 1   129 4   151 1   129 4   151 1   131 4   151 1   131 4   151 1   133 4   151 1   133 4   151 1   133 4   153 1   7   255 126 4   153 1   136 
                                           4   153 1   7   255 131 4   148 1   131 4   159 1   7   255 133 4   89  1   133 4   91  1   133 4   91  1   131 4   92  1   131 4   92  1   129 4   91  1   129 4   91  1   128 4   89  1   128 4   89  1   129 4   87  1   129 4   87  1   131 4   87  1   131 
                                           4   87  1   133 4   87  1   133 4   87  1   133 4   89  1   7   255 126 4   89  1   136 4   89  1   7   255 131 4   84  1   131 4   94  1   7   255 102 5   89  1   101 5   91  1   101 5   91  1   99  5   92  1   99  5   92  1   98  5   91  1   98  5   91  
                                           1   97  5   89  1   97  5   89  1   98  5   87  1   98  5   87  1   99  5   87  1   99  5   87  1   101 5   87  1   101 5   87  1   102 5   89  1   7   255 94  5   89  1   105 5   89  1   7   255 99  5   84  1   99  5   94  1   7   255 102 5   153 1   101 
                                           5   155 1   101 5   155 1   99  5   156 1   99  5   156 1   98  5   155 1   98  5   155 1   97  5   153 1   97  5   153 1   98  5   151 1   98  5   151 1   99  5   151 1   99  5   151 1   101 5   151 1   101 5   151 1   102 5   153 1   7   255 94  5   153 
                                           1   105 5   153 1   7   255 99  5   148 1   99  5   159 1   3   255 3   255 254 4   121 1   253 4   123 1   253 4   123 1   251 4   124 1   251 4   124 1   249 4   123 1   249 4   123 1   249 4   121 1   249 4   121 1   249 4   119 1   249 4   119 1   251 
                                           4   119 1   251 4   119 1   253 4   119 1   253 4   119 1   254 4   121 1   3   255 246 4   121 1   0   5   121 1   3   255 251 4   116 1   251 4   126 1   7   255 7   255 25  5   126 1   24  5   127 1   24  5   127 1   22  5   128 1   22  5   128 1   21  
                                           5   128 1   21  5   128 1   19  5   127 1   19  5   127 1   18  5   125 1   18  5   125 1   17  5   122 1   17  5   122 1   17  5   119 1   17  5   119 1   18  5   117 1   18  5   117 1   19  5   115 1   19  5   115 1   21  5   115 1   21  5   115 1   22  
                                           5   115 1   22  5   115 1   24  5   115 1   24  5   115 1   25  5   117 1   25  5   117 1   26  5   118 1   26  5   118 1   26  5   119 1   26  5   119 1   25  5   121 1   25  5   121 1   24  5   122 1   24  5   122 1   22  5   123 1   22  5   123 1   21  
                                           5   123 1   21  5   123 1   19  5   122 1   19  5   122 1   18  5   121 1   18  5   121 1   17  5   119 1   7   255 84  4   102 1   84  4   107 1   84  4   107 1   88  4   108 1   88  4   108 1   107 4   108 1   107 4   108 1   111 4   107 1   111 4   107 
                                           1   111 4   102 1   111 4   102 1   107 4   101 1   107 4   101 1   88  4   101 1   88  4   101 1   84  4   102 1   7   255 84  4   90  1   84  4   95  1   84  4   95  1   88  4   96  1   88  4   96  1   107 4   96  1   107 4   96  1   111 4   95  1   111 
                                           4   95  1   111 4   90  1   111 4   90  1   107 4   89  1   107 4   89  1   88  4   89  1   88  4   89  1   84  4   90  1   7   255 117 4   102 1   117 4   107 1   117 4   107 1   121 4   108 1   121 4   108 1   140 4   108 1   140 4   108 1   144 4   107 
                                           1   144 4   107 1   144 4   102 1   144 4   102 1   140 4   101 1   140 4   101 1   121 4   101 1   121 4   101 1   117 4   102 1   7   255 117 4   90  1   117 4   95  1   117 4   95  1   121 4   96  1   121 4   96  1   140 4   96  1   140 4   96  1   144 
                                           4   95  1   144 4   95  1   144 4   90  1   144 4   90  1   140 4   89  1   140 4   89  1   121 4   89  1   121 4   89  1   117 4   90  1   7   255 151 4   102 1   151 4   107 1   151 4   107 1   155 4   108 1   155 4   108 1   174 4   108 1   174 4   108 
                                           1   178 4   107 1   178 4   107 1   178 4   102 1   178 4   102 1   174 4   101 1   174 4   101 1   155 4   101 1   155 4   101 1   151 4   102 1   7   255 151 4   90  1   151 4   95  1   151 4   95  1   155 4   96  1   155 4   96  1   174 4   96  1   174 
                                           4   96  1   178 4   95  1   178 4   95  1   178 4   90  1   178 4   90  1   174 4   89  1   174 4   89  1   155 4   89  1   155 4   89  1   151 4   90  1   7   255 84  4   136 1   84  4   140 1   84  4   140 1   88  4   141 1   88  4   141 1   107 4   141 
                                           1   107 4   141 1   111 4   140 1   111 4   140 1   111 4   136 1   111 4   136 1   107 4   135 1   107 4   135 1   88  4   135 1   88  4   135 1   84  4   136 1   7   255 84  4   148 1   84  4   152 1   84  4   152 1   88  4   153 1   88  4   153 1   107 
                                           4   153 1   107 4   153 1   111 4   152 1   111 4   152 1   111 4   148 1   111 4   148 1   107 4   147 1   107 4   147 1   88  4   147 1   88  4   147 1   84  4   148 1   7   255 117 4   136 1   117 4   140 1   117 4   140 1   121 4   141 1   121 4   141 
                                           1   140 4   141 1   140 4   141 1   144 4   140 1   144 4   140 1   144 4   136 1   144 4   136 1   140 4   135 1   140 4   135 1   121 4   135 1   121 4   135 1   117 4   136 1   7   255 117 4   148 1   117 4   152 1   117 4   152 1   121 4   153 1   121 
                                           4   153 1   140 4   153 1   140 4   153 1   144 4   152 1   144 4   152 1   144 4   148 1   144 4   148 1   140 4   147 1   140 4   147 1   121 4   147 1   121 4   147 1   117 4   148 1   7   255 151 4   136 1   151 4   140 1   151 4   140 1   155 4   141 
                                           1   155 4   141 1   174 4   141 1   174 4   141 1   178 4   140 1   178 4   140 1   178 4   136 1   178 4   136 1   174 4   135 1   174 4   135 1   155 4   135 1   155 4   135 1   151 4   136 1   7   255 151 4   148 1   151 4   152 1   151 4   152 1   155 
                                           4   153 1   155 4   153 1   174 4   153 1   174 4   153 1   178 4   152 1   178 4   152 1   178 4   148 1   178 4   148 1   174 4   147 1   174 4   147 1   155 4   147 1   155 4   147 1   151 4   148 1   7   255 251 4   113 1   84  6   113 1   84  6   113 
                                           1   84  6   129 1   84  6   129 1   251 4   129 1   251 4   129 1   251 4   113 1   7   255 251 4   113 1   251 4   113 1   7   255 251 4   113 1   251 4   113 1   7   255 104 5   121 1   103 5   123 1   103 5   123 1   102 5   125 1   102 5   125 1   99  
                                           5   126 1   99  5   126 1   97  5   125 1   97  5   125 1   96  5   123 1   96  5   123 1   95  5   121 1   95  5   121 1   96  5   119 1   96  5   119 1   97  5   118 1   97  5   118 1   99  5   117 1   99  5   117 1   102 5   118 1   102 5   118 1   103 
                                           5   119 1   103 5   119 1   104 5   121 1   7   255 253 5   102 1   253 5   107 1   253 5   107 1   1   6   108 1   1   6   108 1   20  6   108 1   20  6   108 1   24  6   107 1   24  6   107 1   24  6   102 1   24  6   102 1   20  6   101 1   20  6   101 
                                           1   1   6   101 1   1   6   101 1   253 5   102 1   7   255 253 5   90  1   253 5   95  1   253 5   95  1   1   6   96  1   1   6   96  1   20  6   96  1   20  6   96  1   24  6   95  1   24  6   95  1   24  6   90  1   24  6   90  1   20  6   89  1   20  
                                           6   89  1   1   6   89  1   1   6   89  1   253 5   90  1   7   255 253 5   136 1   253 5   140 1   253 5   140 1   1   6   141 1   1   6   141 1   20  6   141 1   20  6   141 1   24  6   140 1   24  6   140 1   24  6   136 1   24  6   136 1   20  6   135 
                                           1   20  6   135 1   1   6   135 1   1   6   135 1   253 5   136 1   7   255 253 5   148 1   253 5   152 1   253 5   152 1   1   6   153 1   1   6   153 1   20  6   153 1   20  6   153 1   24  6   152 1   24  6   152 1   24  6   148 1   24  6   148 1   20  
                                           6   147 1   20  6   147 1   1   6   147 1   1   6   147 1   253 5   148 1   7   255 31  6   102 1   31  6   107 1   31  6   107 1   34  6   108 1   34  6   108 1   54  6   108 1   54  6   108 1   57  6   107 1   57  6   107 1   57  6   102 1   57  6   102 
                                           )) "a")
 (_WriteStream FILE (vl-list->string (list 1   54  6   101 1   54  6   101 1   34  6   101 1   34  6   101 1   31  6   102 1   7   255 31  6   90  1   31  6   95  1   31  6   95  1   34  6   96  1   34  6   96  1   54  6   96  1   54  6   96  1   57  6   95  1   57  6   95  1   57  6   90  1   57  
                                           6   90  1   54  6   89  1   54  6   89  1   34  6   89  1   34  6   89  1   31  6   90  1   7   255 31  6   136 1   31  6   140 1   31  6   140 1   34  6   141 1   34  6   141 1   54  6   141 1   54  6   141 1   57  6   140 1   57  6   140 1   57  6   136 
                                           1   57  6   136 1   54  6   135 1   54  6   135 1   34  6   135 1   34  6   135 1   31  6   136 1   7   255 31  6   148 1   31  6   152 1   31  6   152 1   34  6   153 1   34  6   153 1   54  6   153 1   54  6   153 1   57  6   152 1   57  6   152 1   57  
                                           6   148 1   57  6   148 1   54  6   147 1   54  6   147 1   34  6   147 1   34  6   147 1   31  6   148 1   7   255 64  6   102 1   64  6   107 1   64  6   107 1   68  6   108 1   68  6   108 1   87  6   108 1   87  6   108 1   91  6   107 1   91  6   107 
                                           1   91  6   102 1   91  6   102 1   87  6   101 1   87  6   101 1   68  6   101 1   68  6   101 1   64  6   102 1   7   255 64  6   90  1   64  6   95  1   64  6   95  1   68  6   96  1   68  6   96  1   87  6   96  1   87  6   96  1   91  6   95  1   91  
                                           6   95  1   91  6   90  1   91  6   90  1   87  6   89  1   87  6   89  1   68  6   89  1   68  6   89  1   64  6   90  1   7   255 64  6   136 1   64  6   140 1   64  6   140 1   68  6   141 1   68  6   141 1   87  6   141 1   87  6   141 1   91  6   140 
                                           1   91  6   140 1   91  6   136 1   91  6   136 1   87  6   135 1   87  6   135 1   68  6   135 1   68  6   135 1   64  6   136 1   7   255 64  6   148 1   64  6   152 1   64  6   152 1   68  6   153 1   68  6   153 1   87  6   153 1   87  6   153 1   91  
                                           6   152 1   91  6   152 1   91  6   148 1   91  6   148 1   87  6   147 1   87  6   147 1   68  6   147 1   68  6   147 1   64  6   148 1   3   255 3   255 102 5   121 1   101 5   123 1   101 5   123 1   99  5   124 1   99  5   124 1   98  5   123 1   98  
                                           5   123 1   97  5   121 1   97  5   121 1   98  5   119 1   98  5   119 1   99  5   119 1   99  5   119 1   101 5   119 1   101 5   119 1   102 5   121 1   3   255 94  5   121 1   105 5   121 1   3   255 99  5   116 1   99  5   126 1   7   255 7   255 47  
                                           6   153 1   46  6   155 1   46  6   155 1   44  6   156 1   44  6   156 1   42  6   155 1   42  6   155 1   41  6   153 1   41  6   153 1   42  6   151 1   42  6   151 1   44  6   151 1   44  6   151 1   46  6   151 1   46  6   151 1   47  6   153 1   7   
                                           255 39  6   153 1   49  6   153 1   7   255 44  6   148 1   44  6   159 1   7   255 47  6   89  1   46  6   91  1   46  6   91  1   44  6   92  1   44  6   92  1   42  6   91  1   42  6   91  1   41  6   89  1   41  6   89  1   42  6   87  1   42  6   87  
                                           1   44  6   87  1   44  6   87  1   46  6   87  1   46  6   87  1   47  6   89  1   7   255 39  6   89  1   49  6   89  1   7   255 44  6   84  1   44  6   94  1   1   255 1   255 254 4   121 1   253 4   123 1   253 4   123 1   251 4   124 1   251 4   124 
                                           1   249 4   123 1   249 4   123 1   249 4   121 1   249 4   121 1   249 4   119 1   249 4   119 1   251 4   119 1   251 4   119 1   253 4   119 1   253 4   119 1   254 4   121 1   1   255 246 4   121 1   0   5   121 1   1   255 251 4   116 1   251 4   126 
                                           1   7   255 7   255 129 5   128 1   123 5   128 1   123 5   128 1   122 5   122 1   122 5   122 1   123 5   123 1   123 5   123 1   125 5   123 1   125 5   123 1   126 5   123 1   126 5   123 1   128 5   123 1   128 5   123 1   130 5   122 1   130 5   122 
                                           1   130 5   120 1   130 5   120 1   130 5   118 1   130 5   118 1   130 5   117 1   130 5   117 1   128 5   115 1   128 5   115 1   126 5   115 1   126 5   115 1   125 5   115 1   125 5   115 1   123 5   115 1   123 5   115 1   122 5   116 1   122 5   116 
                                           1   121 5   117 1   0   252 65  117 116 111 67  65  68  32  83  108 105 100 101 13  10  26  0   86  2   73  6   247 2   97  120 67  1   2   0   52  18  7   255 7   255 114 4   58  1   41  6   58  1   41  6   58  1   41  6   192 1   41  6   192 1   114 4   
                                           192 1   114 4   192 1   114 4   58  1   7   255 114 4   58  1   114 4   58  1   7   255 114 4   58  1   114 4   58  1   7   255 114 4   58  1   114 4   58  1   7   255 163 5   87  1   163 5   96  1   163 5   96  1   171 5   99  1   171 5   99  1   213 5   
                                           99  1   213 5   99  1   221 5   96  1   221 5   96  1   221 5   87  1   221 5   87  1   213 5   84  1   213 5   84  1   171 5   84  1   171 5   84  1   163 5   87  1   7   255 163 5   61  1   163 5   70  1   163 5   70  1   171 5   73  1   171 5   73  1   
                                           213 5   73  1   213 5   73  1   221 5   70  1   221 5   70  1   221 5   61  1   221 5   61  1   213 5   58  1   213 5   58  1   171 5   58  1   171 5   58  1   163 5   61  1   7   255 163 5   155 1   163 5   164 1   163 5   164 1   171 5   167 1   171 5   
                                           167 1   213 5   167 1   213 5   167 1   221 5   164 1   221 5   164 1   221 5   155 1   221 5   155 1   213 5   152 1   213 5   152 1   171 5   152 1   171 5   152 1   163 5   155 1   7   255 163 5   181 1   163 5   190 1   163 5   190 1   171 5   192 1   
                                           171 5   192 1   213 5   192 1   213 5   192 1   221 5   190 1   221 5   190 1   221 5   181 1   221 5   181 1   213 5   178 1   213 5   178 1   171 5   178 1   171 5   178 1   163 5   181 1   7   255 229 5   87  1   229 5   96  1   229 5   96  1   237 5   
                                           99  1   237 5   99  1   22  6   99  1   22  6   99  1   30  6   96  1   30  6   96  1   30  6   87  1   30  6   87  1   22  6   84  1   22  6   84  1   237 5   84  1   237 5   84  1   229 5   87  1   7   255 229 5   61  1   229 5   70  1   229 5   70  1   
                                           237 5   73  1   237 5   73  1   22  6   73  1   22  6   73  1   30  6   70  1   30  6   70  1   30  6   61  1   30  6   61  1   22  6   58  1   22  6   58  1   237 5   58  1   237 5   58  1   229 5   61  1   7   255 229 5   155 1   229 5   164 1   229 5   
                                           164 1   237 5   167 1   237 5   167 1   22  6   167 1   22  6   167 1   30  6   164 1   30  6   164 1   30  6   155 1   30  6   155 1   22  6   152 1   22  6   152 1   237 5   152 1   237 5   152 1   229 5   155 1   7   255 229 5   181 1   229 5   190 1   
                                           229 5   190 1   237 5   192 1   237 5   192 1   22  6   192 1   22  6   192 1   30  6   190 1   30  6   190 1   30  6   181 1   30  6   181 1   22  6   178 1   22  6   178 1   237 5   178 1   237 5   178 1   229 5   181 1   7   255 150 4   125 1   149 4   
                                           128 1   149 4   128 1   147 4   130 1   147 4   130 1   145 4   131 1   145 4   131 1   142 4   130 1   142 4   130 1   140 4   128 1   140 4   128 1   140 4   125 1   140 4   125 1   140 4   123 1   140 4   123 1   142 4   121 1   142 4   121 1   145 4   
                                           120 1   145 4   120 1   147 4   121 1   147 4   121 1   149 4   123 1   149 4   123 1   150 4   125 1   7   255 134 4   125 1   155 4   125 1   7   255 145 4   115 1   145 4   136 1   7   255 119 4   58  1   118 4   61  1   118 4   61  1   116 4   63  1   
                                           116 4   63  1   114 4   63  1   114 4   63  1   111 4   63  1   111 4   63  1   109 4   61  1   109 4   61  1   109 4   58  1   109 4   58  1   109 4   56  1   109 4   56  1   111 4   54  1   111 4   54  1   114 4   53  1   114 4   53  1   116 4   54  1   
                                           116 4   54  1   118 4   56  1   118 4   56  1   119 4   58  1   7   255 103 4   58  1   124 4   58  1   7   255 114 4   48  1   114 4   69  1   7   255 119 4   192 1   118 4   195 1   118 4   195 1   116 4   197 1   116 4   197 1   114 4   198 1   114 4   
                                           198 1   111 4   197 1   111 4   197 1   109 4   195 1   109 4   195 1   109 4   192 1   109 4   192 1   109 4   190 1   109 4   190 1   111 4   188 1   111 4   188 1   114 4   187 1   114 4   187 1   116 4   188 1   116 4   188 1   118 4   190 1   118 4   
                                           190 1   119 4   192 1   7   255 103 4   192 1   124 4   192 1   7   255 114 4   182 1   114 4   203 1   7   255 46  6   192 1   45  6   195 1   45  6   195 1   44  6   197 1   44  6   197 1   41  6   198 1   41  6   198 1   38  6   197 1   38  6   197 1   
                                           37  6   195 1   37  6   195 1   36  6   192 1   36  6   192 1   37  6   190 1   37  6   190 1   38  6   188 1   38  6   188 1   41  6   187 1   41  6   187 1   44  6   188 1   44  6   188 1   45  6   190 1   45  6   190 1   46  6   192 1   7   255 31  6   
                                           192 1   51  6   192 1   7   255 41  6   182 1   41  6   203 1   7   255 46  6   58  1   45  6   61  1   45  6   61  1   44  6   63  1   44  6   63  1   41  6   63  1   41  6   63  1   38  6   63  1   38  6   63  1   37  6   61  1   37  6   61  1   36  6   
                                           58  1   36  6   58  1   37  6   56  1   37  6   56  1   38  6   54  1   38  6   54  1   41  6   53  1   41  6   53  1   44  6   54  1   44  6   54  1   45  6   56  1   45  6   56  1   46  6   58  1   7   255 31  6   58  1   51  6   58  1   7   255 41  6   
                                           48  1   41  6   69  1   7   255 230 5   192 1   229 5   195 1   229 5   195 1   227 5   197 1   227 5   197 1   225 5   198 1   225 5   198 1   222 5   197 1   222 5   197 1   220 5   195 1   220 5   195 1   219 5   192 1   219 5   192 1   220 5   190 1   
                                           220 5   190 1   222 5   188 1   222 5   188 1   225 5   187 1   225 5   187 1   227 5   188 1   227 5   188 1   229 5   190 1   229 5   190 1   230 5   192 1   7   255 214 5   192 1   235 5   192 1   7   255 225 5   182 1   225 5   203 1   7   255 230 5   
                                           58  1   229 5   61  1   229 5   61  1   227 5   63  1   227 5   63  1   225 5   63  1   225 5   63  1   222 5   63  1   222 5   63  1   220 5   61  1   220 5   61  1   219 5   58  1   219 5   58  1   220 5   56  1   220 5   56  1   222 5   54  1   222 5   
                                           54  1   225 5   53  1   225 5   53  1   227 5   54  1   227 5   54  1   229 5   56  1   229 5   56  1   230 5   58  1   7   255 214 5   58  1   235 5   58  1   7   255 225 5   48  1   225 5   69  1   7   255 36  4   125 1   145 4   125 1   7   255 116 4   
                                           87  1   116 4   96  1   116 4   96  1   124 4   99  1   124 4   99  1   166 4   99  1   166 4   99  1   174 4   96  1   174 4   96  1   174 4   87  1   174 4   87  1   166 4   84  1   166 4   84  1   124 4   84  1   124 4   84  1   116 4   87  1   7   255 
                                           116 4   61  1   116 4   70  1   116 4   70  1   124 4   73  1   124 4   73  1   166 4   73  1   166 4   73  1   174 4   70  1   174 4   70  1   174 4   61  1   174 4   61  1   166 4   58  1   166 4   58  1   124 4   58  1   124 4   58  1   116 4   61  1   
                                           7   255 116 4   155 1   116 4   164 1   116 4   164 1   124 4   167 1   124 4   167 1   166 4   167 1   166 4   167 1   174 4   164 1   174 4   164 1   174 4   155 1   174 4   155 1   166 4   152 1   166 4   152 1   124 4   152 1   124 4   152 1   116 4   
                                           155 1   7   255 116 4   181 1   116 4   190 1   116 4   190 1   124 4   192 1   124 4   192 1   166 4   192 1   166 4   192 1   174 4   190 1   174 4   190 1   174 4   181 1   174 4   181 1   166 4   178 1   166 4   178 1   124 4   178 1   124 4   178 1   
                                           116 4   181 1   7   255 41  4   125 1   41  4   127 1   41  4   127 1   40  4   128 1   40  4   128 1   39  4   130 1   39  4   130 1   38  4   130 1   38  4   130 1   36  4   131 1   36  4   131 1   35  4   130 1   35  4   130 1   33  4   130 1   33  4   
                                           130 1   32  4   128 1   32  4   128 1   31  4   127 1   31  4   127 1   31  4   125 1   31  4   125 1   31  4   124 1   31  4   124 1   32  4   122 1   32  4   122 1   33  4   121 1   33  4   121 1   35  4   120 1   35  4   120 1   36  4   120 1   36  4   
                                           120 1   38  4   120 1   38  4   120 1   39  4   121 1   39  4   121 1   40  4   122 1   40  4   122 1   41  4   124 1   41  4   124 1   41  4   125 1   7   255 26  4   125 1   47  4   125 1   7   255 36  4   115 1   36  4   136 1   7   255 150 4   192 1   
                                           150 4   194 1   150 4   194 1   149 4   196 1   149 4   196 1   148 4   197 1   148 4   197 1   146 4   197 1   146 4   197 1   145 4   198 1   145 4   198 1   143 4   197 1   143 4   197 1   142 4   197 1   142 4   197 1   141 4   196 1   141 4   196 1   
                                           140 4   194 1   140 4   194 1   140 4   192 1   140 4   192 1   140 4   191 1   140 4   191 1   141 4   189 1   141 4   189 1   142 4   188 1   142 4   188 1   143 4   188 1   143 4   188 1   145 4   187 1   145 4   187 1   146 4   188 1   146 4   188 1   
                                           148 4   188 1   148 4   188 1   149 4   189 1   149 4   189 1   150 4   191 1   150 4   191 1   150 4   192 1   7   255 134 4   192 1   155 4   192 1   7   255 145 4   182 1   145 4   203 1   7   255 150 4   58  1   150 4   60  1   150 4   60  1   149 4   
                                           61  1   149 4   61  1   148 4   62  1   148 4   62  1   146 4   63  1   146 4   63  1   145 4   63  1   145 4   63  1   143 4   63  1   143 4   63  1   142 4   62  1   142 4   62  1   141 4   61  1   141 4   61  1   140 4   60  1   140 4   60  1   140 4   
                                           58  1   140 4   58  1   140 4   57  1   140 4   57  1   141 4   55  1   141 4   55  1   142 4   54  1   142 4   54  1   143 4   53  1   143 4   53  1   145 4   53  1   145 4   53  1   146 4   53  1   146 4   53  1   148 4   54  1   148 4   54  1   149 4   
                                           55  1   149 4   55  1   150 4   57  1   150 4   57  1   150 4   58  1   7   255 134 4   58  1   155 4   58  1   7   255 145 4   48  1   145 4   69  1   7   255 150 4   125 1   150 4   127 1   150 4   127 1   149 4   128 1   149 4   128 1   148 4   130 1   
                                           148 4   130 1   146 4   130 1   146 4   130 1   145 4   131 1   145 4   131 1   143 4   130 1   143 4   130 1   142 4   130 1   142 4   130 1   141 4   128 1   141 4   128 1   140 4   127 1   140 4   127 1   140 4   125 1   140 4   125 1   140 4   124 1   
                                           140 4   124 1   141 4   122 1   141 4   122 1   142 4   121 1   142 4   121 1   143 4   120 1   143 4   120 1   145 4   120 1   145 4   120 1   146 4   120 1   146 4   120 1   148 4   121 1   148 4   121 1   149 4   122 1   149 4   122 1   150 4   124 1   
                                           150 4   124 1   150 4   125 1   7   255 134 4   125 1   155 4   125 1   7   255 145 4   115 1   145 4   136 1   7   255 223 0   58  1   36  4   58  1   36  4   58  1   36  4   192 1   36  4   192 1   223 0   192 1   223 0   192 1   223 0   58  1   7   255 
                                           223 0   58  1   223 0   58  1   7   255 223 0   58  1   223 0   58  1   7   255 223 0   58  1   223 0   58  1   7   255 138 3   87  1   138 3   96  1   138 3   96  1   146 3   99  1   146 3   99  1   187 3   99  1   187 3   99  1   195 3   96  1   195 3   
                                           96  1   195 3   87  1   195 3   87  1   187 3   84  1   187 3   84  1   146 3   84  1   146 3   84  1   138 3   87  1   7   255 138 3   61  1   138 3   70  1   138 3   70  1   146 3   73  1   146 3   73  1   187 3   73  1   187 3   73  1   195 3   70  1   
                                           195 3   70  1   195 3   61  1   195 3   61  1   187 3   58  1   187 3   58  1   146 3   58  1   146 3   58  1   138 3   61  1   7   255 138 3   155 1   138 3   164 1   138 3   164 1   146 3   167 1   146 3   167 1   187 3   167 1   187 3   167 1   195 3   
                                           164 1   195 3   164 1   195 3   155 1   195 3   155 1   187 3   152 1   187 3   152 1   146 3   152 1   146 3   152 1   138 3   155 1   7   255 138 3   181 1   138 3   190 1   138 3   190 1   146 3   192 1   146 3   192 1   187 3   192 1   187 3   192 1   
                                           195 3   190 1   195 3   190 1   195 3   181 1   195 3   181 1   187 3   178 1   187 3   178 1   146 3   178 1   146 3   178 1   138 3   181 1   7   255 203 3   87  1   203 3   96  1   203 3   96  1   211 3   99  1   211 3   99  1   253 3   99  1   253 3   
                                           99  1   5   4   96  1   5   4   96  1   5   4   87  1   5   4   87  1   253 3   84  1   253 3   84  1   211 3   84  1   211 3   84  1   203 3   87  1   7   255 203 3   61  1   203 3   70  1   203 3   70  1   211 3   73  1   211 3   73  1   253 3   73  1   
                                           253 3   73  1   5   4   70  1   5   4   70  1   5   4   61  1   5   4   61  1   253 3   58  1   253 3   58  1   211 3   58  1   211 3   58  1   203 3   61  1   7   255 203 3   155 1   203 3   164 1   203 3   164 1   211 3   167 1   211 3   167 1   253 3   
                                           167 1   253 3   167 1   5   4   164 1   5   4   164 1   5   4   155 1   5   4   155 1   253 3   152 1   253 3   152 1   211 3   152 1   211 3   152 1   203 3   155 1   7   255 203 3   181 1   203 3   190 1   203 3   190 1   211 3   192 1   211 3   192 1   
                                           253 3   192 1   253 3   192 1   5   4   190 1   5   4   190 1   5   4   181 1   5   4   181 1   253 3   178 1   253 3   178 1   211 3   178 1   211 3   178 1   203 3   181 1   7   255 70  1   125 1   70  1   127 1   70  1   127 1   69  1   128 1   69  1   
                                           128 1   68  1   130 1   68  1   130 1   67  1   130 1   67  1   130 1   65  1   131 1   65  1   131 1   64  1   130 1   64  1   130 1   62  1   130 1   62  1   130 1   61  1   128 1   61  1   128 1   60  1   127 1   60  1   127 1   60  1   125 1   60  1   
                                           )) "a")
 (_WriteStream FILE (vl-list->string (list 125 1   60  1   124 1   60  1   124 1   61  1   122 1   61  1   122 1   62  1   121 1   62  1   121 1   64  1   120 1   64  1   120 1   65  1   120 1   65  1   120 1   67  1   120 1   67  1   120 1   68  1   121 1   68  1   121 1   69  1   122 1   69  1   
                                           122 1   70  1   124 1   70  1   124 1   70  1   125 1   7   255 55  1   125 1   76  1   125 1   7   255 65  1   115 1   65  1   136 1   7   255 204 3   192 1   204 3   194 1   204 3   194 1   203 3   196 1   203 3   196 1   202 3   197 1   202 3   197 1   
                                           201 3   197 1   201 3   197 1   199 3   198 1   199 3   198 1   198 3   197 1   198 3   197 1   196 3   197 1   196 3   197 1   195 3   196 1   195 3   196 1   194 3   194 1   194 3   194 1   194 3   192 1   194 3   192 1   194 3   191 1   194 3   191 1   
                                           195 3   189 1   195 3   189 1   196 3   188 1   196 3   188 1   198 3   188 1   198 3   188 1   199 3   187 1   199 3   187 1   201 3   188 1   201 3   188 1   202 3   188 1   202 3   188 1   203 3   189 1   203 3   189 1   204 3   191 1   204 3   191 1   
                                           204 3   192 1   7   255 189 3   192 1   210 3   192 1   7   255 199 3   182 1   199 3   203 1   7   255 204 3   58  1   204 3   60  1   204 3   60  1   203 3   61  1   203 3   61  1   202 3   62  1   202 3   62  1   201 3   63  1   201 3   63  1   199 3   
                                           63  1   199 3   63  1   198 3   63  1   198 3   63  1   196 3   62  1   196 3   62  1   195 3   61  1   195 3   61  1   194 3   60  1   194 3   60  1   194 3   58  1   194 3   58  1   194 3   57  1   194 3   57  1   195 3   55  1   195 3   55  1   196 3   
                                           54  1   196 3   54  1   198 3   53  1   198 3   53  1   199 3   53  1   199 3   53  1   201 3   53  1   201 3   53  1   202 3   54  1   202 3   54  1   203 3   55  1   203 3   55  1   204 3   57  1   204 3   57  1   204 3   58  1   7   255 189 3   58  1   
                                           210 3   58  1   7   255 199 3   48  1   199 3   69  1   7   255 41  4   58  1   41  4   60  1   41  4   60  1   40  4   61  1   40  4   61  1   39  4   62  1   39  4   62  1   38  4   63  1   38  4   63  1   36  4   63  1   36  4   63  1   35  4   63  1   
                                           35  4   63  1   33  4   62  1   33  4   62  1   32  4   61  1   32  4   61  1   31  4   60  1   31  4   60  1   31  4   58  1   31  4   58  1   31  4   57  1   31  4   57  1   32  4   55  1   32  4   55  1   33  4   54  1   33  4   54  1   35  4   53  1   
                                           35  4   53  1   36  4   53  1   36  4   53  1   38  4   53  1   38  4   53  1   39  4   54  1   39  4   54  1   40  4   55  1   40  4   55  1   41  4   57  1   41  4   57  1   41  4   58  1   7   255 26  4   58  1   47  4   58  1   7   255 36  4   48  1   
                                           36  4   69  1   7   255 41  4   192 1   41  4   194 1   41  4   194 1   40  4   196 1   40  4   196 1   39  4   197 1   39  4   197 1   38  4   197 1   38  4   197 1   36  4   198 1   36  4   198 1   35  4   197 1   35  4   197 1   33  4   197 1   33  4   
                                           197 1   32  4   196 1   32  4   196 1   31  4   194 1   31  4   194 1   31  4   192 1   31  4   192 1   31  4   191 1   31  4   191 1   32  4   189 1   32  4   189 1   33  4   188 1   33  4   188 1   35  4   188 1   35  4   188 1   36  4   187 1   36  4   
                                           187 1   38  4   188 1   38  4   188 1   39  4   188 1   39  4   188 1   40  4   189 1   40  4   189 1   41  4   191 1   41  4   191 1   41  4   192 1   7   255 26  4   192 1   47  4   192 1   7   255 36  4   182 1   36  4   203 1   7   255 228 0   192 1   
                                           228 0   194 1   228 0   194 1   227 0   196 1   227 0   196 1   226 0   197 1   226 0   197 1   225 0   197 1   225 0   197 1   223 0   198 1   223 0   198 1   222 0   197 1   222 0   197 1   220 0   197 1   220 0   197 1   219 0   196 1   219 0   196 1   
                                           218 0   194 1   218 0   194 1   218 0   192 1   218 0   192 1   218 0   191 1   218 0   191 1   219 0   189 1   219 0   189 1   220 0   188 1   220 0   188 1   222 0   188 1   222 0   188 1   223 0   187 1   223 0   187 1   225 0   188 1   225 0   188 1   
                                           226 0   188 1   226 0   188 1   227 0   189 1   227 0   189 1   228 0   191 1   228 0   191 1   228 0   192 1   7   255 213 0   192 1   233 0   192 1   7   255 223 0   182 1   223 0   203 1   7   255 228 0   58  1   228 0   60  1   228 0   60  1   227 0   
                                           61  1   227 0   61  1   226 0   62  1   226 0   62  1   225 0   63  1   225 0   63  1   223 0   63  1   223 0   63  1   222 0   63  1   222 0   63  1   220 0   62  1   220 0   62  1   219 0   61  1   219 0   61  1   218 0   60  1   218 0   60  1   218 0   
                                           58  1   218 0   58  1   218 0   57  1   218 0   57  1   219 0   55  1   219 0   55  1   220 0   54  1   220 0   54  1   222 0   53  1   222 0   53  1   223 0   53  1   223 0   53  1   225 0   53  1   225 0   53  1   226 0   54  1   226 0   54  1   227 0   
                                           55  1   227 0   55  1   228 0   57  1   228 0   57  1   228 0   58  1   7   255 213 0   58  1   233 0   58  1   7   255 223 0   48  1   223 0   69  1   7   255 41  4   125 1   41  4   127 1   41  4   127 1   40  4   128 1   40  4   128 1   39  4   130 1   
                                           39  4   130 1   38  4   130 1   38  4   130 1   36  4   131 1   36  4   131 1   35  4   130 1   35  4   130 1   33  4   130 1   33  4   130 1   32  4   128 1   32  4   128 1   31  4   127 1   31  4   127 1   31  4   125 1   31  4   125 1   31  4   124 1   
                                           31  4   124 1   32  4   122 1   32  4   122 1   33  4   121 1   33  4   121 1   35  4   120 1   35  4   120 1   36  4   120 1   36  4   120 1   38  4   120 1   38  4   120 1   39  4   121 1   39  4   121 1   40  4   122 1   40  4   122 1   41  4   124 1   
                                           41  4   124 1   41  4   125 1   7   255 26  4   125 1   47  4   125 1   7   255 36  4   115 1   36  4   136 1   7   255 27  0   58  1   182 0   58  1   182 0   58  1   182 0   99  1   182 0   99  1   98  1   99  1   98  1   99  1   98  1   152 1   98  1   
                                           152 1   182 0   152 1   182 0   152 1   182 0   192 1   182 0   192 1   27  0   192 1   27  0   192 1   27  0   58  1   7   255 27  0   58  1   27  0   58  1   7   255 27  0   58  1   27  0   58  1   7   255 27  0   58  1   27  0   58  1   7   255 79  1   
                                           139 1   76  1   141 1   76  1   141 1   73  1   143 1   73  1   143 1   69  1   144 1   69  1   144 1   65  1   145 1   65  1   145 1   62  1   144 1   62  1   144 1   58  1   143 1   58  1   143 1   55  1   141 1   55  1   141 1   52  1   139 1   52  1   
                                           139 1   49  1   136 1   49  1   136 1   48  1   133 1   48  1   133 1   46  1   129 1   46  1   129 1   46  1   125 1   46  1   125 1   46  1   122 1   46  1   122 1   48  1   118 1   48  1   118 1   49  1   115 1   49  1   115 1   52  1   112 1   52  1   
                                           112 1   55  1   109 1   55  1   109 1   58  1   108 1   58  1   108 1   62  1   107 1   62  1   107 1   65  1   106 1   65  1   106 1   69  1   107 1   69  1   107 1   73  1   108 1   73  1   108 1   76  1   109 1   76  1   109 1   79  1   112 1   7   255 
                                           79  1   112 1   79  1   139 1   7   255 4   1   87  1   4   1   96  1   4   1   96  1   12  1   99  1   12  1   99  1   53  1   99  1   53  1   99  1   61  1   96  1   61  1   96  1   61  1   87  1   61  1   87  1   53  1   84  1   53  1   84  1   12  1   
                                           84  1   12  1   84  1   4   1   87  1   7   255 4   1   61  1   4   1   70  1   4   1   70  1   12  1   73  1   12  1   73  1   53  1   73  1   53  1   73  1   61  1   70  1   61  1   70  1   61  1   61  1   61  1   61  1   53  1   58  1   53  1   58  1   
                                           12  1   58  1   12  1   58  1   4   1   61  1   7   255 4   1   155 1   4   1   164 1   4   1   164 1   12  1   167 1   12  1   167 1   53  1   167 1   53  1   167 1   61  1   164 1   61  1   164 1   61  1   155 1   61  1   155 1   53  1   152 1   53  1   
                                           152 1   12  1   152 1   12  1   152 1   4   1   155 1   7   255 4   1   181 1   4   1   190 1   4   1   190 1   12  1   192 1   12  1   192 1   53  1   192 1   53  1   192 1   61  1   190 1   61  1   190 1   61  1   181 1   61  1   181 1   53  1   178 1   
                                           53  1   178 1   12  1   178 1   12  1   178 1   4   1   181 1   7   255 69  1   87  1   69  1   96  1   69  1   96  1   77  1   99  1   77  1   99  1   119 1   99  1   119 1   99  1   127 1   96  1   127 1   96  1   127 1   87  1   127 1   87  1   119 1   
                                           84  1   119 1   84  1   77  1   84  1   77  1   84  1   69  1   87  1   7   255 69  1   61  1   69  1   70  1   69  1   70  1   77  1   73  1   77  1   73  1   119 1   73  1   119 1   73  1   127 1   70  1   127 1   70  1   127 1   61  1   127 1   61  1   
                                           119 1   58  1   119 1   58  1   77  1   58  1   77  1   58  1   69  1   61  1   7   255 69  1   155 1   69  1   164 1   69  1   164 1   77  1   167 1   77  1   167 1   119 1   167 1   119 1   167 1   127 1   164 1   127 1   164 1   127 1   155 1   127 1   
                                           155 1   119 1   152 1   119 1   152 1   77  1   152 1   77  1   152 1   69  1   155 1   7   255 69  1   181 1   69  1   190 1   69  1   190 1   77  1   192 1   77  1   192 1   119 1   192 1   119 1   192 1   127 1   190 1   127 1   190 1   127 1   181 1   
                                           127 1   181 1   119 1   178 1   119 1   178 1   77  1   178 1   77  1   178 1   69  1   181 1   7   255 34  0   61  1   34  0   70  1   34  0   70  1   42  0   73  1   42  0   73  1   84  0   73  1   84  0   73  1   92  0   70  1   92  0   70  1   92  0   
                                           61  1   92  0   61  1   84  0   58  1   84  0   58  1   42  0   58  1   42  0   58  1   34  0   61  1   7   255 34  0   181 1   34  0   190 1   34  0   190 1   42  0   192 1   42  0   192 1   84  0   192 1   84  0   192 1   92  0   190 1   92  0   190 1   
                                           92  0   181 1   92  0   181 1   84  0   178 1   84  0   178 1   42  0   178 1   42  0   178 1   34  0   181 1   7   255 70  1   192 1   70  1   194 1   70  1   194 1   69  1   196 1   69  1   196 1   67  1   197 1   67  1   197 1   65  1   198 1   65  1   
                                           198 1   63  1   197 1   63  1   197 1   62  1   196 1   62  1   196 1   61  1   194 1   61  1   194 1   60  1   192 1   60  1   192 1   61  1   191 1   61  1   191 1   62  1   189 1   62  1   189 1   63  1   188 1   63  1   188 1   65  1   187 1   65  1   
                                           187 1   67  1   188 1   67  1   188 1   69  1   189 1   69  1   189 1   70  1   191 1   70  1   191 1   70  1   192 1   7   255 55  1   192 1   76  1   192 1   7   255 65  1   182 1   65  1   203 1   7   255 70  1   58  1   70  1   60  1   70  1   60  1   
                                           69  1   62  1   69  1   62  1   67  1   63  1   67  1   63  1   65  1   63  1   65  1   63  1   63  1   63  1   63  1   63  1   62  1   62  1   62  1   62  1   61  1   60  1   61  1   60  1   60  1   58  1   60  1   58  1   61  1   56  1   61  1   56  1   
                                           62  1   55  1   62  1   55  1   63  1   53  1   63  1   53  1   65  1   53  1   65  1   53  1   67  1   53  1   67  1   53  1   69  1   55  1   69  1   55  1   70  1   56  1   70  1   56  1   70  1   58  1   7   255 55  1   58  1   76  1   58  1   7   255 
                                           65  1   48  1   65  1   69  1   7   255 32  0   192 1   32  0   194 1   32  0   194 1   30  0   196 1   30  0   196 1   29  0   197 1   29  0   197 1   27  0   198 1   27  0   198 1   25  0   197 1   25  0   197 1   23  0   196 1   23  0   196 1   22  0   
                                           194 1   22  0   194 1   22  0   192 1   22  0   192 1   22  0   191 1   22  0   191 1   23  0   189 1   23  0   189 1   25  0   188 1   25  0   188 1   27  0   187 1   27  0   187 1   29  0   188 1   29  0   188 1   30  0   189 1   30  0   189 1   32  0   
                                           191 1   32  0   191 1   32  0   192 1   7   255 16  0   192 1   37  0   192 1   7   255 27  0   182 1   27  0   203 1   7   255 32  0   58  1   32  0   60  1   32  0   60  1   30  0   62  1   30  0   62  1   29  0   63  1   29  0   63  1   27  0   63  1   
                                           27  0   63  1   25  0   63  1   25  0   63  1   23  0   62  1   23  0   62  1   22  0   60  1   22  0   60  1   22  0   58  1   22  0   58  1   22  0   56  1   22  0   56  1   23  0   55  1   23  0   55  1   25  0   53  1   25  0   53  1   27  0   53  1   
                                           27  0   53  1   29  0   53  1   29  0   53  1   30  0   55  1   30  0   55  1   32  0   56  1   32  0   56  1   32  0   58  1   7   255 16  0   58  1   37  0   58  1   7   255 27  0   48  1   27  0   69  1   7   255 68  0   58  1   68  0   60  1   68  0   
                                           60  1   67  0   62  1   67  0   62  1   65  0   63  1   65  0   63  1   63  0   63  1   63  0   63  1   61  0   63  1   61  0   63  1   59  0   62  1   59  0   62  1   58  0   60  1   58  0   60  1   58  0   58  1   58  0   58  1   58  0   56  1   58  0   
                                           56  1   59  0   55  1   59  0   55  1   61  0   53  1   61  0   53  1   63  0   53  1   63  0   53  1   65  0   53  1   65  0   53  1   67  0   55  1   67  0   55  1   68  0   56  1   68  0   56  1   68  0   58  1   7   255 53  0   58  1   73  0   58  1   
                                           7   255 63  0   48  1   63  0   69  1   7   255 68  0   192 1   68  0   194 1   68  0   194 1   67  0   196 1   67  0   196 1   65  0   197 1   65  0   197 1   63  0   198 1   63  0   198 1   61  0   197 1   61  0   197 1   59  0   196 1   59  0   196 1   
                                           58  0   194 1   58  0   194 1   58  0   192 1   58  0   192 1   58  0   191 1   58  0   191 1   59  0   189 1   59  0   189 1   61  0   188 1   61  0   188 1   63  0   187 1   63  0   187 1   65  0   188 1   65  0   188 1   67  0   189 1   67  0   189 1   
                                           68  0   191 1   68  0   191 1   68  0   192 1   7   255 53  0   192 1   73  0   192 1   7   255 63  0   182 1   63  0   203 1   7   255 68  0   125 1   68  0   127 1   68  0   127 1   67  0   129 1   67  0   129 1   65  0   130 1   65  0   130 1   63  0   
                                           131 1   63  0   131 1   61  0   130 1   61  0   130 1   59  0   129 1   59  0   129 1   58  0   127 1   58  0   127 1   58  0   125 1   58  0   125 1   58  0   123 1   58  0   123 1   59  0   122 1   59  0   122 1   61  0   121 1   61  0   121 1   63  0   
                                           120 1   63  0   120 1   65  0   121 1   65  0   121 1   67  0   122 1   67  0   122 1   68  0   123 1   68  0   123 1   68  0   125 1   7   255 53  0   125 1   73  0   125 1   7   255 63  0   115 1   63  0   136 1   7   255 70  1   125 1   70  1   127 1   
                                           70  1   127 1   69  1   129 1   69  1   129 1   67  1   130 1   67  1   130 1   65  1   131 1   65  1   131 1   63  1   130 1   63  1   130 1   62  1   129 1   62  1   129 1   61  1   127 1   61  1   127 1   60  1   125 1   60  1   125 1   61  1   123 1   
                                           61  1   123 1   62  1   122 1   62  1   122 1   63  1   121 1   63  1   121 1   65  1   120 1   65  1   120 1   67  1   121 1   67  1   121 1   69  1   122 1   69  1   122 1   70  1   123 1   70  1   123 1   70  1   125 1   7   255 55  1   125 1   76  1   
                                           125 1   7   255 65  1   115 1   65  1   136 1   0   252 65  117 116 111 67  65  68  32  83  108 105 100 101 13  10  26  0   86  2   106 6   234 2   99  219 79  1   2   0   52  18  7   255 7   255 42  0   23  1   115 3   23  1   115 3   23  1   115 3   226 
                                           1   115 3   226 1   42  0   226 1   42  0   226 1   42  0   23  1   7   255 42  0   23  1   42  0   23  1   7   255 42  0   23  1   42  0   23  1   7   255 115 3   124 1   166 3   124 1   7   255 175 3   124 1   173 3   129 1   173 3   129 1   170 3   132 
                                           1   170 3   132 1   166 3   133 1   166 3   133 1   162 3   132 1   162 3   132 1   159 3   129 1   159 3   129 1   157 3   124 1   157 3   124 1   159 3   120 1   159 3   120 1   162 3   117 1   162 3   117 1   166 3   116 1   166 3   116 1   170 3   117 
                                           1   170 3   117 1   173 3   120 1   173 3   120 1   175 3   124 1   7   255 226 2   27  1   226 2   40  1   226 2   40  1   238 2   44  1   238 2   44  1   44  3   44  1   44  3   44  1   56  3   40  1   56  3   40  1   56  3   27  1   56  3   27  1   44  
                                           3   23  1   44  3   23  1   238 2   23  1   238 2   23  1   226 2   27  1   7   255 226 2   209 1   226 2   222 1   226 2   222 1   238 2   226 1   238 2   226 1   44  3   226 1   44  3   226 1   56  3   222 1   56  3   222 1   56  3   209 1   56  3   209 
                                           1   44  3   205 1   44  3   205 1   238 2   205 1   238 2   205 1   226 2   209 1   7   255 67  1   124 1   65  1   129 1   65  1   129 1   62  1   132 1   62  1   132 1   58  1   133 1   58  1   133 1   54  1   132 1   54  1   132 1   51  1   129 1   51  
                                           1   129 1   50  1   124 1   50  1   124 1   51  1   120 1   51  1   120 1   54  1   117 1   54  1   117 1   58  1   116 1   58  1   116 1   62  1   117 1   62  1   117 1   65  1   120 1   65  1   120 1   67  1   124 1   7   255 41  1   124 1   75  1   124 
                                           1   7   255 58  1   107 1   58  1   141 1   7   255 51  0   23  1   50  0   27  1   50  0   27  1   47  0   30  1   47  0   30  1   42  0   31  1   42  0   31  1   38  0   30  1   38  0   30  1   35  0   27  1   35  0   27  1   34  0   23  1   34  0   23  
                                           1   35  0   18  1   35  0   18  1   38  0   15  1   38  0   15  1   42  0   14  1   42  0   14  1   47  0   15  1   47  0   15  1   50  0   18  1   50  0   18  1   51  0   23  1   7   255 25  0   23  1   59  0   23  1   7   255 42  0   6   1   42  0   40  
                                           )) "a")
 (_WriteStream FILE (vl-list->string (list 1   7   255 51  0   226 1   50  0   231 1   50  0   231 1   47  0   234 1   47  0   234 1   42  0   235 1   42  0   235 1   38  0   234 1   38  0   234 1   35  0   231 1   35  0   231 1   34  0   226 1   34  0   226 1   35  0   222 1   35  0   222 1   38  
                                           0   219 1   38  0   219 1   42  0   218 1   42  0   218 1   47  0   219 1   47  0   219 1   50  0   222 1   50  0   222 1   51  0   226 1   7   255 25  0   226 1   59  0   226 1   7   255 42  0   209 1   42  0   243 1   7   255 124 3   226 1   122 3   231 
                                           1   122 3   231 1   119 3   234 1   119 3   234 1   115 3   235 1   115 3   235 1   111 3   234 1   111 3   234 1   108 3   231 1   108 3   231 1   107 3   226 1   107 3   226 1   108 3   222 1   108 3   222 1   111 3   219 1   111 3   219 1   115 3   218 
                                           1   115 3   218 1   119 3   219 1   119 3   219 1   122 3   222 1   122 3   222 1   124 3   226 1   7   255 98  3   226 1   132 3   226 1   7   255 115 3   209 1   115 3   243 1   7   255 124 3   23  1   122 3   27  1   122 3   27  1   119 3   30  1   119 
                                           3   30  1   115 3   31  1   115 3   31  1   111 3   30  1   111 3   30  1   108 3   27  1   108 3   27  1   107 3   23  1   107 3   23  1   108 3   18  1   108 3   18  1   111 3   15  1   111 3   15  1   115 3   14  1   115 3   14  1   119 3   15  1   119 
                                           3   15  1   122 3   18  1   122 3   18  1   124 3   23  1   7   255 98  3   23  1   132 3   23  1   7   255 115 3   6   1   115 3   40  1   7   255 67  1   226 1   65  1   231 1   65  1   231 1   62  1   234 1   62  1   234 1   58  1   235 1   58  1   235 
                                           1   54  1   234 1   54  1   234 1   51  1   231 1   51  1   231 1   50  1   226 1   50  1   226 1   51  1   222 1   51  1   222 1   54  1   219 1   54  1   219 1   58  1   218 1   58  1   218 1   62  1   219 1   62  1   219 1   65  1   222 1   65  1   222 
                                           1   67  1   226 1   7   255 41  1   226 1   75  1   226 1   7   255 58  1   209 1   58  1   243 1   7   255 67  1   23  1   65  1   27  1   65  1   27  1   62  1   30  1   62  1   30  1   58  1   31  1   58  1   31  1   54  1   30  1   54  1   30  1   51  
                                           1   27  1   51  1   27  1   50  1   23  1   50  1   23  1   51  1   18  1   51  1   18  1   54  1   15  1   54  1   15  1   58  1   14  1   58  1   14  1   62  1   15  1   62  1   15  1   65  1   18  1   65  1   18  1   67  1   23  1   7   255 41  1   23  
                                           1   75  1   23  1   7   255 58  1   6   1   58  1   40  1   7   255 22  3   23  1   21  3   27  1   21  3   27  1   17  3   30  1   17  3   30  1   13  3   31  1   13  3   31  1   9   3   30  1   9   3   30  1   6   3   27  1   6   3   27  1   5   3   23  
                                           1   5   3   23  1   6   3   18  1   6   3   18  1   9   3   15  1   9   3   15  1   13  3   14  1   13  3   14  1   17  3   15  1   17  3   15  1   21  3   18  1   21  3   18  1   22  3   23  1   7   255 252 2   23  1   30  3   23  1   7   255 13  3   6   
                                           1   13  3   40  1   7   255 22  3   226 1   21  3   231 1   21  3   231 1   17  3   234 1   17  3   234 1   13  3   235 1   13  3   235 1   9   3   234 1   9   3   234 1   6   3   231 1   6   3   231 1   5   3   226 1   5   3   226 1   6   3   222 1   6   
                                           3   222 1   9   3   219 1   9   3   219 1   13  3   218 1   13  3   218 1   17  3   219 1   17  3   219 1   21  3   222 1   21  3   222 1   22  3   226 1   7   255 252 2   226 1   30  3   226 1   7   255 13  3   209 1   13  3   243 1   7   255 175 3   124 
                                           1   173 3   129 1   173 3   129 1   170 3   132 1   170 3   132 1   166 3   133 1   166 3   133 1   162 3   132 1   162 3   132 1   159 3   129 1   159 3   129 1   158 3   124 1   158 3   124 1   159 3   120 1   159 3   120 1   162 3   117 1   162 3   117 
                                           1   166 3   116 1   166 3   116 1   170 3   117 1   170 3   117 1   173 3   120 1   173 3   120 1   175 3   124 1   7   255 149 3   124 1   183 3   124 1   7   255 166 3   107 1   166 3   141 1   7   255 15  1   209 1   15  1   222 1   15  1   222 1   27  
                                           1   226 1   27  1   226 1   89  1   226 1   89  1   226 1   101 1   222 1   101 1   222 1   101 1   209 1   101 1   209 1   89  1   205 1   89  1   205 1   27  1   205 1   27  1   205 1   15  1   209 1   7   255 15  1   27  1   15  1   40  1   15  1   40  
                                           1   27  1   44  1   27  1   44  1   89  1   44  1   89  1   44  1   101 1   40  1   101 1   40  1   101 1   27  1   101 1   27  1   89  1   23  1   89  1   23  1   27  1   23  1   27  1   23  1   15  1   27  1   7   255 217 3   23  1   60  6   23  1   60  
                                           6   23  1   60  6   226 1   7   255 60  6   226 1   217 3   226 1   7   255 217 3   226 1   217 3   23  1   7   255 217 3   23  1   217 3   23  1   7   255 217 3   23  1   217 3   23  1   7   255 166 3   124 1   217 3   124 1   7   255 180 3   124 1   178 
                                           3   131 1   178 3   131 1   173 3   136 1   173 3   136 1   166 3   138 1   166 3   138 1   159 3   136 1   159 3   136 1   154 3   131 1   154 3   131 1   152 3   124 1   152 3   124 1   154 3   118 1   154 3   118 1   159 3   113 1   159 3   113 1   166 
                                           3   111 1   166 3   111 1   173 3   113 1   173 3   113 1   178 3   118 1   178 3   118 1   180 3   124 1   7   255 19  5   27  1   19  5   40  1   19  5   40  1   31  5   44  1   31  5   44  1   93  5   44  1   93  5   44  1   105 5   40  1   105 5   40  
                                           1   105 5   27  1   105 5   27  1   93  5   23  1   93  5   23  1   31  5   23  1   31  5   23  1   19  5   27  1   7   255 19  5   209 1   19  5   222 1   19  5   222 1   31  5   226 1   31  5   226 1   93  5   226 1   93  5   226 1   105 5   222 1   105 
                                           5   222 1   105 5   209 1   105 5   209 1   93  5   205 1   93  5   205 1   31  5   205 1   31  5   205 1   19  5   209 1   7   255 175 3   124 1   173 3   129 1   173 3   129 1   170 3   132 1   170 3   132 1   166 3   133 1   166 3   133 1   162 3   132 
                                           1   162 3   132 1   159 3   129 1   159 3   129 1   158 3   124 1   158 3   124 1   159 3   120 1   159 3   120 1   162 3   117 1   162 3   117 1   166 3   116 1   166 3   116 1   170 3   117 1   170 3   117 1   173 3   120 1   173 3   120 1   175 3   124 
                                           1   7   255 149 3   124 1   183 3   124 1   7   255 166 3   107 1   166 3   141 1   7   255 70  5   23  1   69  5   27  1   69  5   27  1   66  5   30  1   66  5   30  1   62  5   31  1   62  5   31  1   57  5   30  1   57  5   30  1   54  5   27  1   54  
                                           5   27  1   53  5   23  1   53  5   23  1   54  5   18  1   54  5   18  1   57  5   15  1   57  5   15  1   62  5   14  1   62  5   14  1   66  5   15  1   66  5   15  1   69  5   18  1   69  5   18  1   70  5   23  1   7   255 45  5   23  1   79  5   23  
                                           1   7   255 62  5   6   1   62  5   40  1   7   255 70  5   226 1   69  5   231 1   69  5   231 1   66  5   234 1   66  5   234 1   62  5   235 1   62  5   235 1   57  5   234 1   57  5   234 1   54  5   231 1   54  5   231 1   53  5   226 1   53  5   226 
                                           1   54  5   222 1   54  5   222 1   57  5   219 1   57  5   219 1   62  5   218 1   62  5   218 1   66  5   219 1   66  5   219 1   69  5   222 1   69  5   222 1   70  5   226 1   7   255 45  5   226 1   79  5   226 1   7   255 62  5   209 1   62  5   243 
                                           1   7   255 69  6   226 1   68  6   231 1   68  6   231 1   65  6   234 1   65  6   234 1   60  6   235 1   60  6   235 1   56  6   234 1   56  6   234 1   53  6   231 1   53  6   231 1   52  6   226 1   52  6   226 1   53  6   222 1   53  6   222 1   56  
                                           6   219 1   56  6   219 1   60  6   218 1   60  6   218 1   65  6   219 1   65  6   219 1   68  6   222 1   68  6   222 1   69  6   226 1   7   255 43  6   226 1   77  6   226 1   7   255 60  6   209 1   60  6   243 1   7   255 69  6   23  1   68  6   27  
                                           1   68  6   27  1   65  6   30  1   65  6   30  1   60  6   31  1   60  6   31  1   56  6   30  1   56  6   30  1   53  6   27  1   53  6   27  1   52  6   23  1   52  6   23  1   53  6   18  1   53  6   18  1   56  6   15  1   56  6   15  1   60  6   14  
                                           1   60  6   14  1   65  6   15  1   65  6   15  1   68  6   18  1   68  6   18  1   69  6   23  1   7   255 43  6   23  1   77  6   23  1   7   255 60  6   6   1   60  6   40  1   0   252 65  117 116 111 67  65  68  32  83  108 105 100 101 13  10  26  0   
                                           86  2   73  6   247 2   97  120 67  1   2   0   52  18  7   255 7   255 158 3   67  1   42  6   67  1   42  6   67  1   42  6   182 1   7   255 42  6   182 1   158 3   182 1   7   255 158 3   182 1   158 3   67  1   7   255 158 3   67  1   158 3   67  1   
                                           7   255 158 3   67  1   158 3   67  1   7   255 158 3   67  1   158 3   67  1   7   255 42  6   125 1   42  6   125 1   7   255 46  6   125 1   45  6   128 1   45  6   128 1   42  6   129 1   42  6   129 1   38  6   128 1   38  6   128 1   37  6   125 1   
                                           37  6   125 1   38  6   121 1   38  6   121 1   42  6   120 1   42  6   120 1   45  6   121 1   45  6   121 1   46  6   125 1   7   255 203 3   125 1   202 3   128 1   202 3   128 1   199 3   129 1   199 3   129 1   196 3   128 1   196 3   128 1   194 3   
                                           125 1   194 3   125 1   196 3   121 1   196 3   121 1   199 3   120 1   199 3   120 1   202 3   121 1   202 3   121 1   203 3   125 1   7   255 187 5   89  1   187 5   96  1   187 5   96  1   193 5   99  1   193 5   99  1   226 5   99  1   226 5   99  1   
                                           232 5   96  1   232 5   96  1   232 5   89  1   232 5   89  1   226 5   87  1   226 5   87  1   193 5   87  1   193 5   87  1   187 5   89  1   7   255 187 5   69  1   187 5   76  1   187 5   76  1   193 5   78  1   193 5   78  1   226 5   78  1   226 5   
                                           78  1   232 5   76  1   232 5   76  1   232 5   69  1   232 5   69  1   226 5   67  1   226 5   67  1   193 5   67  1   193 5   67  1   187 5   69  1   7   255 187 5   153 1   187 5   160 1   187 5   160 1   193 5   162 1   193 5   162 1   226 5   162 1   
                                           226 5   162 1   232 5   160 1   232 5   160 1   232 5   153 1   232 5   153 1   226 5   151 1   226 5   151 1   193 5   151 1   193 5   151 1   187 5   153 1   7   255 187 5   173 1   187 5   180 1   187 5   180 1   193 5   182 1   193 5   182 1   226 5   
                                           182 1   226 5   182 1   232 5   180 1   232 5   180 1   232 5   173 1   232 5   173 1   226 5   171 1   226 5   171 1   193 5   171 1   193 5   171 1   187 5   173 1   7   255 241 5   89  1   241 5   96  1   241 5   96  1   247 5   99  1   247 5   99  1   
                                           24  6   99  1   24  6   99  1   30  6   96  1   30  6   96  1   30  6   89  1   30  6   89  1   24  6   87  1   24  6   87  1   247 5   87  1   247 5   87  1   241 5   89  1   7   255 241 5   69  1   241 5   76  1   241 5   76  1   247 5   78  1   247 5   
                                           78  1   24  6   78  1   24  6   78  1   30  6   76  1   30  6   76  1   30  6   69  1   30  6   69  1   24  6   67  1   24  6   67  1   247 5   67  1   247 5   67  1   241 5   69  1   7   255 241 5   153 1   241 5   160 1   241 5   160 1   247 5   162 1   
                                           247 5   162 1   24  6   162 1   24  6   162 1   30  6   160 1   30  6   160 1   30  6   153 1   30  6   153 1   24  6   151 1   24  6   151 1   247 5   151 1   247 5   151 1   241 5   153 1   7   255 241 5   173 1   241 5   180 1   241 5   180 1   247 5   
                                           182 1   247 5   182 1   24  6   182 1   24  6   182 1   30  6   180 1   30  6   180 1   30  6   173 1   30  6   173 1   24  6   171 1   24  6   171 1   247 5   171 1   247 5   171 1   241 5   173 1   7   255 159 3   67  1   159 3   68  1   159 3   68  1   
                                           158 3   68  1   158 3   68  1   157 3   68  1   157 3   68  1   157 3   67  1   157 3   67  1   157 3   66  1   157 3   66  1   158 3   66  1   158 3   66  1   159 3   66  1   159 3   66  1   159 3   67  1   7   255 155 3   67  1   161 3   67  1   7   255 
                                           158 3   64  1   158 3   70  1   7   255 43  6   67  1   43  6   68  1   43  6   68  1   42  6   68  1   42  6   68  1   41  6   68  1   41  6   68  1   40  6   67  1   40  6   67  1   41  6   66  1   41  6   66  1   42  6   66  1   42  6   66  1   43  6   
                                           66  1   43  6   66  1   43  6   67  1   7   255 39  6   67  1   44  6   67  1   7   255 42  6   64  1   42  6   70  1   7   255 159 3   182 1   159 3   183 1   159 3   183 1   158 3   184 1   158 3   184 1   157 3   183 1   157 3   183 1   157 3   182 1   
                                           157 3   182 1   157 3   181 1   157 3   181 1   158 3   181 1   158 3   181 1   159 3   181 1   159 3   181 1   159 3   182 1   7   255 155 3   182 1   161 3   182 1   7   255 158 3   179 1   158 3   185 1   7   255 43  6   182 1   43  6   183 1   43  6   
                                           183 1   42  6   184 1   42  6   184 1   41  6   183 1   41  6   183 1   40  6   182 1   40  6   182 1   41  6   181 1   41  6   181 1   42  6   181 1   42  6   181 1   43  6   181 1   43  6   181 1   43  6   182 1   7   255 39  6   182 1   44  6   182 1   
                                           7   255 42  6   179 1   42  6   185 1   7   255 200 3   125 1   199 3   126 1   199 3   126 1   198 3   125 1   198 3   125 1   197 3   125 1   197 3   125 1   198 3   124 1   198 3   124 1   199 3   123 1   199 3   123 1   200 3   124 1   200 3   124 1   
                                           200 3   125 1   7   255 196 3   125 1   202 3   125 1   7   255 199 3   122 1   199 3   127 1   7   255 43  6   125 1   42  6   126 1   42  6   126 1   41  6   125 1   41  6   125 1   40  6   125 1   40  6   125 1   41  6   124 1   41  6   124 1   42  6   
                                           123 1   42  6   123 1   43  6   124 1   43  6   124 1   43  6   125 1   7   255 39  6   125 1   44  6   125 1   7   255 42  6   122 1   42  6   127 1   7   255 238 5   182 1   238 5   183 1   238 5   183 1   237 5   184 1   237 5   184 1   236 5   183 1   
                                           236 5   183 1   235 5   182 1   235 5   182 1   236 5   181 1   236 5   181 1   237 5   181 1   237 5   181 1   238 5   181 1   238 5   181 1   238 5   182 1   7   255 234 5   182 1   239 5   182 1   7   255 237 5   179 1   237 5   185 1   7   255 238 5   
                                           67  1   238 5   68  1   238 5   68  1   237 5   68  1   237 5   68  1   236 5   68  1   236 5   68  1   235 5   67  1   235 5   67  1   236 5   66  1   236 5   66  1   237 5   66  1   237 5   66  1   238 5   66  1   238 5   66  1   238 5   67  1   7   255 
                                           234 5   67  1   239 5   67  1   7   255 237 5   64  1   237 5   70  1   7   255 63  3   125 1   199 3   125 1   7   255 71  3   125 1   69  3   130 1   69  3   130 1   63  3   132 1   63  3   132 1   58  3   130 1   58  3   130 1   55  3   125 1   55  3   
                                           125 1   58  3   119 1   58  3   119 1   63  3   117 1   63  3   117 1   69  3   119 1   69  3   119 1   71  3   125 1   7   255 149 3   89  1   149 3   96  1   149 3   96  1   155 3   99  1   155 3   99  1   188 3   99  1   188 3   99  1   194 3   96  1   
                                           194 3   96  1   194 3   89  1   194 3   89  1   188 3   87  1   188 3   87  1   155 3   87  1   155 3   87  1   149 3   89  1   7   255 149 3   69  1   149 3   76  1   149 3   76  1   155 3   78  1   155 3   78  1   188 3   78  1   188 3   78  1   194 3   
                                           76  1   194 3   76  1   194 3   69  1   194 3   69  1   188 3   67  1   188 3   67  1   155 3   67  1   155 3   67  1   149 3   69  1   7   255 149 3   153 1   149 3   160 1   149 3   160 1   155 3   162 1   155 3   162 1   188 3   162 1   188 3   162 1   
                                           194 3   160 1   194 3   160 1   194 3   153 1   194 3   153 1   188 3   151 1   188 3   151 1   155 3   151 1   155 3   151 1   149 3   153 1   7   255 149 3   173 1   149 3   180 1   149 3   180 1   155 3   182 1   155 3   182 1   188 3   182 1   188 3   
                                           182 1   194 3   180 1   194 3   180 1   194 3   173 1   194 3   173 1   188 3   171 1   188 3   171 1   155 3   171 1   155 3   171 1   149 3   173 1   7   255 203 3   89  1   203 3   96  1   203 3   96  1   210 3   99  1   210 3   99  1   242 3   99  1   
                                           242 3   99  1   249 3   96  1   249 3   96  1   249 3   89  1   249 3   89  1   242 3   87  1   242 3   87  1   210 3   87  1   210 3   87  1   203 3   89  1   7   255 203 3   69  1   203 3   76  1   203 3   76  1   210 3   78  1   210 3   78  1   242 3   
                                           78  1   242 3   78  1   249 3   76  1   249 3   76  1   249 3   69  1   249 3   69  1   242 3   67  1   242 3   67  1   210 3   67  1   210 3   67  1   203 3   69  1   7   255 203 3   153 1   203 3   160 1   203 3   160 1   210 3   162 1   210 3   162 1   
                                           242 3   162 1   242 3   162 1   249 3   160 1   249 3   160 1   249 3   153 1   249 3   153 1   242 3   151 1   242 3   151 1   210 3   151 1   210 3   151 1   203 3   153 1   7   255 203 3   173 1   203 3   180 1   203 3   180 1   210 3   182 1   210 3   
                                           182 1   242 3   182 1   242 3   182 1   249 3   180 1   249 3   180 1   249 3   173 1   249 3   173 1   242 3   171 1   242 3   171 1   210 3   171 1   210 3   171 1   203 3   173 1   7   255 64  3   125 1   63  3   126 1   63  3   126 1   62  3   125 1   
                                           62  3   125 1   62  3   124 1   62  3   124 1   63  3   123 1   63  3   123 1   64  3   124 1   64  3   124 1   64  3   125 1   7   255 60  3   125 1   66  3   125 1   7   255 63  3   122 1   63  3   127 1   7   255 200 3   125 1   199 3   126 1   199 3   
                                           )) "a")
 (_WriteStream FILE (vl-list->string (list 126 1   198 3   125 1   198 3   125 1   197 3   125 1   197 3   125 1   198 3   124 1   198 3   124 1   199 3   123 1   199 3   123 1   200 3   124 1   200 3   124 1   200 3   125 1   7   255 196 3   125 1   202 3   125 1   7   255 199 3   122 1   199 3   
                                           127 1   7   255 200 3   182 1   200 3   183 1   200 3   183 1   199 3   184 1   199 3   184 1   198 3   183 1   198 3   183 1   197 3   182 1   197 3   182 1   198 3   181 1   198 3   181 1   199 3   181 1   199 3   181 1   200 3   181 1   200 3   181 1   
                                           200 3   182 1   7   255 196 3   182 1   202 3   182 1   7   255 199 3   179 1   199 3   185 1   7   255 200 3   67  1   200 3   68  1   200 3   68  1   199 3   68  1   199 3   68  1   198 3   68  1   198 3   68  1   197 3   67  1   197 3   67  1   198 3   
                                           66  1   198 3   66  1   199 3   66  1   199 3   66  1   200 3   66  1   200 3   66  1   200 3   67  1   7   255 196 3   67  1   202 3   67  1   7   255 199 3   64  1   199 3   70  1   7   255 180 0   67  1   63  3   67  1   63  3   67  1   63  3   182 1   
                                           7   255 63  3   182 1   180 0   182 1   7   255 180 0   182 1   180 0   67  1   7   255 180 0   67  1   180 0   67  1   7   255 180 0   67  1   180 0   67  1   7   255 180 0   67  1   180 0   67  1   7   255 63  3   125 1   63  3   125 1   7   255 68  3   
                                           125 1   66  3   128 1   66  3   128 1   63  3   129 1   63  3   129 1   60  3   128 1   60  3   128 1   59  3   125 1   59  3   125 1   60  3   121 1   60  3   121 1   63  3   120 1   63  3   120 1   66  3   121 1   66  3   121 1   68  3   125 1   7   255 
                                           225 0   125 1   224 0   128 1   224 0   128 1   220 0   129 1   220 0   129 1   217 0   128 1   217 0   128 1   216 0   125 1   216 0   125 1   217 0   121 1   217 0   121 1   220 0   120 1   220 0   120 1   224 0   121 1   224 0   121 1   225 0   125 1   
                                           7   255 208 2   89  1   208 2   96  1   208 2   96  1   215 2   99  1   215 2   99  1   247 2   99  1   247 2   99  1   253 2   96  1   253 2   96  1   253 2   89  1   253 2   89  1   247 2   87  1   247 2   87  1   215 2   87  1   215 2   87  1   208 2   
                                           89  1   7   255 208 2   69  1   208 2   76  1   208 2   76  1   215 2   78  1   215 2   78  1   247 2   78  1   247 2   78  1   253 2   76  1   253 2   76  1   253 2   69  1   253 2   69  1   247 2   67  1   247 2   67  1   215 2   67  1   215 2   67  1   
                                           208 2   69  1   7   255 208 2   153 1   208 2   160 1   208 2   160 1   215 2   162 1   215 2   162 1   247 2   162 1   247 2   162 1   253 2   160 1   253 2   160 1   253 2   153 1   253 2   153 1   247 2   151 1   247 2   151 1   215 2   151 1   215 2   
                                           151 1   208 2   153 1   7   255 208 2   173 1   208 2   180 1   208 2   180 1   215 2   182 1   215 2   182 1   247 2   182 1   247 2   182 1   253 2   180 1   253 2   180 1   253 2   173 1   253 2   173 1   247 2   171 1   247 2   171 1   215 2   171 1   
                                           215 2   171 1   208 2   173 1   7   255 7   3   89  1   7   3   96  1   7   3   96  1   13  3   99  1   13  3   99  1   45  3   99  1   45  3   99  1   52  3   96  1   52  3   96  1   52  3   89  1   52  3   89  1   45  3   87  1   45  3   87  1   13  3   
                                           87  1   13  3   87  1   7   3   89  1   7   255 7   3   69  1   7   3   76  1   7   3   76  1   13  3   78  1   13  3   78  1   45  3   78  1   45  3   78  1   52  3   76  1   52  3   76  1   52  3   69  1   52  3   69  1   45  3   67  1   45  3   67  1   
                                           13  3   67  1   13  3   67  1   7   3   69  1   7   255 7   3   153 1   7   3   160 1   7   3   160 1   13  3   162 1   13  3   162 1   45  3   162 1   45  3   162 1   52  3   160 1   52  3   160 1   52  3   153 1   52  3   153 1   45  3   151 1   45  3   
                                           151 1   13  3   151 1   13  3   151 1   7   3   153 1   7   255 7   3   173 1   7   3   180 1   7   3   180 1   13  3   182 1   13  3   182 1   45  3   182 1   45  3   182 1   52  3   180 1   52  3   180 1   52  3   173 1   52  3   173 1   45  3   171 1   
                                           45  3   171 1   13  3   171 1   13  3   171 1   7   3   173 1   7   255 181 0   67  1   181 0   68  1   181 0   68  1   180 0   68  1   180 0   68  1   179 0   68  1   179 0   68  1   178 0   67  1   178 0   67  1   179 0   66  1   179 0   66  1   180 0   
                                           66  1   180 0   66  1   181 0   66  1   181 0   66  1   181 0   67  1   7   255 177 0   67  1   182 0   67  1   7   255 180 0   64  1   180 0   70  1   7   255 64  3   67  1   64  3   68  1   64  3   68  1   63  3   68  1   63  3   68  1   62  3   68  1   
                                           62  3   68  1   62  3   67  1   62  3   67  1   62  3   66  1   62  3   66  1   63  3   66  1   63  3   66  1   64  3   66  1   64  3   66  1   64  3   67  1   7   255 60  3   67  1   66  3   67  1   7   255 63  3   64  1   63  3   70  1   7   255 181 0   
                                           182 1   181 0   183 1   181 0   183 1   180 0   184 1   180 0   184 1   179 0   183 1   179 0   183 1   178 0   182 1   178 0   182 1   179 0   181 1   179 0   181 1   180 0   181 1   180 0   181 1   181 0   181 1   181 0   181 1   181 0   182 1   7   255 
                                           177 0   182 1   182 0   182 1   7   255 180 0   179 1   180 0   185 1   7   255 64  3   182 1   64  3   183 1   64  3   183 1   63  3   184 1   63  3   184 1   62  3   183 1   62  3   183 1   62  3   182 1   62  3   182 1   62  3   181 1   62  3   181 1   
                                           63  3   181 1   63  3   181 1   64  3   181 1   64  3   181 1   64  3   182 1   7   255 60  3   182 1   66  3   182 1   7   255 63  3   179 1   63  3   185 1   7   255 222 0   125 1   221 0   125 1   221 0   125 1   220 0   126 1   220 0   126 1   219 0   
                                           125 1   219 0   125 1   219 0   124 1   219 0   124 1   220 0   123 1   220 0   123 1   221 0   124 1   221 0   124 1   222 0   125 1   7   255 218 0   125 1   223 0   125 1   7   255 220 0   122 1   220 0   127 1   7   255 64  3   125 1   63  3   126 1   
                                           63  3   126 1   62  3   125 1   62  3   125 1   62  3   124 1   62  3   124 1   63  3   123 1   63  3   123 1   64  3   124 1   64  3   124 1   64  3   125 1   7   255 60  3   125 1   66  3   125 1   7   255 63  3   122 1   63  3   127 1   7   255 3   3   
                                           182 1   3   3   183 1   3   3   183 1   2   3   184 1   2   3   184 1   1   3   183 1   1   3   183 1   1   3   182 1   1   3   182 1   1   3   181 1   1   3   181 1   2   3   181 1   2   3   181 1   3   3   181 1   3   3   181 1   3   3   182 1   7   255 
                                           255 2   182 1   5   3   182 1   7   255 2   3   179 1   2   3   185 1   7   255 3   3   67  1   3   3   68  1   3   3   68  1   2   3   68  1   2   3   68  1   1   3   68  1   1   3   68  1   1   3   67  1   1   3   67  1   1   3   66  1   1   3   66  1   
                                           2   3   66  1   2   3   66  1   3   3   66  1   3   3   66  1   3   3   67  1   7   255 255 2   67  1   5   3   67  1   7   255 2   3   64  1   2   3   70  1   7   255 30  0   70  1   119 0   70  1   119 0   70  1   119 0   102 1   119 0   102 1   0   1   
                                           102 1   0   1   102 1   0   1   147 1   0   1   147 1   119 0   147 1   119 0   147 1   119 0   179 1   119 0   179 1   30  0   179 1   30  0   179 1   30  0   70  1   7   255 30  0   70  1   30  0   70  1   7   255 30  0   70  1   30  0   70  1   7   255 
                                           30  0   70  1   30  0   70  1   7   255 231 0   135 1   224 0   139 1   224 0   139 1   216 0   139 1   216 0   139 1   209 0   135 1   209 0   135 1   205 0   129 1   205 0   129 1   205 0   121 1   205 0   121 1   209 0   114 1   209 0   114 1   216 0   
                                           110 1   216 0   110 1   224 0   110 1   224 0   110 1   231 0   114 1   7   255 231 0   114 1   231 0   135 1   7   255 176 0   93  1   176 0   100 1   176 0   100 1   182 0   102 1   182 0   102 1   215 0   102 1   215 0   102 1   221 0   100 1   221 0   
                                           100 1   221 0   93  1   221 0   93  1   215 0   91  1   215 0   91  1   182 0   91  1   182 0   91  1   176 0   93  1   7   255 176 0   72  1   176 0   79  1   176 0   79  1   182 0   82  1   182 0   82  1   215 0   82  1   215 0   82  1   221 0   79  1   
                                           221 0   79  1   221 0   72  1   221 0   72  1   215 0   70  1   215 0   70  1   182 0   70  1   182 0   70  1   176 0   72  1   7   255 176 0   149 1   176 0   156 1   176 0   156 1   182 0   158 1   182 0   158 1   215 0   158 1   215 0   158 1   221 0   
                                           156 1   221 0   156 1   221 0   149 1   221 0   149 1   215 0   147 1   215 0   147 1   182 0   147 1   182 0   147 1   176 0   149 1   7   255 176 0   170 1   176 0   177 1   176 0   177 1   182 0   179 1   182 0   179 1   215 0   179 1   215 0   179 1   
                                           221 0   177 1   221 0   177 1   221 0   170 1   221 0   170 1   215 0   167 1   215 0   167 1   182 0   167 1   182 0   167 1   176 0   170 1   7   255 233 0   93  1   233 0   100 1   233 0   100 1   239 0   102 1   239 0   102 1   16  1   102 1   16  1   
                                           102 1   22  1   100 1   22  1   100 1   22  1   93  1   22  1   93  1   16  1   91  1   16  1   91  1   239 0   91  1   239 0   91  1   233 0   93  1   7   255 233 0   72  1   233 0   79  1   233 0   79  1   239 0   82  1   239 0   82  1   16  1   82  1   
                                           16  1   82  1   22  1   79  1   22  1   79  1   22  1   72  1   22  1   72  1   16  1   70  1   16  1   70  1   239 0   70  1   239 0   70  1   233 0   72  1   7   255 233 0   149 1   233 0   156 1   233 0   156 1   239 0   158 1   239 0   158 1   16  1   
                                           158 1   16  1   158 1   22  1   156 1   22  1   156 1   22  1   149 1   22  1   149 1   16  1   147 1   16  1   147 1   239 0   147 1   239 0   147 1   233 0   149 1   7   255 233 0   170 1   233 0   177 1   233 0   177 1   239 0   179 1   239 0   179 1   
                                           16  1   179 1   16  1   179 1   22  1   177 1   22  1   177 1   22  1   170 1   22  1   170 1   16  1   167 1   16  1   167 1   239 0   167 1   239 0   167 1   233 0   170 1   7   255 32  0   70  1   31  0   71  1   31  0   71  1   30  0   72  1   30  0   
                                           72  1   29  0   71  1   29  0   71  1   29  0   70  1   29  0   70  1   29  0   69  1   29  0   69  1   30  0   69  1   30  0   69  1   31  0   69  1   31  0   69  1   32  0   70  1   7   255 28  0   70  1   33  0   70  1   7   255 30  0   68  1   30  0   
                                           73  1   7   255 63  0   70  1   62  0   71  1   62  0   71  1   62  0   72  1   62  0   72  1   61  0   71  1   61  0   71  1   60  0   70  1   60  0   70  1   61  0   69  1   61  0   69  1   62  0   69  1   62  0   69  1   63  0   70  1   7   255 59  0   
                                           70  1   64  0   70  1   7   255 62  0   68  1   62  0   73  1   7   255 32  0   179 1   31  0   180 1   31  0   180 1   30  0   180 1   30  0   180 1   29  0   180 1   29  0   180 1   29  0   179 1   29  0   179 1   29  0   178 1   29  0   178 1   30  0   
                                           177 1   30  0   177 1   31  0   178 1   31  0   178 1   32  0   179 1   7   255 28  0   179 1   33  0   179 1   7   255 30  0   176 1   30  0   181 1   7   255 63  0   179 1   62  0   180 1   62  0   180 1   61  0   180 1   61  0   180 1   60  0   179 1   
                                           60  0   179 1   61  0   178 1   61  0   178 1   62  0   177 1   62  0   177 1   62  0   178 1   62  0   178 1   63  0   179 1   7   255 59  0   179 1   64  0   179 1   7   255 62  0   176 1   62  0   181 1   7   255 63  0   125 1   62  0   125 1   62  0   
                                           125 1   62  0   126 1   62  0   126 1   61  0   125 1   61  0   125 1   60  0   125 1   60  0   125 1   61  0   124 1   61  0   124 1   62  0   123 1   62  0   123 1   62  0   124 1   62  0   124 1   63  0   125 1   7   255 59  0   125 1   64  0   125 1   
                                           7   255 62  0   122 1   62  0   127 1   7   255 222 0   125 1   221 0   125 1   221 0   125 1   220 0   126 1   220 0   126 1   219 0   125 1   219 0   125 1   219 0   124 1   219 0   124 1   220 0   123 1   220 0   123 1   221 0   124 1   221 0   124 1   
                                           222 0   125 1   7   255 218 0   125 1   223 0   125 1   7   255 220 0   122 1   220 0   127 1   7   255 228 0   179 1   228 0   180 1   228 0   180 1   227 0   180 1   227 0   180 1   226 0   180 1   226 0   180 1   226 0   179 1   226 0   179 1   226 0   
                                           178 1   226 0   178 1   227 0   177 1   227 0   177 1   228 0   178 1   228 0   178 1   228 0   179 1   7   255 224 0   179 1   230 0   179 1   7   255 227 0   176 1   227 0   181 1   7   255 228 0   70  1   228 0   71  1   228 0   71  1   227 0   72  1   
                                           227 0   72  1   226 0   71  1   226 0   71  1   226 0   70  1   226 0   70  1   226 0   69  1   226 0   69  1   227 0   69  1   227 0   69  1   228 0   69  1   228 0   69  1   228 0   70  1   7   255 224 0   70  1   230 0   70  1   7   255 227 0   68  1   
                                           227 0   73  1   7   255 39  0   72  1   39  0   79  1   39  0   79  1   45  0   82  1   45  0   82  1   78  0   82  1   78  0   82  1   84  0   79  1   84  0   79  1   84  0   72  1   84  0   72  1   78  0   70  1   78  0   70  1   45  0   70  1   45  0   
                                           70  1   39  0   72  1   7   255 39  0   170 1   39  0   177 1   39  0   177 1   45  0   179 1   45  0   179 1   78  0   179 1   78  0   179 1   84  0   177 1   84  0   177 1   84  0   170 1   84  0   170 1   78  0   167 1   78  0   167 1   45  0   167 1   
                                           45  0   167 1   39  0   170 1   0   252 65  117 116 111 67  65  68  32  83  108 105 100 101 13  10  26  0   86  2   73  6   247 2   97  120 67  1   2   0   52  18  7   255 7   255 255 1   11  1   22  6   11  1   22  6   11  1   22  6   246 1   22  6   246 
                                           1   255 1   246 1   255 1   246 1   255 1   11  1   7   255 255 1   11  1   255 1   11  1   7   255 255 1   11  1   255 1   11  1   7   255 255 1   11  1   255 1   11  1   7   255 62  5   61  1   62  5   77  1   62  5   77  1   76  5   82  1   76  5   82  
                                           1   148 5   82  1   148 5   82  1   163 5   77  1   163 5   77  1   163 5   61  1   163 5   61  1   148 5   57  1   148 5   57  1   76  5   57  1   76  5   57  1   62  5   61  1   7   255 62  5   16  1   62  5   32  1   62  5   32  1   76  5   37  1   76  
                                           5   37  1   148 5   37  1   148 5   37  1   163 5   32  1   163 5   32  1   163 5   16  1   163 5   16  1   148 5   11  1   148 5   11  1   76  5   11  1   76  5   11  1   62  5   16  1   7   255 62  5   180 1   62  5   196 1   62  5   196 1   76  5   200 
                                           1   76  5   200 1   148 5   200 1   148 5   200 1   163 5   196 1   163 5   196 1   163 5   180 1   163 5   180 1   148 5   175 1   148 5   175 1   76  5   175 1   76  5   175 1   62  5   180 1   7   255 62  5   225 1   62  5   241 1   62  5   241 1   76  
                                           5   246 1   76  5   246 1   148 5   246 1   148 5   246 1   163 5   241 1   163 5   241 1   163 5   225 1   163 5   225 1   148 5   221 1   148 5   221 1   76  5   221 1   76  5   221 1   62  5   225 1   7   255 176 5   61  1   176 5   77  1   176 5   77  
                                           1   190 5   82  1   190 5   82  1   7   6   82  1   7   6   82  1   21  6   77  1   21  6   77  1   21  6   61  1   21  6   61  1   7   6   57  1   7   6   57  1   190 5   57  1   190 5   57  1   176 5   61  1   7   255 176 5   16  1   176 5   32  1   176 
                                           5   32  1   190 5   37  1   190 5   37  1   7   6   37  1   7   6   37  1   21  6   32  1   21  6   32  1   21  6   16  1   21  6   16  1   7   6   11  1   7   6   11  1   190 5   11  1   190 5   11  1   176 5   16  1   7   255 176 5   180 1   176 5   196 
                                           1   176 5   196 1   190 5   200 1   190 5   200 1   7   6   200 1   7   6   200 1   21  6   196 1   21  6   196 1   21  6   180 1   21  6   180 1   7   6   175 1   7   6   175 1   190 5   175 1   190 5   175 1   176 5   180 1   7   255 176 5   225 1   176 
                                           5   241 1   176 5   241 1   190 5   246 1   190 5   246 1   7   6   246 1   7   6   246 1   21  6   241 1   21  6   241 1   21  6   225 1   21  6   225 1   7   6   221 1   7   6   221 1   190 5   221 1   190 5   221 1   176 5   225 1   7   255 126 2   129 
                                           1   124 2   133 1   124 2   133 1   121 2   136 1   121 2   136 1   117 2   138 1   117 2   138 1   112 2   136 1   112 2   136 1   109 2   133 1   109 2   133 1   108 2   129 1   108 2   129 1   109 2   124 1   109 2   124 1   112 2   121 1   112 2   121 
                                           1   117 2   120 1   117 2   120 1   121 2   121 1   121 2   121 1   124 2   124 1   124 2   124 1   126 2   129 1   7   255 99  2   129 1   135 2   129 1   7   255 117 2   111 1   117 2   147 1   7   255 8   2   246 1   7   2   250 1   7   2   250 1   4   
                                           2   254 1   4   2   254 1   255 1   255 1   255 1   255 1   251 1   254 1   251 1   254 1   247 1   250 1   247 1   250 1   246 1   246 1   246 1   246 1   247 1   241 1   247 1   241 1   251 1   238 1   251 1   238 1   255 1   237 1   255 1   237 1   4   
                                           2   238 1   4   2   238 1   7   2   241 1   7   2   241 1   8   2   246 1   7   255 237 1   246 1   17  2   246 1   7   255 255 1   228 1   255 1   8   2   7   255 8   2   11  1   7   2   16  1   7   2   16  1   4   2   19  1   4   2   19  1   255 1   20  
                                           1   255 1   20  1   251 1   19  1   251 1   19  1   247 1   16  1   247 1   16  1   246 1   11  1   246 1   11  1   247 1   7   1   247 1   7   1   251 1   4   1   251 1   4   1   255 1   2   1   255 1   2   1   4   2   4   1   4   2   4   1   7   2   7   
                                           )) "a")
 (_WriteStream FILE (vl-list->string (list 1   7   2   7   1   8   2   11  1   7   255 237 1   11  1   17  2   11  1   7   255 255 1   249 0   255 1   29  1   7   255 31  6   11  1   30  6   16  1   30  6   16  1   26  6   19  1   26  6   19  1   22  6   20  1   22  6   20  1   17  6   19  1   17  
                                           6   19  1   14  6   16  1   14  6   16  1   13  6   11  1   13  6   11  1   14  6   7   1   14  6   7   1   17  6   4   1   17  6   4   1   22  6   2   1   22  6   2   1   26  6   4   1   26  6   4   1   30  6   7   1   30  6   7   1   31  6   11  1   7   
                                           255 4   6   11  1   40  6   11  1   7   255 22  6   249 0   22  6   29  1   7   255 31  6   246 1   30  6   250 1   30  6   250 1   26  6   254 1   26  6   254 1   22  6   255 1   22  6   255 1   17  6   254 1   17  6   254 1   14  6   250 1   14  6   250 
                                           1   13  6   246 1   13  6   246 1   14  6   241 1   14  6   241 1   17  6   238 1   17  6   238 1   22  6   237 1   22  6   237 1   26  6   238 1   26  6   238 1   30  6   241 1   30  6   241 1   31  6   246 1   7   255 4   6   246 1   40  6   246 1   7   
                                           255 22  6   228 1   22  6   8   2   7   255 178 5   246 1   177 5   250 1   177 5   250 1   174 5   254 1   174 5   254 1   169 5   255 1   169 5   255 1   165 5   254 1   165 5   254 1   162 5   250 1   162 5   250 1   160 5   246 1   160 5   246 1   162 
                                           5   241 1   162 5   241 1   165 5   238 1   165 5   238 1   169 5   237 1   169 5   237 1   174 5   238 1   174 5   238 1   177 5   241 1   177 5   241 1   178 5   246 1   7   255 151 5   246 1   187 5   246 1   7   255 169 5   228 1   169 5   8   2   7   
                                           255 178 5   11  1   177 5   16  1   177 5   16  1   174 5   19  1   174 5   19  1   169 5   20  1   169 5   20  1   165 5   19  1   165 5   19  1   162 5   16  1   162 5   16  1   160 5   11  1   160 5   11  1   162 5   7   1   162 5   7   1   165 5   4   
                                           1   165 5   4   1   169 5   2   1   169 5   2   1   174 5   4   1   174 5   4   1   177 5   7   1   177 5   7   1   178 5   11  1   7   255 151 5   11  1   187 5   11  1   7   255 169 5   249 0   169 5   29  1   7   255 51  0   11  1   66  1   11  1   66  
                                           1   11  1   66  1   82  1   66  1   82  1   174 2   82  1   174 2   82  1   174 2   175 1   174 2   175 1   66  1   175 1   66  1   175 1   66  1   246 1   66  1   246 1   51  0   246 1   51  0   246 1   51  0   11  1   7   255 51  0   11  1   51  0   11  
                                           1   7   255 51  0   11  1   51  0   11  1   7   255 51  0   11  1   51  0   11  1   7   255 140 2   152 1   137 2   155 1   137 2   155 1   133 2   158 1   133 2   158 1   129 2   160 1   129 2   160 1   125 2   161 1   125 2   161 1   121 2   162 1   121 
                                           2   162 1   117 2   162 1   117 2   162 1   112 2   162 1   112 2   162 1   108 2   161 1   108 2   161 1   104 2   160 1   104 2   160 1   100 2   158 1   100 2   158 1   96  2   155 1   96  2   155 1   93  2   152 1   93  2   152 1   90  2   149 1   90  
                                           2   149 1   88  2   145 1   88  2   145 1   86  2   141 1   86  2   141 1   84  2   137 1   84  2   137 1   83  2   133 1   83  2   133 1   83  2   129 1   83  2   129 1   83  2   124 1   83  2   124 1   84  2   120 1   84  2   120 1   86  2   116 1   86  
                                           2   116 1   88  2   112 1   88  2   112 1   90  2   108 1   90  2   108 1   93  2   105 1   93  2   105 1   96  2   102 1   96  2   102 1   100 2   100 1   100 2   100 1   104 2   98  1   104 2   98  1   108 2   96  1   108 2   96  1   112 2   95  1   112 
                                           2   95  1   117 2   95  1   117 2   95  1   121 2   95  1   121 2   95  1   125 2   96  1   125 2   96  1   129 2   98  1   129 2   98  1   133 2   100 1   133 2   100 1   137 2   102 1   137 2   102 1   140 2   105 1   7   255 140 2   105 1   140 2   152 
                                           1   7   255 9   2   61  1   9   2   77  1   9   2   77  1   23  2   82  1   23  2   82  1   96  2   82  1   96  2   82  1   110 2   77  1   110 2   77  1   110 2   61  1   110 2   61  1   96  2   57  1   96  2   57  1   23  2   57  1   23  2   57  1   9   
                                           2   61  1   7   255 9   2   16  1   9   2   32  1   9   2   32  1   23  2   37  1   23  2   37  1   96  2   37  1   96  2   37  1   110 2   32  1   110 2   32  1   110 2   16  1   110 2   16  1   96  2   11  1   96  2   11  1   23  2   11  1   23  2   11  
                                           1   9   2   16  1   7   255 9   2   180 1   9   2   196 1   9   2   196 1   23  2   200 1   23  2   200 1   96  2   200 1   96  2   200 1   110 2   196 1   110 2   196 1   110 2   180 1   110 2   180 1   96  2   175 1   96  2   175 1   23  2   175 1   23  
                                           2   175 1   9   2   180 1   7   255 9   2   225 1   9   2   241 1   9   2   241 1   23  2   246 1   23  2   246 1   96  2   246 1   96  2   246 1   110 2   241 1   110 2   241 1   110 2   225 1   110 2   225 1   96  2   221 1   96  2   221 1   23  2   221 
                                           1   23  2   221 1   9   2   225 1   7   255 123 2   61  1   123 2   77  1   123 2   77  1   138 2   82  1   138 2   82  1   210 2   82  1   210 2   82  1   224 2   77  1   224 2   77  1   224 2   61  1   224 2   61  1   210 2   57  1   210 2   57  1   138 
                                           2   57  1   138 2   57  1   123 2   61  1   7   255 123 2   16  1   123 2   32  1   123 2   32  1   138 2   37  1   138 2   37  1   210 2   37  1   210 2   37  1   224 2   32  1   224 2   32  1   224 2   16  1   224 2   16  1   210 2   11  1   210 2   11  
                                           1   138 2   11  1   138 2   11  1   123 2   16  1   7   255 123 2   180 1   123 2   196 1   123 2   196 1   138 2   200 1   138 2   200 1   210 2   200 1   210 2   200 1   224 2   196 1   224 2   196 1   224 2   180 1   224 2   180 1   210 2   175 1   210 
                                           2   175 1   138 2   175 1   138 2   175 1   123 2   180 1   7   255 123 2   225 1   123 2   241 1   123 2   241 1   138 2   246 1   138 2   246 1   210 2   246 1   210 2   246 1   224 2   241 1   224 2   241 1   224 2   225 1   224 2   225 1   210 2   221 
                                           1   210 2   221 1   138 2   221 1   138 2   221 1   123 2   225 1   7   255 141 0   129 1   141 0   131 1   141 0   131 1   140 0   133 1   140 0   133 1   139 0   135 1   139 0   135 1   137 0   136 1   137 0   136 1   135 0   137 1   135 0   137 1   132 
                                           0   138 1   132 0   138 1   130 0   137 1   130 0   137 1   128 0   136 1   128 0   136 1   126 0   135 1   126 0   135 1   125 0   133 1   125 0   133 1   124 0   131 1   124 0   131 1   123 0   129 1   123 0   129 1   124 0   126 1   124 0   126 1   125 
                                           0   124 1   125 0   124 1   126 0   122 1   126 0   122 1   128 0   121 1   128 0   121 1   130 0   120 1   130 0   120 1   132 0   120 1   132 0   120 1   135 0   120 1   135 0   120 1   137 0   121 1   137 0   121 1   139 0   122 1   139 0   122 1   140 
                                           0   124 1   140 0   124 1   141 0   126 1   141 0   126 1   141 0   129 1   7   255 114 0   129 1   150 0   129 1   7   255 132 0   111 1   132 0   147 1   7   255 82  0   16  1   82  0   32  1   82  0   32  1   96  0   37  1   96  0   37  1   169 0   37  
                                           1   169 0   37  1   183 0   32  1   183 0   32  1   183 0   16  1   183 0   16  1   169 0   11  1   169 0   11  1   96  0   11  1   96  0   11  1   82  0   16  1   7   255 82  0   225 1   82  0   241 1   82  0   241 1   96  0   246 1   96  0   246 1   169 
                                           0   246 1   169 0   246 1   183 0   241 1   183 0   241 1   183 0   225 1   183 0   225 1   169 0   221 1   169 0   221 1   96  0   221 1   96  0   221 1   82  0   225 1   7   255 141 0   246 1   141 0   248 1   141 0   248 1   140 0   250 1   140 0   250 
                                           1   139 0   252 1   139 0   252 1   137 0   254 1   137 0   254 1   135 0   254 1   135 0   254 1   132 0   255 1   132 0   255 1   130 0   254 1   130 0   254 1   128 0   254 1   128 0   254 1   126 0   252 1   126 0   252 1   125 0   250 1   125 0   250 
                                           1   124 0   248 1   124 0   248 1   123 0   246 1   123 0   246 1   124 0   243 1   124 0   243 1   125 0   241 1   125 0   241 1   126 0   239 1   126 0   239 1   128 0   238 1   128 0   238 1   130 0   237 1   130 0   237 1   132 0   237 1   132 0   237 
                                           1   135 0   237 1   135 0   237 1   137 0   238 1   137 0   238 1   139 0   239 1   139 0   239 1   140 0   241 1   140 0   241 1   141 0   243 1   141 0   243 1   141 0   246 1   7   255 114 0   246 1   150 0   246 1   7   255 132 0   228 1   132 0   8   
                                           2   7   255 60  0   246 1   60  0   248 1   60  0   248 1   59  0   250 1   59  0   250 1   58  0   252 1   58  0   252 1   56  0   254 1   56  0   254 1   54  0   254 1   54  0   254 1   51  0   255 1   51  0   255 1   49  0   254 1   49  0   254 1   47  
                                           0   254 1   47  0   254 1   45  0   252 1   45  0   252 1   43  0   250 1   43  0   250 1   42  0   248 1   42  0   248 1   42  0   246 1   42  0   246 1   42  0   243 1   42  0   243 1   43  0   241 1   43  0   241 1   45  0   239 1   45  0   239 1   47  
                                           0   238 1   47  0   238 1   49  0   237 1   49  0   237 1   51  0   237 1   51  0   237 1   54  0   237 1   54  0   237 1   56  0   238 1   56  0   238 1   58  0   239 1   58  0   239 1   59  0   241 1   59  0   241 1   60  0   243 1   60  0   243 1   60  
                                           0   246 1   7   255 33  0   246 1   69  0   246 1   7   255 51  0   228 1   51  0   8   2   7   255 126 2   246 1   125 2   248 1   125 2   248 1   124 2   250 1   124 2   250 1   123 2   252 1   123 2   252 1   121 2   254 1   121 2   254 1   119 2   254 
                                           1   119 2   254 1   117 2   255 1   117 2   255 1   114 2   254 1   114 2   254 1   112 2   254 1   112 2   254 1   110 2   252 1   110 2   252 1   109 2   250 1   109 2   250 1   108 2   248 1   108 2   248 1   108 2   246 1   108 2   246 1   108 2   243 
                                           1   108 2   243 1   109 2   241 1   109 2   241 1   110 2   239 1   110 2   239 1   112 2   238 1   112 2   238 1   114 2   237 1   114 2   237 1   117 2   237 1   117 2   237 1   119 2   237 1   119 2   237 1   121 2   238 1   121 2   238 1   123 2   239 
                                           1   123 2   239 1   124 2   241 1   124 2   241 1   125 2   243 1   125 2   243 1   126 2   246 1   7   255 99  2   246 1   135 2   246 1   7   255 117 2   228 1   117 2   8   2   7   255 141 0   11  1   141 0   14  1   141 0   14  1   140 0   16  1   140 
                                           0   16  1   139 0   18  1   139 0   18  1   137 0   19  1   137 0   19  1   135 0   20  1   135 0   20  1   132 0   20  1   132 0   20  1   130 0   20  1   130 0   20  1   128 0   19  1   128 0   19  1   126 0   18  1   126 0   18  1   125 0   16  1   125 
                                           0   16  1   124 0   14  1   124 0   14  1   123 0   11  1   123 0   11  1   124 0   9   1   124 0   9   1   125 0   7   1   125 0   7   1   126 0   5   1   126 0   5   1   128 0   4   1   128 0   4   1   130 0   3   1   130 0   3   1   132 0   2   1   132 
                                           0   2   1   135 0   3   1   135 0   3   1   137 0   4   1   137 0   4   1   139 0   5   1   139 0   5   1   140 0   7   1   140 0   7   1   141 0   9   1   141 0   9   1   141 0   11  1   7   255 114 0   11  1   150 0   11  1   7   255 132 0   249 0   132 
                                           0   29  1   7   255 60  0   11  1   60  0   14  1   60  0   14  1   59  0   16  1   59  0   16  1   58  0   18  1   58  0   18  1   56  0   19  1   56  0   19  1   54  0   20  1   54  0   20  1   51  0   20  1   51  0   20  1   49  0   20  1   49  0   20  
                                           1   47  0   19  1   47  0   19  1   45  0   18  1   45  0   18  1   43  0   16  1   43  0   16  1   42  0   14  1   42  0   14  1   42  0   11  1   42  0   11  1   42  0   9   1   42  0   9   1   43  0   7   1   43  0   7   1   45  0   5   1   45  0   5   
                                           1   47  0   4   1   47  0   4   1   49  0   3   1   49  0   3   1   51  0   2   1   51  0   2   1   54  0   3   1   54  0   3   1   56  0   4   1   56  0   4   1   58  0   5   1   58  0   5   1   59  0   7   1   59  0   7   1   60  0   9   1   60  0   9   
                                           1   60  0   11  1   7   255 33  0   11  1   69  0   11  1   7   255 51  0   249 0   51  0   29  1   7   255 126 2   11  1   125 2   14  1   125 2   14  1   124 2   16  1   124 2   16  1   123 2   18  1   123 2   18  1   121 2   19  1   121 2   19  1   119 
                                           2   20  1   119 2   20  1   117 2   20  1   117 2   20  1   114 2   20  1   114 2   20  1   112 2   19  1   112 2   19  1   110 2   18  1   110 2   18  1   109 2   16  1   109 2   16  1   108 2   14  1   108 2   14  1   108 2   11  1   108 2   11  1   108 
                                           2   9   1   108 2   9   1   109 2   7   1   109 2   7   1   110 2   5   1   110 2   5   1   112 2   4   1   112 2   4   1   114 2   3   1   114 2   3   1   117 2   2   1   117 2   2   1   119 2   3   1   119 2   3   1   121 2   4   1   121 2   4   1   123 
                                           2   5   1   123 2   5   1   124 2   7   1   124 2   7   1   125 2   9   1   125 2   9   1   126 2   11  1   7   255 99  2   11  1   135 2   11  1   7   255 117 2   249 0   117 2   29  1   7   255 126 2   129 1   125 2   131 1   125 2   131 1   124 2   133 
                                           1   124 2   133 1   123 2   135 1   123 2   135 1   121 2   136 1   121 2   136 1   119 2   137 1   119 2   137 1   117 2   138 1   117 2   138 1   114 2   137 1   114 2   137 1   112 2   136 1   112 2   136 1   110 2   135 1   110 2   135 1   109 2   133 
                                           1   109 2   133 1   108 2   131 1   108 2   131 1   108 2   129 1   108 2   129 1   108 2   126 1   108 2   126 1   109 2   124 1   109 2   124 1   110 2   122 1   110 2   122 1   112 2   121 1   112 2   121 1   114 2   120 1   114 2   120 1   117 2   120 
                                           1   117 2   120 1   119 2   120 1   119 2   120 1   121 2   121 1   121 2   121 1   123 2   122 1   123 2   122 1   124 2   124 1   124 2   124 1   125 2   126 1   125 2   126 1   126 2   129 1   7   255 99  2   129 1   135 2   129 1   7   255 117 2   111 
                                           1   117 2   147 1   0   252 65  117 116 111 67  65  68  32  83  108 105 100 101 13  10  26  0   86  2   106 6   234 2   99  219 79  1   2   0   52  18  7   255 7   255 135 0   244 0   236 5   244 0   236 5   244 0   236 5   3   2   236 5   3   2   135 0   
                                           3   2   135 0   3   2   135 0   244 0   7   255 135 0   244 0   135 0   244 0   7   255 135 0   244 0   135 0   244 0   7   255 117 4   249 0   117 4   11  1   117 4   11  1   133 4   17  1   133 4   17  1   216 4   17  1   216 4   17  1   232 4   11  1   
                                           232 4   11  1   232 4   249 0   232 4   249 0   216 4   244 0   216 4   244 0   133 4   244 0   133 4   244 0   117 4   249 0   7   255 117 4   236 1   117 4   254 1   117 4   254 1   133 4   3   2   133 4   3   2   216 4   3   2   216 4   3   2   232 4   
                                           254 1   232 4   254 1   232 4   236 1   232 4   236 1   216 4   230 1   216 4   230 1   133 4   230 1   133 4   230 1   117 4   236 1   7   255 147 0   244 0   145 0   250 0   145 0   250 0   141 0   254 0   141 0   254 0   135 0   255 0   135 0   255 0   
                                           130 0   254 0   130 0   254 0   126 0   250 0   126 0   250 0   124 0   244 0   124 0   244 0   126 0   238 0   126 0   238 0   130 0   234 0   130 0   234 0   135 0   233 0   135 0   233 0   141 0   234 0   141 0   234 0   145 0   238 0   145 0   238 0   
                                           147 0   244 0   7   255 113 0   244 0   158 0   244 0   7   255 135 0   221 0   135 0   10  1   7   255 147 0   3   2   145 0   9   2   145 0   9   2   141 0   13  2   141 0   13  2   135 0   14  2   135 0   14  2   130 0   13  2   130 0   13  2   126 0   
                                           9   2   126 0   9   2   124 0   3   2   124 0   3   2   126 0   254 1   126 0   254 1   130 0   249 1   130 0   249 1   135 0   248 1   135 0   248 1   141 0   249 1   141 0   249 1   145 0   254 1   145 0   254 1   147 0   3   2   7   255 113 0   3   2   
                                           158 0   3   2   7   255 135 0   237 1   135 0   26  2   7   255 247 5   3   2   245 5   9   2   245 5   9   2   241 5   13  2   241 5   13  2   236 5   14  2   236 5   14  2   230 5   13  2   230 5   13  2   226 5   9   2   226 5   9   2   224 5   3   2   
                                           224 5   3   2   226 5   254 1   226 5   254 1   230 5   249 1   230 5   249 1   236 5   248 1   236 5   248 1   241 5   249 1   241 5   249 1   245 5   254 1   245 5   254 1   247 5   3   2   7   255 213 5   3   2   2   6   3   2   7   255 236 5   237 1   
                                           236 5   26  2   7   255 247 5   244 0   245 5   250 0   245 5   250 0   241 5   254 0   241 5   254 0   236 5   255 0   236 5   255 0   230 5   254 0   230 5   254 0   226 5   250 0   226 5   250 0   224 5   244 0   224 5   244 0   226 5   238 0   226 5   
                                           238 0   230 5   234 0   230 5   234 0   236 5   233 0   236 5   233 0   241 5   234 0   241 5   234 0   245 5   238 0   245 5   238 0   247 5   244 0   7   255 213 5   244 0   2   6   244 0   7   255 236 5   221 0   236 5   10  1   7   255 140 1   124 1   
                                           138 1   129 1   138 1   129 1   134 1   133 1   134 1   133 1   128 1   135 1   128 1   135 1   123 1   133 1   123 1   133 1   118 1   129 1   118 1   129 1   117 1   124 1   117 1   124 1   118 1   118 1   118 1   118 1   123 1   114 1   123 1   114 1   
                                           128 1   112 1   128 1   112 1   134 1   114 1   134 1   114 1   138 1   118 1   138 1   118 1   140 1   124 1   7   255 106 1   124 1   151 1   124 1   7   255 128 1   101 1   128 1   146 1   7   255 140 1   3   2   138 1   9   2   138 1   9   2   134 1   
                                           )) "a")
 (_WriteStream FILE (vl-list->string (list 13  2   134 1   13  2   128 1   14  2   128 1   14  2   123 1   13  2   123 1   13  2   118 1   9   2   118 1   9   2   117 1   3   2   117 1   3   2   118 1   254 1   118 1   254 1   123 1   249 1   123 1   249 1   128 1   248 1   128 1   248 1   134 1   
                                           249 1   134 1   249 1   138 1   254 1   138 1   254 1   140 1   3   2   7   255 106 1   3   2   151 1   3   2   7   255 128 1   237 1   128 1   26  2   7   255 186 4   3   2   185 4   9   2   185 4   9   2   180 4   13  2   180 4   13  2   175 4   14  2   
                                           175 4   14  2   169 4   13  2   169 4   13  2   165 4   9   2   165 4   9   2   163 4   3   2   163 4   3   2   165 4   254 1   165 4   254 1   169 4   249 1   169 4   249 1   175 4   248 1   175 4   248 1   180 4   249 1   180 4   249 1   185 4   254 1   
                                           185 4   254 1   186 4   3   2   7   255 152 4   3   2   197 4   3   2   7   255 175 4   237 1   175 4   26  2   7   255 186 4   244 0   185 4   250 0   185 4   250 0   180 4   254 0   180 4   254 0   175 4   255 0   175 4   255 0   169 4   254 0   169 4   
                                           254 0   165 4   250 0   165 4   250 0   163 4   244 0   163 4   244 0   165 4   238 0   165 4   238 0   169 4   234 0   169 4   234 0   175 4   233 0   175 4   233 0   180 4   234 0   180 4   234 0   185 4   238 0   185 4   238 0   186 4   244 0   7   255 
                                           152 4   244 0   197 4   244 0   7   255 175 4   221 0   175 4   10  1   7   255 140 1   244 0   138 1   250 0   138 1   250 0   134 1   254 0   134 1   254 0   128 1   255 0   128 1   255 0   123 1   254 0   123 1   254 0   118 1   250 0   118 1   250 0   
                                           117 1   244 0   117 1   244 0   118 1   238 0   118 1   238 0   123 1   234 0   123 1   234 0   128 1   233 0   128 1   233 0   134 1   234 0   134 1   234 0   138 1   238 0   138 1   238 0   140 1   244 0   7   255 106 1   244 0   151 1   244 0   7   255 
                                           128 1   221 0   128 1   10  1   7   255 71  1   249 0   71  1   11  1   71  1   11  1   87  1   17  1   87  1   17  1   170 1   17  1   170 1   17  1   186 1   11  1   186 1   11  1   186 1   249 0   186 1   249 0   170 1   244 0   170 1   244 0   87  1   
                                           244 0   87  1   244 0   71  1   249 0   7   255 71  1   236 1   71  1   254 1   71  1   254 1   87  1   3   2   87  1   3   2   170 1   3   2   170 1   3   2   186 1   254 1   186 1   254 1   186 1   236 1   186 1   236 1   170 1   230 1   170 1   230 1   
                                           87  1   230 1   87  1   230 1   71  1   236 1   0   252 65  117 116 111 67  65  68  32  83  108 105 100 101 13  10  26  0   86  2   73  6   31  3   200 70  51  1   2   0   52  18  7   255 7   255 36  6   254 1   35  6   1   2   35  6   1   2   33  6   4   
                                           2   33  6   4   2   29  6   5   2   29  6   5   2   25  6   4   2   25  6   4   2   23  6   1   2   23  6   1   2   22  6   254 1   22  6   254 1   23  6   250 1   23  6   250 1   25  6   248 1   25  6   248 1   29  6   247 1   29  6   247 1   33  6   248 
                                           1   33  6   248 1   35  6   250 1   35  6   250 1   36  6   254 1   7   255 15  6   254 1   43  6   254 1   7   255 29  6   240 1   29  6   12  2   7   255 36  6   70  1   35  6   73  1   35  6   73  1   33  6   76  1   33  6   76  1   29  6   77  1   29  
                                           6   77  1   25  6   76  1   25  6   76  1   23  6   73  1   23  6   73  1   22  6   70  1   22  6   70  1   23  6   66  1   23  6   66  1   25  6   64  1   25  6   64  1   29  6   63  1   29  6   63  1   33  6   64  1   33  6   64  1   35  6   66  1   35  
                                           6   66  1   36  6   70  1   7   255 15  6   70  1   43  6   70  1   7   255 29  6   55  1   29  6   84  1   7   255 132 1   70  1   131 1   73  1   131 1   73  1   128 1   76  1   128 1   76  1   125 1   77  1   125 1   77  1   121 1   76  1   121 1   76  
                                           1   119 1   73  1   119 1   73  1   118 1   70  1   118 1   70  1   119 1   66  1   119 1   66  1   121 1   64  1   121 1   64  1   125 1   63  1   125 1   63  1   128 1   64  1   128 1   64  1   131 1   66  1   131 1   66  1   132 1   70  1   7   255 111 
                                           1   70  1   139 1   70  1   7   255 125 1   55  1   125 1   84  1   7   255 132 1   254 1   131 1   1   2   131 1   1   2   128 1   4   2   128 1   4   2   125 1   5   2   125 1   5   2   121 1   4   2   121 1   4   2   119 1   1   2   119 1   1   2   118 
                                           1   254 1   118 1   254 1   119 1   250 1   119 1   250 1   121 1   248 1   121 1   248 1   125 1   247 1   125 1   247 1   128 1   248 1   128 1   248 1   131 1   250 1   131 1   250 1   132 1   254 1   7   255 111 1   254 1   139 1   254 1   7   255 125 
                                           1   240 1   125 1   12  2   3   255 3   255 19  5   162 1   18  5   165 1   18  5   165 1   16  5   168 1   16  5   168 1   12  5   169 1   12  5   169 1   8   5   168 1   8   5   168 1   6   5   165 1   6   5   165 1   5   5   162 1   5   5   162 1   6   
                                           5   158 1   6   5   158 1   8   5   156 1   8   5   156 1   12  5   155 1   12  5   155 1   16  5   156 1   16  5   156 1   18  5   158 1   18  5   158 1   19  5   162 1   3   255 254 4   162 1   26  5   162 1   3   255 12  5   148 1   12  5   176 1   3   
                                           255 53  2   162 1   52  2   165 1   52  2   165 1   50  2   168 1   50  2   168 1   46  2   169 1   46  2   169 1   43  2   168 1   43  2   168 1   40  2   165 1   40  2   165 1   39  2   162 1   39  2   162 1   40  2   158 1   40  2   158 1   43  2   156 
                                           1   43  2   156 1   46  2   155 1   46  2   155 1   50  2   156 1   50  2   156 1   52  2   158 1   52  2   158 1   53  2   162 1   3   255 32  2   162 1   60  2   162 1   3   255 46  2   148 1   46  2   176 1   7   255 7   255 57  2   162 1   55  2   167 
                                           1   55  2   167 1   52  2   171 1   52  2   171 1   46  2   173 1   46  2   173 1   41  2   171 1   41  2   171 1   37  2   167 1   37  2   167 1   35  2   162 1   35  2   162 1   37  2   156 1   37  2   156 1   41  2   152 1   41  2   152 1   46  2   151 
                                           1   46  2   151 1   52  2   152 1   52  2   152 1   55  2   156 1   55  2   156 1   57  2   162 1   7   255 125 1   70  1   29  6   70  1   29  6   70  1   29  6   254 1   29  6   254 1   125 1   254 1   125 1   254 1   125 1   70  1   7   255 125 1   70  
                                           1   125 1   70  1   7   255 23  5   162 1   21  5   167 1   21  5   167 1   17  5   171 1   17  5   171 1   12  5   173 1   12  5   173 1   7   5   171 1   7   5   171 1   3   5   167 1   3   5   167 1   1   5   162 1   1   5   162 1   3   5   156 1   3   
                                           5   156 1   7   5   152 1   7   5   152 1   12  5   151 1   12  5   151 1   17  5   152 1   17  5   152 1   21  5   156 1   21  5   156 1   23  5   162 1   7   255 121 2   179 1   104 2   156 1   104 2   156 1   130 2   156 1   7   255 121 2   179 1   121 
                                           2   144 1   1   255 1   255 53  2   162 1   52  2   165 1   52  2   165 1   50  2   168 1   50  2   168 1   46  2   169 1   46  2   169 1   43  2   168 1   43  2   168 1   40  2   165 1   40  2   165 1   39  2   162 1   39  2   162 1   40  2   158 1   40  
                                           2   158 1   43  2   156 1   43  2   156 1   46  2   155 1   46  2   155 1   50  2   156 1   50  2   156 1   52  2   158 1   52  2   158 1   53  2   162 1   1   255 32  2   162 1   60  2   162 1   1   255 46  2   148 1   46  2   176 1   7   255 7   255 57  
                                           2   162 1   55  2   167 1   55  2   167 1   52  2   171 1   52  2   171 1   46  2   173 1   46  2   173 1   41  2   171 1   41  2   171 1   37  2   167 1   37  2   167 1   35  2   162 1   35  2   162 1   37  2   156 1   37  2   156 1   41  2   152 1   41  
                                           2   152 1   46  2   151 1   46  2   151 1   52  2   152 1   52  2   152 1   55  2   156 1   55  2   156 1   57  2   162 1   7   255 32  0   254 1   31  0   1   2   31  0   1   2   28  0   4   2   28  0   4   2   25  0   5   2   25  0   5   2   21  0   4   
                                           2   21  0   4   2   19  0   1   2   19  0   1   2   18  0   254 1   18  0   254 1   19  0   250 1   19  0   250 1   21  0   248 1   21  0   248 1   25  0   247 1   25  0   247 1   28  0   248 1   28  0   248 1   31  0   250 1   31  0   250 1   32  0   254 
                                           1   7   255 11  0   254 1   39  0   254 1   7   255 25  0   240 1   25  0   12  2   7   255 32  0   70  1   31  0   73  1   31  0   73  1   28  0   76  1   28  0   76  1   25  0   77  1   25  0   77  1   21  0   76  1   21  0   76  1   19  0   73  1   19  
                                           0   73  1   18  0   70  1   18  0   70  1   19  0   66  1   19  0   66  1   21  0   64  1   21  0   64  1   25  0   63  1   25  0   63  1   28  0   64  1   28  0   64  1   31  0   66  1   31  0   66  1   32  0   70  1   7   255 11  0   70  1   39  0   70  
                                           1   7   255 25  0   55  1   25  0   84  1   7   255 80  2   70  1   79  2   73  1   79  2   73  1   77  2   76  1   77  2   76  1   73  2   77  1   73  2   77  1   70  2   76  1   70  2   76  1   67  2   73  1   67  2   73  1   66  2   70  1   66  2   70  
                                           1   67  2   66  1   67  2   66  1   70  2   64  1   70  2   64  1   73  2   63  1   73  2   63  1   77  2   64  1   77  2   64  1   79  2   66  1   79  2   66  1   80  2   70  1   7   255 59  2   70  1   87  2   70  1   7   255 73  2   55  1   73  2   84  
                                           1   7   255 80  2   254 1   79  2   1   2   79  2   1   2   77  2   4   2   77  2   4   2   73  2   5   2   73  2   5   2   70  2   4   2   70  2   4   2   67  2   1   2   67  2   1   2   66  2   254 1   66  2   254 1   67  2   250 1   67  2   250 1   70  
                                           2   248 1   70  2   248 1   73  2   247 1   73  2   247 1   77  2   248 1   77  2   248 1   79  2   250 1   79  2   250 1   80  2   254 1   7   255 59  2   254 1   87  2   254 1   7   255 73  2   240 1   73  2   12  2   7   255 110 0   70  1   109 0   73  
                                           1   109 0   73  1   106 0   76  1   106 0   76  1   103 0   77  1   103 0   77  1   99  0   76  1   99  0   76  1   97  0   73  1   97  0   73  1   96  0   70  1   96  0   70  1   97  0   66  1   97  0   66  1   99  0   64  1   99  0   64  1   103 0   63  
                                           1   103 0   63  1   106 0   64  1   106 0   64  1   109 0   66  1   109 0   66  1   110 0   70  1   7   255 89  0   70  1   117 0   70  1   7   255 103 0   55  1   103 0   84  1   7   255 110 0   254 1   109 0   1   2   109 0   1   2   106 0   4   2   106 
                                           0   4   2   103 0   5   2   103 0   5   2   99  0   4   2   99  0   4   2   97  0   1   2   97  0   1   2   96  0   254 1   96  0   254 1   97  0   250 1   97  0   250 1   99  0   248 1   99  0   248 1   103 0   247 1   103 0   247 1   106 0   248 1   106 
                                           0   248 1   109 0   250 1   109 0   250 1   110 0   254 1   7   255 89  0   254 1   117 0   254 1   7   255 103 0   240 1   103 0   12  2   7   255 110 0   162 1   109 0   165 1   109 0   165 1   106 0   168 1   106 0   168 1   103 0   169 1   103 0   169 
                                           1   99  0   168 1   99  0   168 1   97  0   165 1   97  0   165 1   96  0   162 1   96  0   162 1   97  0   158 1   97  0   158 1   99  0   156 1   99  0   156 1   103 0   155 1   103 0   155 1   106 0   156 1   106 0   156 1   109 0   158 1   109 0   158 
                                           1   110 0   162 1   7   255 89  0   162 1   117 0   162 1   7   255 103 0   148 1   103 0   176 1   7   255 63  0   73  1   63  0   86  1   63  0   86  1   74  0   89  1   74  0   89  1   131 0   89  1   131 0   89  1   143 0   86  1   143 0   86  1   143 
                                           0   73  1   143 0   73  1   131 0   70  1   131 0   70  1   74  0   70  1   74  0   70  1   63  0   73  1   7   255 63  0   238 1   63  0   250 1   63  0   250 1   74  0   254 1   74  0   254 1   131 0   254 1   131 0   254 1   143 0   250 1   143 0   250 
                                           1   143 0   238 1   143 0   238 1   131 0   234 1   131 0   234 1   74  0   234 1   74  0   234 1   63  0   238 1   7   255 33  2   238 1   33  2   250 1   33  2   250 1   45  2   254 1   45  2   254 1   102 2   254 1   102 2   254 1   113 2   250 1   113 
                                           2   250 1   113 2   238 1   113 2   238 1   102 2   234 1   102 2   234 1   45  2   234 1   45  2   234 1   33  2   238 1   7   255 33  2   202 1   33  2   215 1   33  2   215 1   45  2   218 1   45  2   218 1   102 2   218 1   102 2   218 1   113 2   215 
                                           1   113 2   215 1   113 2   202 1   113 2   202 1   102 2   198 1   102 2   198 1   45  2   198 1   45  2   198 1   33  2   202 1   7   255 33  2   109 1   33  2   121 1   33  2   121 1   45  2   125 1   45  2   125 1   102 2   125 1   102 2   125 1   113 
                                           2   121 1   113 2   121 1   113 2   109 1   113 2   109 1   102 2   105 1   102 2   105 1   45  2   105 1   45  2   105 1   33  2   109 1   7   255 33  2   73  1   33  2   86  1   33  2   86  1   45  2   89  1   45  2   89  1   102 2   89  1   102 2   89  
                                           1   113 2   86  1   113 2   86  1   113 2   73  1   113 2   73  1   102 2   70  1   102 2   70  1   45  2   70  1   45  2   70  1   33  2   73  1   7   255 25  0   70  1   194 0   70  1   194 0   70  1   194 0   125 1   194 0   125 1   48  3   125 1   48  
                                           3   125 1   48  3   199 1   48  3   199 1   194 0   199 1   194 0   199 1   194 0   254 1   194 0   254 1   25  0   254 1   25  0   254 1   25  0   70  1   7   255 25  0   70  1   25  0   70  1   7   255 25  0   70  1   25  0   70  1   7   255 170 0   173 
                                           1   173 0   174 1   173 0   174 1   178 0   179 1   178 0   179 1   178 0   144 1   7   255 20  3   162 1   19  3   165 1   19  3   165 1   16  3   168 1   16  3   168 1   13  3   169 1   13  3   169 1   9   3   168 1   9   3   168 1   7   3   165 1   7   
                                           3   165 1   6   3   162 1   6   3   162 1   7   3   158 1   7   3   158 1   9   3   156 1   9   3   156 1   13  3   155 1   13  3   155 1   16  3   156 1   16  3   156 1   19  3   158 1   19  3   158 1   20  3   162 1   7   255 255 2   162 1   27  3   162 
                                           1   7   255 13  3   148 1   13  3   176 1   7   255 25  3   162 1   24  3   166 1   24  3   166 1   21  3   170 1   21  3   170 1   17  3   173 1   17  3   173 1   13  3   174 1   13  3   174 1   8   3   173 1   8   3   173 1   4   3   170 1   4   3   170 
                                           1   1   3   166 1   1   3   166 1   0   3   162 1   0   3   162 1   1   3   157 1   1   3   157 1   4   3   153 1   4   3   153 1   8   3   150 1   8   3   150 1   13  3   149 1   13  3   149 1   17  3   150 1   17  3   150 1   21  3   153 1   21  3   153 
                                           1   24  3   157 1   24  3   157 1   25  3   162 1   7   255 47  4   70  1   46  4   73  1   46  4   73  1   43  4   76  1   43  4   76  1   40  4   77  1   40  4   77  1   36  4   76  1   36  4   76  1   34  4   73  1   34  4   73  1   33  4   70  1   33  
                                           4   70  1   34  4   66  1   34  4   66  1   36  4   64  1   36  4   64  1   40  4   63  1   40  4   63  1   43  4   64  1   43  4   64  1   46  4   66  1   46  4   66  1   47  4   70  1   7   255 26  4   70  1   54  4   70  1   7   255 40  4   55  1   40  
                                           4   84  1   7   255 47  4   254 1   46  4   1   2   46  4   1   2   43  4   4   2   43  4   4   2   40  4   5   2   40  4   5   2   36  4   4   2   36  4   4   2   34  4   1   2   34  4   1   2   33  4   254 1   33  4   254 1   34  4   250 1   34  4   250 
                                           1   36  4   248 1   36  4   248 1   40  4   247 1   40  4   247 1   43  4   248 1   43  4   248 1   46  4   250 1   46  4   250 1   47  4   254 1   7   255 26  4   254 1   54  4   254 1   7   255 40  4   240 1   40  4   12  2   7   255 20  3   162 1   19  
                                           3   165 1   19  3   165 1   16  3   168 1   16  3   168 1   13  3   169 1   13  3   169 1   9   3   168 1   9   3   168 1   7   3   165 1   7   3   165 1   6   3   162 1   6   3   162 1   7   3   158 1   7   3   158 1   9   3   156 1   9   3   156 1   13  
                                           3   155 1   13  3   155 1   16  3   156 1   16  3   156 1   19  3   158 1   19  3   158 1   20  3   162 1   7   255 255 2   162 1   27  3   162 1   7   255 13  3   148 1   13  3   176 1   7   255 47  4   162 1   46  4   165 1   46  4   165 1   43  4   168 
                                           1   43  4   168 1   40  4   169 1   40  4   169 1   36  4   168 1   36  4   168 1   34  4   165 1   34  4   165 1   33  4   162 1   33  4   162 1   34  4   158 1   34  4   158 1   36  4   156 1   36  4   156 1   40  4   155 1   40  4   155 1   43  4   156 
                                           1   43  4   156 1   46  4   158 1   46  4   158 1   47  4   162 1   7   255 26  4   162 1   54  4   162 1   7   255 40  4   148 1   40  4   176 1   7   255 52  4   162 1   51  4   166 1   51  4   166 1   48  4   170 1   48  4   170 1   44  4   173 1   44  
                                           4   173 1   40  4   174 1   40  4   174 1   35  4   173 1   35  4   173 1   31  4   170 1   31  4   170 1   28  4   166 1   28  4   166 1   27  4   162 1   27  4   162 1   28  4   157 1   28  4   157 1   31  4   153 1   31  4   153 1   35  4   150 1   35  
                                           4   150 1   40  4   149 1   40  4   149 1   44  4   150 1   44  4   150 1   48  4   153 1   48  4   153 1   51  4   157 1   51  4   157 1   52  4   162 1   7   255 0   4   238 1   0   4   250 1   0   4   250 1   11  4   254 1   11  4   254 1   68  4   254 
                                           1   68  4   254 1   79  4   250 1   79  4   250 1   79  4   238 1   79  4   238 1   68  4   234 1   68  4   234 1   11  4   234 1   11  4   234 1   0   4   238 1   7   255 0   4   202 1   0   4   215 1   0   4   215 1   11  4   218 1   11  4   218 1   68  
                                           )) "a")
 (_WriteStream FILE (vl-list->string (list 4   218 1   68  4   218 1   79  4   215 1   79  4   215 1   79  4   202 1   79  4   202 1   68  4   198 1   68  4   198 1   11  4   198 1   11  4   198 1   0   4   202 1   7   255 0   4   109 1   0   4   121 1   0   4   121 1   11  4   125 1   11  4   125 
                                           1   68  4   125 1   68  4   125 1   79  4   121 1   79  4   121 1   79  4   109 1   79  4   109 1   68  4   105 1   68  4   105 1   11  4   105 1   11  4   105 1   0   4   109 1   7   255 0   4   73  1   0   4   86  1   0   4   86  1   11  4   89  1   11  
                                           4   89  1   68  4   89  1   68  4   89  1   79  4   86  1   79  4   86  1   79  4   73  1   79  4   73  1   68  4   70  1   68  4   70  1   11  4   70  1   11  4   70  1   0   4   73  1   7   255 20  3   162 1   19  3   165 1   19  3   165 1   16  3   168 
                                           1   16  3   168 1   13  3   169 1   13  3   169 1   9   3   168 1   9   3   168 1   6   3   165 1   6   3   165 1   5   3   162 1   5   3   162 1   6   3   158 1   6   3   158 1   9   3   155 1   9   3   155 1   13  3   154 1   13  3   154 1   16  3   155 
                                           1   16  3   155 1   19  3   158 1   19  3   158 1   20  3   162 1   7   255 233 2   126 1   75  4   126 1   75  4   126 1   75  4   197 1   75  4   197 1   233 2   197 1   233 2   197 1   233 2   126 1   7   255 233 2   126 1   233 2   126 1   7   255 233 
                                           2   126 1   233 2   126 1   7   255 74  3   171 1   74  3   173 1   74  3   173 1   75  3   176 1   75  3   176 1   77  3   178 1   77  3   178 1   80  3   179 1   80  3   179 1   87  3   179 1   87  3   179 1   90  3   178 1   90  3   178 1   92  3   176 
                                           1   92  3   176 1   94  3   173 1   94  3   173 1   94  3   169 1   94  3   169 1   92  3   166 1   92  3   166 1   89  3   161 1   89  3   161 1   72  3   144 1   72  3   144 1   95  3   144 1   7   255 120 5   70  1   120 5   73  1   120 5   73  1   117 
                                           5   76  1   117 5   76  1   113 5   77  1   113 5   77  1   110 5   76  1   110 5   76  1   107 5   73  1   107 5   73  1   106 5   70  1   106 5   70  1   107 5   66  1   107 5   66  1   110 5   64  1   110 5   64  1   113 5   63  1   113 5   63  1   117 
                                           5   64  1   117 5   64  1   120 5   66  1   120 5   66  1   120 5   70  1   7   255 99  5   70  1   128 5   70  1   7   255 113 5   55  1   113 5   84  1   7   255 120 5   254 1   120 5   1   2   120 5   1   2   117 5   4   2   117 5   4   2   113 5   5   
                                           2   113 5   5   2   110 5   4   2   110 5   4   2   107 5   1   2   107 5   1   2   106 5   254 1   106 5   254 1   107 5   250 1   107 5   250 1   110 5   248 1   110 5   248 1   113 5   247 1   113 5   247 1   117 5   248 1   117 5   248 1   120 5   250 
                                           1   120 5   250 1   120 5   254 1   7   255 99  5   254 1   128 5   254 1   7   255 113 5   240 1   113 5   12  2   7   255 47  4   162 1   46  4   165 1   46  4   165 1   43  4   168 1   43  4   168 1   40  4   169 1   40  4   169 1   36  4   168 1   36  
                                           4   168 1   34  4   165 1   34  4   165 1   33  4   162 1   33  4   162 1   34  4   158 1   34  4   158 1   36  4   156 1   36  4   156 1   40  4   155 1   40  4   155 1   43  4   156 1   43  4   156 1   46  4   158 1   46  4   158 1   47  4   162 1   7   
                                           255 26  4   162 1   54  4   162 1   7   255 40  4   148 1   40  4   176 1   7   255 23  5   162 1   21  5   167 1   21  5   167 1   17  5   171 1   17  5   171 1   12  5   173 1   12  5   173 1   7   5   171 1   7   5   171 1   3   5   167 1   3   5   167 
                                           1   1   5   162 1   1   5   162 1   3   5   156 1   3   5   156 1   7   5   152 1   7   5   152 1   12  5   151 1   12  5   151 1   17  5   152 1   17  5   152 1   21  5   156 1   21  5   156 1   23  5   162 1   1   255 1   255 19  5   162 1   18  5   165 
                                           1   18  5   165 1   16  5   168 1   16  5   168 1   12  5   169 1   12  5   169 1   8   5   168 1   8   5   168 1   6   5   165 1   6   5   165 1   5   5   162 1   5   5   162 1   6   5   158 1   6   5   158 1   8   5   156 1   8   5   156 1   12  5   155 
                                           1   12  5   155 1   16  5   156 1   16  5   156 1   18  5   158 1   18  5   158 1   19  5   162 1   1   255 254 4   162 1   26  5   162 1   1   255 12  5   148 1   12  5   176 1   7   255 7   255 74  5   202 1   74  5   215 1   74  5   215 1   85  5   218 
                                           1   85  5   218 1   142 5   218 1   142 5   218 1   153 5   215 1   153 5   215 1   153 5   202 1   153 5   202 1   142 5   198 1   142 5   198 1   85  5   198 1   85  5   198 1   74  5   202 1   7   255 74  5   109 1   74  5   121 1   74  5   121 1   85  
                                           5   125 1   85  5   125 1   142 5   125 1   142 5   125 1   153 5   121 1   153 5   121 1   153 5   109 1   153 5   109 1   142 5   105 1   142 5   105 1   85  5   105 1   85  5   105 1   74  5   109 1   7   255 74  5   73  1   74  5   86  1   74  5   86  
                                           1   85  5   89  1   85  5   89  1   142 5   89  1   142 5   89  1   153 5   86  1   153 5   86  1   153 5   73  1   153 5   73  1   142 5   70  1   142 5   70  1   85  5   70  1   85  5   70  1   74  5   73  1   7   255 74  5   238 1   74  5   250 1   74  
                                           5   250 1   85  5   254 1   85  5   254 1   142 5   254 1   142 5   254 1   153 5   250 1   153 5   250 1   153 5   238 1   153 5   238 1   142 5   234 1   142 5   234 1   85  5   234 1   85  5   234 1   74  5   238 1   7   255 47  4   162 1   46  4   165 
                                           1   46  4   165 1   43  4   168 1   43  4   168 1   40  4   169 1   40  4   169 1   36  4   168 1   36  4   168 1   33  4   165 1   33  4   165 1   32  4   162 1   32  4   162 1   33  4   158 1   33  4   158 1   36  4   156 1   36  4   156 1   40  4   155 
                                           1   40  4   155 1   43  4   156 1   43  4   156 1   46  4   158 1   46  4   158 1   47  4   162 1   7   255 4   4   126 1   29  6   126 1   29  6   126 1   29  6   197 1   29  6   197 1   4   4   197 1   4   4   197 1   4   4   126 1   7   255 4   4   126 
                                           1   4   4   126 1   7   255 4   4   126 1   4   4   126 1   7   255 102 4   179 1   121 4   179 1   121 4   179 1   111 4   166 1   111 4   166 1   116 4   166 1   116 4   166 1   119 4   164 1   119 4   164 1   121 4   163 1   121 4   163 1   122 4   158 
                                           1   122 4   158 1   122 4   154 1   122 4   154 1   121 4   149 1   121 4   149 1   117 4   146 1   117 4   146 1   112 4   144 1   112 4   144 1   107 4   144 1   107 4   144 1   102 4   146 1   102 4   146 1   100 4   147 1   100 4   147 1   99  4   151 
                                           1   0   252 65  117 116 111 67  65  68  32  83  108 105 100 101 13  10  26  0   86  2   106 6   234 2   99  219 79  1   2   0   52  18  7   255 7   255 23  0   72  1   125 0   72  1   125 0   72  1   125 0   97  1   125 0   97  1   39  1   97  1   39  1   
                                           97  1   39  1   138 1   39  1   138 1   125 0   138 1   125 0   138 1   125 0   163 1   125 0   163 1   23  0   163 1   23  0   163 1   23  0   72  1   7   255 23  0   72  1   23  0   72  1   7   255 23  0   72  1   23  0   72  1   7   255 24  1   127 1   
                                           19  1   129 1   19  1   129 1   14  1   130 1   14  1   130 1   9   1   129 1   9   1   129 1   5   1   127 1   5   1   127 1   2   1   122 1   2   1   122 1   1   1   117 1   1   1   117 1   2   1   112 1   2   1   112 1   5   1   108 1   5   1   108 1   
                                           9   1   105 1   9   1   105 1   14  1   104 1   14  1   104 1   19  1   105 1   19  1   105 1   24  1   108 1   7   255 24  1   108 1   24  1   127 1   7   255 227 0   89  1   227 0   95  1   227 0   95  1   232 0   97  1   232 0   97  1   2   1   97  1   
                                           2   1   97  1   7   1   95  1   7   1   95  1   7   1   89  1   7   1   89  1   2   1   88  1   2   1   88  1   232 0   88  1   232 0   88  1   227 0   89  1   7   255 227 0   73  1   227 0   79  1   227 0   79  1   232 0   81  1   232 0   81  1   2   1   
                                           81  1   2   1   81  1   7   1   79  1   7   1   79  1   7   1   73  1   7   1   73  1   2   1   72  1   2   1   72  1   232 0   72  1   232 0   72  1   227 0   73  1   7   255 227 0   140 1   227 0   145 1   227 0   145 1   232 0   147 1   232 0   147 1   
                                           2   1   147 1   2   1   147 1   7   1   145 1   7   1   145 1   7   1   140 1   7   1   140 1   2   1   138 1   2   1   138 1   232 0   138 1   232 0   138 1   227 0   140 1   7   255 227 0   156 1   227 0   161 1   227 0   161 1   232 0   163 1   232 0   
                                           163 1   2   1   163 1   2   1   163 1   7   1   161 1   7   1   161 1   7   1   156 1   7   1   156 1   2   1   154 1   2   1   154 1   232 0   154 1   232 0   154 1   227 0   156 1   7   255 22  1   89  1   22  1   95  1   22  1   95  1   27  1   97  1   
                                           27  1   97  1   52  1   97  1   52  1   97  1   57  1   95  1   57  1   95  1   57  1   89  1   57  1   89  1   52  1   88  1   52  1   88  1   27  1   88  1   27  1   88  1   22  1   89  1   7   255 22  1   73  1   22  1   79  1   22  1   79  1   27  1   
                                           81  1   27  1   81  1   52  1   81  1   52  1   81  1   57  1   79  1   57  1   79  1   57  1   73  1   57  1   73  1   52  1   72  1   52  1   72  1   27  1   72  1   27  1   72  1   22  1   73  1   7   255 22  1   140 1   22  1   145 1   22  1   145 1   
                                           27  1   147 1   27  1   147 1   52  1   147 1   52  1   147 1   57  1   145 1   57  1   145 1   57  1   140 1   57  1   140 1   52  1   138 1   52  1   138 1   27  1   138 1   27  1   138 1   22  1   140 1   7   255 22  1   156 1   22  1   161 1   22  1   
                                           161 1   27  1   163 1   27  1   163 1   52  1   163 1   52  1   163 1   57  1   161 1   57  1   161 1   57  1   156 1   57  1   156 1   52  1   154 1   52  1   154 1   27  1   154 1   27  1   154 1   22  1   156 1   7   255 55  0   117 1   54  0   120 1   
                                           54  0   120 1   52  0   121 1   52  0   121 1   49  0   120 1   49  0   120 1   48  0   117 1   48  0   117 1   49  0   115 1   49  0   115 1   52  0   114 1   52  0   114 1   54  0   115 1   54  0   115 1   55  0   117 1   7   255 45  0   117 1   59  0   
                                           117 1   7   255 52  0   110 1   52  0   124 1   7   255 55  0   163 1   54  0   166 1   54  0   166 1   52  0   167 1   52  0   167 1   49  0   166 1   49  0   166 1   48  0   163 1   48  0   163 1   49  0   161 1   49  0   161 1   52  0   160 1   52  0   
                                           160 1   54  0   161 1   54  0   161 1   55  0   163 1   7   255 45  0   163 1   59  0   163 1   7   255 52  0   156 1   52  0   170 1   7   255 55  0   72  1   54  0   74  1   54  0   74  1   52  0   75  1   52  0   75  1   49  0   74  1   49  0   74  1   
                                           48  0   72  1   48  0   72  1   49  0   69  1   49  0   69  1   52  0   68  1   52  0   68  1   54  0   69  1   54  0   69  1   55  0   72  1   7   255 45  0   72  1   59  0   72  1   7   255 52  0   65  1   52  0   79  1   7   255 18  1   72  1   17  1   
                                           74  1   17  1   74  1   14  1   75  1   14  1   75  1   12  1   74  1   12  1   74  1   11  1   72  1   11  1   72  1   12  1   69  1   12  1   69  1   14  1   68  1   14  1   68  1   17  1   69  1   17  1   69  1   18  1   72  1   7   255 7   1   72  1   
                                           21  1   72  1   7   255 14  1   65  1   14  1   79  1   7   255 18  1   163 1   17  1   166 1   17  1   166 1   14  1   167 1   14  1   167 1   12  1   166 1   12  1   166 1   11  1   163 1   11  1   163 1   12  1   161 1   12  1   161 1   14  1   160 1   
                                           14  1   160 1   17  1   161 1   17  1   161 1   18  1   163 1   7   255 7   1   163 1   21  1   163 1   7   255 14  1   156 1   14  1   170 1   7   255 26  0   163 1   25  0   166 1   25  0   166 1   23  0   167 1   23  0   167 1   20  0   166 1   20  0   
                                           166 1   19  0   163 1   19  0   163 1   20  0   161 1   20  0   161 1   23  0   160 1   23  0   160 1   25  0   161 1   25  0   161 1   26  0   163 1   7   255 16  0   163 1   30  0   163 1   7   255 23  0   156 1   23  0   170 1   7   255 26  0   72  1   
                                           25  0   74  1   25  0   74  1   23  0   75  1   23  0   75  1   20  0   74  1   20  0   74  1   19  0   72  1   19  0   72  1   20  0   69  1   20  0   69  1   23  0   68  1   23  0   68  1   25  0   69  1   25  0   69  1   26  0   72  1   7   255 16  0   
                                           72  1   30  0   72  1   7   255 23  0   65  1   23  0   79  1   7   255 18  1   117 1   17  1   120 1   17  1   120 1   14  1   121 1   14  1   121 1   12  1   120 1   12  1   120 1   11  1   117 1   11  1   117 1   12  1   115 1   12  1   115 1   14  1   
                                           114 1   14  1   114 1   17  1   115 1   17  1   115 1   18  1   117 1   7   255 7   1   117 1   21  1   117 1   7   255 14  1   110 1   14  1   124 1   7   255 34  0   73  1   34  0   79  1   34  0   79  1   39  0   81  1   39  0   81  1   65  0   81  1   
                                           65  0   81  1   70  0   79  1   70  0   79  1   70  0   73  1   70  0   73  1   65  0   72  1   65  0   72  1   39  0   72  1   39  0   72  1   34  0   73  1   7   255 34  0   156 1   34  0   161 1   34  0   161 1   39  0   163 1   39  0   163 1   65  0   
                                           163 1   65  0   163 1   70  0   161 1   70  0   161 1   70  0   156 1   70  0   156 1   65  0   154 1   65  0   154 1   39  0   154 1   39  0   154 1   34  0   156 1   7   255 14  1   90  1   158 1   90  1   158 1   90  1   158 1   104 1   158 1   104 1   
                                           214 1   104 1   214 1   104 1   214 1   130 1   214 1   130 1   158 1   130 1   158 1   130 1   158 1   144 1   158 1   144 1   14  1   144 1   14  1   144 1   14  1   90  1   7   255 14  1   90  1   14  1   90  1   7   255 14  1   90  1   14  1   90  1   
                                           7   255 22  1   117 1   21  1   121 1   21  1   121 1   18  1   124 1   18  1   124 1   14  1   125 1   14  1   125 1   11  1   124 1   11  1   124 1   8   1   121 1   8   1   121 1   7   1   117 1   7   1   117 1   8   1   114 1   8   1   114 1   11  1   
                                           111 1   11  1   111 1   14  1   110 1   14  1   110 1   18  1   111 1   18  1   111 1   21  1   114 1   21  1   114 1   22  1   117 1   7   255 205 1   136 1   200 1   140 1   200 1   140 1   193 1   143 1   193 1   143 1   187 1   143 1   187 1   143 1   
                                           180 1   143 1   180 1   143 1   174 1   140 1   174 1   140 1   168 1   136 1   168 1   136 1   164 1   130 1   164 1   130 1   161 1   124 1   161 1   124 1   161 1   117 1   161 1   117 1   161 1   111 1   161 1   111 1   164 1   104 1   164 1   104 1   
                                           168 1   99  1   168 1   99  1   174 1   95  1   174 1   95  1   180 1   92  1   180 1   92  1   187 1   91  1   187 1   91  1   193 1   92  1   193 1   92  1   200 1   95  1   200 1   95  1   205 1   99  1   7   255 205 1   99  1   205 1   136 1   7   255 
                                           144 1   97  1   144 1   109 1   144 1   109 1   148 1   112 1   148 1   112 1   171 1   112 1   171 1   112 1   176 1   109 1   176 1   109 1   176 1   97  1   176 1   97  1   171 1   94  1   171 1   94  1   148 1   94  1   148 1   94  1   144 1   97  1   
                                           7   255 144 1   63  1   144 1   75  1   144 1   75  1   148 1   78  1   148 1   78  1   171 1   78  1   171 1   78  1   176 1   75  1   176 1   75  1   176 1   63  1   176 1   63  1   171 1   60  1   171 1   60  1   148 1   60  1   148 1   60  1   144 1   
                                           63  1   7   255 144 1   29  1   144 1   41  1   144 1   41  1   148 1   45  1   148 1   45  1   171 1   45  1   171 1   45  1   176 1   41  1   176 1   41  1   176 1   29  1   176 1   29  1   171 1   26  1   171 1   26  1   148 1   26  1   148 1   26  1   
                                           144 1   29  1   7   255 144 1   126 1   144 1   138 1   144 1   138 1   148 1   141 1   148 1   141 1   171 1   141 1   171 1   141 1   176 1   138 1   176 1   138 1   176 1   126 1   176 1   126 1   171 1   122 1   171 1   122 1   148 1   122 1   148 1   
                                           122 1   144 1   126 1   7   255 144 1   160 1   144 1   171 1   144 1   171 1   148 1   175 1   148 1   175 1   171 1   175 1   171 1   175 1   176 1   171 1   176 1   171 1   176 1   160 1   176 1   160 1   171 1   156 1   171 1   156 1   148 1   156 1   
                                           148 1   156 1   144 1   160 1   7   255 144 1   194 1   144 1   205 1   144 1   205 1   148 1   209 1   148 1   209 1   171 1   209 1   171 1   209 1   176 1   205 1   176 1   205 1   176 1   194 1   176 1   194 1   171 1   190 1   171 1   190 1   148 1   
                                           190 1   148 1   190 1   144 1   194 1   7   255 197 1   97  1   197 1   109 1   197 1   109 1   202 1   112 1   202 1   112 1   225 1   112 1   225 1   112 1   230 1   109 1   230 1   109 1   230 1   97  1   230 1   97  1   225 1   94  1   225 1   94  1   
                                           202 1   94  1   202 1   94  1   197 1   97  1   7   255 197 1   63  1   197 1   75  1   197 1   75  1   202 1   78  1   202 1   78  1   225 1   78  1   225 1   78  1   230 1   75  1   230 1   75  1   230 1   63  1   230 1   63  1   225 1   60  1   225 1   
                                           60  1   202 1   60  1   202 1   60  1   197 1   63  1   7   255 197 1   29  1   197 1   41  1   197 1   41  1   202 1   45  1   202 1   45  1   225 1   45  1   225 1   45  1   230 1   41  1   230 1   41  1   230 1   29  1   230 1   29  1   225 1   26  1   
                                           225 1   26  1   202 1   26  1   202 1   26  1   197 1   29  1   7   255 197 1   126 1   197 1   138 1   197 1   138 1   202 1   141 1   202 1   141 1   225 1   141 1   225 1   141 1   230 1   138 1   230 1   138 1   230 1   126 1   230 1   126 1   225 1   
                                           )) "a")
 (_WriteStream FILE (vl-list->string (list 122 1   225 1   122 1   202 1   122 1   202 1   122 1   197 1   126 1   7   255 197 1   160 1   197 1   171 1   197 1   171 1   202 1   175 1   202 1   175 1   225 1   175 1   225 1   175 1   230 1   171 1   230 1   171 1   230 1   160 1   230 1   160 1   
                                           225 1   156 1   225 1   156 1   202 1   156 1   202 1   156 1   197 1   160 1   7   255 197 1   194 1   197 1   205 1   197 1   205 1   202 1   209 1   202 1   209 1   225 1   209 1   225 1   209 1   230 1   205 1   230 1   205 1   230 1   194 1   230 1   
                                           194 1   225 1   190 1   225 1   190 1   202 1   190 1   202 1   190 1   197 1   194 1   7   255 190 1   117 1   189 1   120 1   189 1   120 1   187 1   121 1   187 1   121 1   184 1   120 1   184 1   120 1   183 1   117 1   183 1   117 1   184 1   115 1   
                                           184 1   115 1   187 1   114 1   187 1   114 1   189 1   115 1   189 1   115 1   190 1   117 1   7   255 180 1   117 1   194 1   117 1   7   255 187 1   110 1   187 1   124 1   7   255 18  1   117 1   17  1   120 1   17  1   120 1   14  1   121 1   14  1   
                                           121 1   12  1   120 1   12  1   120 1   11  1   117 1   11  1   117 1   12  1   115 1   12  1   115 1   14  1   114 1   14  1   114 1   17  1   115 1   17  1   115 1   18  1   117 1   7   255 7   1   117 1   21  1   117 1   7   255 14  1   110 1   14  1   
                                           124 1   7   255 190 1   209 1   189 1   211 1   189 1   211 1   187 1   212 1   187 1   212 1   184 1   211 1   184 1   211 1   183 1   209 1   183 1   209 1   184 1   206 1   184 1   206 1   187 1   205 1   187 1   205 1   189 1   206 1   189 1   206 1   
                                           190 1   209 1   7   255 180 1   209 1   194 1   209 1   7   255 187 1   202 1   187 1   216 1   7   255 190 1   26  1   189 1   28  1   189 1   28  1   187 1   30  1   187 1   30  1   184 1   28  1   184 1   28  1   183 1   26  1   183 1   26  1   184 1   
                                           23  1   184 1   23  1   187 1   22  1   187 1   22  1   189 1   23  1   189 1   23  1   190 1   26  1   7   255 180 1   26  1   194 1   26  1   7   255 187 1   19  1   187 1   33  1   7   255 187 1   90  1   74  2   90  1   74  2   90  1   74  2   105 1   
                                           74  2   105 1   130 2   105 1   130 2   105 1   130 2   129 1   7   255 130 2   129 1   74  2   129 1   7   255 74  2   129 1   74  2   144 1   74  2   144 1   187 1   144 1   187 1   144 1   187 1   90  1   7   255 187 1   90  1   187 1   90  1   7   255 
                                           187 1   90  1   187 1   90  1   7   255 194 1   117 1   193 1   121 1   193 1   121 1   190 1   124 1   190 1   124 1   187 1   125 1   187 1   125 1   183 1   124 1   183 1   124 1   180 1   121 1   180 1   121 1   179 1   117 1   179 1   117 1   180 1   
                                           114 1   180 1   114 1   183 1   111 1   183 1   111 1   187 1   110 1   187 1   110 1   190 1   111 1   190 1   111 1   193 1   114 1   193 1   114 1   194 1   117 1   7   255 35  2   136 1   30  2   140 1   30  2   140 1   23  2   143 1   23  2   143 1   
                                           17  2   143 1   17  2   143 1   10  2   143 1   10  2   143 1   4   2   140 1   4   2   140 1   254 1   136 1   254 1   136 1   250 1   130 1   250 1   130 1   247 1   124 1   247 1   124 1   247 1   117 1   247 1   117 1   247 1   111 1   247 1   111 1   
                                           250 1   104 1   250 1   104 1   254 1   99  1   254 1   99  1   4   2   95  1   4   2   95  1   10  2   92  1   10  2   92  1   17  2   91  1   17  2   91  1   23  2   92  1   23  2   92  1   30  2   95  1   30  2   95  1   35  2   99  1   7   255 35  2   
                                           99  1   35  2   136 1   7   255 60  2   98  1   60  2   109 1   60  2   109 1   64  2   113 1   64  2   113 1   88  2   113 1   88  2   113 1   92  2   109 1   92  2   109 1   92  2   98  1   92  2   98  1   88  2   94  1   88  2   94  1   64  2   94  1   
                                           64  2   94  1   60  2   98  1   7   255 60  2   64  1   60  2   75  1   60  2   75  1   64  2   79  1   64  2   79  1   88  2   79  1   88  2   79  1   92  2   75  1   92  2   75  1   92  2   64  1   92  2   64  1   88  2   60  1   88  2   60  1   64  2   
                                           60  1   64  2   60  1   60  2   64  1   7   255 60  2   30  1   60  2   41  1   60  2   41  1   64  2   45  1   64  2   45  1   88  2   45  1   88  2   45  1   92  2   41  1   92  2   41  1   92  2   30  1   92  2   30  1   88  2   26  1   88  2   26  1   
                                           64  2   26  1   64  2   26  1   60  2   30  1   7   255 60  2   125 1   60  2   137 1   60  2   137 1   64  2   141 1   64  2   141 1   88  2   141 1   88  2   141 1   92  2   137 1   92  2   137 1   92  2   125 1   92  2   125 1   88  2   122 1   88  2   
                                           122 1   64  2   122 1   64  2   122 1   60  2   125 1   7   255 60  2   159 1   60  2   171 1   60  2   171 1   64  2   175 1   64  2   175 1   88  2   175 1   88  2   175 1   92  2   171 1   92  2   171 1   92  2   159 1   92  2   159 1   88  2   156 1   
                                           88  2   156 1   64  2   156 1   64  2   156 1   60  2   159 1   7   255 60  2   193 1   60  2   205 1   60  2   205 1   64  2   209 1   64  2   209 1   88  2   209 1   88  2   209 1   92  2   205 1   92  2   205 1   92  2   193 1   92  2   193 1   88  2   
                                           190 1   88  2   190 1   64  2   190 1   64  2   190 1   60  2   193 1   7   255 114 2   98  1   114 2   109 1   114 2   109 1   118 2   113 1   118 2   113 1   141 2   113 1   141 2   113 1   146 2   109 1   146 2   109 1   146 2   98  1   146 2   98  1   
                                           141 2   94  1   141 2   94  1   118 2   94  1   118 2   94  1   114 2   98  1   7   255 114 2   64  1   114 2   75  1   114 2   75  1   118 2   79  1   118 2   79  1   141 2   79  1   141 2   79  1   146 2   75  1   146 2   75  1   146 2   64  1   146 2   
                                           64  1   141 2   60  1   141 2   60  1   118 2   60  1   118 2   60  1   114 2   64  1   7   255 114 2   30  1   114 2   41  1   114 2   41  1   118 2   45  1   118 2   45  1   141 2   45  1   141 2   45  1   146 2   41  1   146 2   41  1   146 2   30  1   
                                           146 2   30  1   141 2   26  1   141 2   26  1   118 2   26  1   118 2   26  1   114 2   30  1   7   255 114 2   125 1   114 2   137 1   114 2   137 1   118 2   141 1   118 2   141 1   141 2   141 1   141 2   141 1   146 2   137 1   146 2   137 1   146 2   
                                           125 1   146 2   125 1   141 2   122 1   141 2   122 1   118 2   122 1   118 2   122 1   114 2   125 1   7   255 114 2   159 1   114 2   171 1   114 2   171 1   118 2   175 1   118 2   175 1   141 2   175 1   141 2   175 1   146 2   171 1   146 2   171 1   
                                           146 2   159 1   146 2   159 1   141 2   156 1   141 2   156 1   118 2   156 1   118 2   156 1   114 2   159 1   7   255 114 2   193 1   114 2   205 1   114 2   205 1   118 2   209 1   118 2   209 1   141 2   209 1   141 2   209 1   146 2   205 1   146 2   
                                           205 1   146 2   193 1   146 2   193 1   141 2   190 1   141 2   190 1   118 2   190 1   118 2   190 1   114 2   193 1   7   255 190 1   117 1   189 1   120 1   189 1   120 1   187 1   121 1   187 1   121 1   184 1   120 1   184 1   120 1   183 1   117 1   
                                           183 1   117 1   184 1   115 1   184 1   115 1   187 1   114 1   187 1   114 1   189 1   115 1   189 1   115 1   190 1   117 1   7   255 180 1   117 1   194 1   117 1   7   255 187 1   110 1   187 1   124 1   7   255 20  2   117 1   19  2   120 1   19  2   
                                           120 1   17  2   121 1   17  2   121 1   14  2   120 1   14  2   120 1   13  2   117 1   13  2   117 1   14  2   115 1   14  2   115 1   17  2   114 1   17  2   114 1   19  2   115 1   19  2   115 1   20  2   117 1   7   255 10  2   117 1   24  2   117 1   
                                           7   255 17  2   110 1   17  2   124 1   7   255 106 2   26  1   105 2   28  1   105 2   28  1   103 2   30  1   103 2   30  1   100 2   28  1   100 2   28  1   99  2   26  1   99  2   26  1   100 2   23  1   100 2   23  1   103 2   22  1   103 2   22  1   
                                           105 2   23  1   105 2   23  1   106 2   26  1   7   255 96  2   26  1   110 2   26  1   7   255 103 2   19  1   103 2   33  1   7   255 106 2   209 1   105 2   211 1   105 2   211 1   103 2   212 1   103 2   212 1   100 2   211 1   100 2   211 1   99  2   
                                           209 1   99  2   209 1   100 2   206 1   100 2   206 1   103 2   205 1   103 2   205 1   105 2   206 1   105 2   206 1   106 2   209 1   7   255 96  2   209 1   110 2   209 1   7   255 103 2   202 1   103 2   216 1   7   255 106 2   117 1   105 2   120 1   
                                           105 2   120 1   103 2   121 1   103 2   121 1   100 2   120 1   100 2   120 1   99  2   117 1   99  2   117 1   100 2   115 1   100 2   115 1   103 2   114 1   103 2   114 1   105 2   115 1   105 2   115 1   106 2   117 1   7   255 96  2   117 1   110 2   
                                           117 1   7   255 103 2   110 1   103 2   124 1   7   255 17  2   53  1   4   6   53  1   4   6   53  1   4   6   182 1   4   6   182 1   17  2   182 1   17  2   182 1   17  2   53  1   7   255 17  2   53  1   17  2   53  1   7   255 17  2   53  1   17  2   
                                           53  1   7   255 20  2   117 1   19  2   120 1   19  2   120 1   17  2   121 1   17  2   121 1   14  2   120 1   14  2   120 1   13  2   117 1   13  2   117 1   14  2   115 1   14  2   115 1   17  2   114 1   17  2   114 1   19  2   115 1   19  2   115 1   
                                           20  2   117 1   7   255 10  2   117 1   24  2   117 1   7   255 17  2   110 1   17  2   124 1   7   255 20  2   182 1   19  2   184 1   19  2   184 1   17  2   185 1   17  2   185 1   14  2   184 1   14  2   184 1   13  2   182 1   13  2   182 1   14  2   
                                           179 1   14  2   179 1   17  2   178 1   17  2   178 1   19  2   179 1   19  2   179 1   20  2   182 1   7   255 10  2   182 1   24  2   182 1   7   255 17  2   175 1   17  2   189 1   7   255 20  2   53  1   19  2   55  1   19  2   55  1   17  2   56  1   
                                           17  2   56  1   14  2   55  1   14  2   55  1   13  2   53  1   13  2   53  1   14  2   50  1   14  2   50  1   17  2   49  1   17  2   49  1   19  2   50  1   19  2   50  1   20  2   53  1   7   255 10  2   53  1   24  2   53  1   7   255 17  2   46  1   
                                           17  2   60  1   7   255 210 5   117 1   209 5   120 1   209 5   120 1   206 5   121 1   206 5   121 1   204 5   120 1   204 5   120 1   203 5   117 1   203 5   117 1   204 5   115 1   204 5   115 1   206 5   114 1   206 5   114 1   209 5   115 1   209 5   
                                           115 1   210 5   117 1   7   255 199 5   117 1   214 5   117 1   7   255 206 5   110 1   206 5   124 1   7   255 8   6   53  1   7   6   55  1   7   6   55  1   4   6   56  1   4   6   56  1   2   6   55  1   2   6   55  1   1   6   53  1   1   6   53  1   
                                           2   6   50  1   2   6   50  1   4   6   49  1   4   6   49  1   7   6   50  1   7   6   50  1   8   6   53  1   7   255 253 5   53  1   11  6   53  1   7   255 4   6   46  1   4   6   60  1   7   255 8   6   182 1   7   6   184 1   7   6   184 1   4   6   
                                           185 1   4   6   185 1   2   6   184 1   2   6   184 1   1   6   182 1   1   6   182 1   2   6   179 1   2   6   179 1   4   6   178 1   4   6   178 1   7   6   179 1   7   6   179 1   8   6   182 1   7   255 253 5   182 1   11  6   182 1   7   255 4   6   
                                           175 1   4   6   189 1   7   255 14  4   117 1   13  4   120 1   13  4   120 1   11  4   121 1   11  4   121 1   8   4   120 1   8   4   120 1   7   4   117 1   7   4   117 1   8   4   115 1   8   4   115 1   11  4   114 1   11  4   114 1   13  4   115 1   
                                           13  4   115 1   14  4   117 1   7   255 4   4   117 1   18  4   117 1   7   255 11  4   110 1   11  4   124 1   7   255 120 5   90  1   8   6   90  1   8   6   90  1   8   6   106 1   8   6   106 1   63  6   106 1   63  6   106 1   63  6   129 1   63  6   
                                           129 1   8   6   129 1   8   6   129 1   8   6   144 1   8   6   144 1   120 5   144 1   120 5   144 1   120 5   90  1   7   255 120 5   90  1   120 5   90  1   7   255 120 5   90  1   120 5   90  1   7   255 219 5   117 1   218 5   122 1   218 5   122 1   
                                           215 5   126 1   215 5   126 1   211 5   129 1   211 5   129 1   206 5   130 1   206 5   130 1   202 5   129 1   202 5   129 1   198 5   126 1   198 5   126 1   195 5   122 1   195 5   122 1   194 5   117 1   194 5   117 1   195 5   113 1   195 5   113 1   
                                           198 5   109 1   198 5   109 1   202 5   106 1   202 5   106 1   206 5   105 1   206 5   105 1   211 5   106 1   211 5   106 1   215 5   109 1   215 5   109 1   218 5   113 1   218 5   113 1   219 5   117 1   7   255 249 5   98  1   249 5   110 1   249 5   
                                           110 1   254 5   113 1   254 5   113 1   21  6   113 1   21  6   113 1   26  6   110 1   26  6   110 1   26  6   98  1   26  6   98  1   21  6   94  1   21  6   94  1   254 5   94  1   254 5   94  1   249 5   98  1   7   255 249 5   64  1   249 5   76  1   
                                           249 5   76  1   254 5   79  1   254 5   79  1   21  6   79  1   21  6   79  1   26  6   76  1   26  6   76  1   26  6   64  1   26  6   64  1   21  6   60  1   21  6   60  1   254 5   60  1   254 5   60  1   249 5   64  1   7   255 249 5   30  1   249 5   
                                           41  1   249 5   41  1   254 5   45  1   254 5   45  1   21  6   45  1   21  6   45  1   26  6   41  1   26  6   41  1   26  6   30  1   26  6   30  1   21  6   26  1   21  6   26  1   254 5   26  1   254 5   26  1   249 5   30  1   7   255 249 5   125 1   
                                           249 5   137 1   249 5   137 1   254 5   140 1   254 5   140 1   21  6   140 1   21  6   140 1   26  6   137 1   26  6   137 1   26  6   125 1   26  6   125 1   21  6   121 1   21  6   121 1   254 5   121 1   254 5   121 1   249 5   125 1   7   255 249 5   
                                           159 1   249 5   171 1   249 5   171 1   254 5   175 1   254 5   175 1   21  6   175 1   21  6   175 1   26  6   171 1   26  6   171 1   26  6   159 1   26  6   159 1   21  6   156 1   21  6   156 1   254 5   156 1   254 5   156 1   249 5   159 1   7   255 
                                           249 5   193 1   249 5   205 1   249 5   205 1   254 5   209 1   254 5   209 1   21  6   209 1   21  6   209 1   26  6   205 1   26  6   205 1   26  6   193 1   26  6   193 1   21  6   190 1   21  6   190 1   254 5   190 1   254 5   190 1   249 5   193 1   
                                           7   255 47  6   98  1   47  6   110 1   47  6   110 1   52  6   113 1   52  6   113 1   75  6   113 1   75  6   113 1   80  6   110 1   80  6   110 1   80  6   98  1   80  6   98  1   75  6   94  1   75  6   94  1   52  6   94  1   52  6   94  1   47  6   
                                           98  1   7   255 47  6   64  1   47  6   76  1   47  6   76  1   52  6   79  1   52  6   79  1   75  6   79  1   75  6   79  1   80  6   76  1   80  6   76  1   80  6   64  1   80  6   64  1   75  6   60  1   75  6   60  1   52  6   60  1   52  6   60  1   
                                           47  6   64  1   7   255 47  6   30  1   47  6   41  1   47  6   41  1   52  6   45  1   52  6   45  1   75  6   45  1   75  6   45  1   80  6   41  1   80  6   41  1   80  6   30  1   80  6   30  1   75  6   26  1   75  6   26  1   52  6   26  1   52  6   
                                           26  1   47  6   30  1   7   255 47  6   125 1   47  6   137 1   47  6   137 1   52  6   140 1   52  6   140 1   75  6   140 1   75  6   140 1   80  6   137 1   80  6   137 1   80  6   125 1   80  6   125 1   75  6   121 1   75  6   121 1   52  6   121 1   
                                           52  6   121 1   47  6   125 1   7   255 47  6   159 1   47  6   171 1   47  6   171 1   52  6   175 1   52  6   175 1   75  6   175 1   75  6   175 1   80  6   171 1   80  6   171 1   80  6   159 1   80  6   159 1   75  6   156 1   75  6   156 1   52  6   
                                           156 1   52  6   156 1   47  6   159 1   7   255 47  6   193 1   47  6   205 1   47  6   205 1   52  6   209 1   52  6   209 1   75  6   209 1   75  6   209 1   80  6   205 1   80  6   205 1   80  6   193 1   80  6   193 1   75  6   190 1   75  6   190 1   
                                           52  6   190 1   52  6   190 1   47  6   193 1   7   255 40  6   209 1   39  6   211 1   39  6   211 1   37  6   212 1   37  6   212 1   34  6   211 1   34  6   211 1   33  6   209 1   33  6   209 1   34  6   206 1   34  6   206 1   37  6   205 1   37  6   
                                           205 1   39  6   206 1   39  6   206 1   40  6   209 1   7   255 29  6   209 1   44  6   209 1   7   255 37  6   202 1   37  6   216 1   7   255 124 5   209 1   123 5   211 1   123 5   211 1   120 5   212 1   120 5   212 1   118 5   211 1   118 5   211 1   
                                           117 5   209 1   117 5   209 1   118 5   206 1   118 5   206 1   120 5   205 1   120 5   205 1   123 5   206 1   123 5   206 1   124 5   209 1   7   255 113 5   209 1   127 5   209 1   7   255 120 5   202 1   120 5   216 1   7   255 40  6   26  1   39  6   
                                           28  1   39  6   28  1   37  6   30  1   37  6   30  1   34  6   28  1   34  6   28  1   33  6   26  1   33  6   26  1   34  6   23  1   34  6   23  1   37  6   22  1   37  6   22  1   39  6   23  1   39  6   23  1   40  6   26  1   7   255 29  6   26  1   
                                           44  6   26  1   7   255 37  6   19  1   37  6   33  1   7   255 124 5   26  1   123 5   28  1   123 5   28  1   120 5   30  1   120 5   30  1   118 5   28  1   118 5   28  1   117 5   26  1   117 5   26  1   118 5   23  1   118 5   23  1   120 5   22  1   
                                           120 5   22  1   123 5   23  1   123 5   23  1   124 5   26  1   7   255 113 5   26  1   127 5   26  1   7   255 120 5   19  1   120 5   33  1   7   255 210 5   117 1   209 5   120 1   209 5   120 1   206 5   121 1   206 5   121 1   204 5   120 1   204 5   
                                           )) "a")
 (_WriteStream FILE (vl-list->string (list 120 1   203 5   117 1   203 5   117 1   204 5   115 1   204 5   115 1   206 5   114 1   206 5   114 1   209 5   115 1   209 5   115 1   210 5   117 1   7   255 199 5   117 1   214 5   117 1   7   255 206 5   110 1   206 5   124 1   7   255 77  5   30  1   
                                           77  5   41  1   77  5   41  1   82  5   45  1   82  5   45  1   105 5   45  1   105 5   45  1   110 5   41  1   110 5   41  1   110 5   30  1   110 5   30  1   105 5   26  1   105 5   26  1   82  5   26  1   82  5   26  1   77  5   30  1   7   255 77  5   
                                           64  1   77  5   76  1   77  5   76  1   82  5   79  1   82  5   79  1   105 5   79  1   105 5   79  1   110 5   76  1   110 5   76  1   110 5   64  1   110 5   64  1   105 5   60  1   105 5   60  1   82  5   60  1   82  5   60  1   77  5   64  1   7   255 
                                           77  5   98  1   77  5   110 1   77  5   110 1   82  5   113 1   82  5   113 1   105 5   113 1   105 5   113 1   110 5   110 1   110 5   110 1   110 5   98  1   110 5   98  1   105 5   94  1   105 5   94  1   82  5   94  1   82  5   94  1   77  5   98  1   
                                           7   255 77  5   125 1   77  5   137 1   77  5   137 1   82  5   140 1   82  5   140 1   105 5   140 1   105 5   140 1   110 5   137 1   110 5   137 1   110 5   125 1   110 5   125 1   105 5   121 1   105 5   121 1   82  5   121 1   82  5   121 1   77  5   
                                           125 1   7   255 77  5   159 1   77  5   171 1   77  5   171 1   82  5   175 1   82  5   175 1   105 5   175 1   105 5   175 1   110 5   171 1   110 5   171 1   110 5   159 1   110 5   159 1   105 5   156 1   105 5   156 1   82  5   156 1   82  5   156 1   
                                           77  5   159 1   7   255 77  5   193 1   77  5   205 1   77  5   205 1   82  5   209 1   82  5   209 1   105 5   209 1   105 5   209 1   110 5   205 1   110 5   205 1   110 5   193 1   110 5   193 1   105 5   190 1   105 5   190 1   82  5   190 1   82  5   
                                           190 1   77  5   193 1   7   255 131 5   30  1   131 5   41  1   131 5   41  1   136 5   45  1   136 5   45  1   159 5   45  1   159 5   45  1   163 5   41  1   163 5   41  1   163 5   30  1   163 5   30  1   159 5   26  1   159 5   26  1   136 5   26  1   
                                           136 5   26  1   131 5   30  1   7   255 131 5   64  1   131 5   76  1   131 5   76  1   136 5   79  1   136 5   79  1   159 5   79  1   159 5   79  1   163 5   76  1   163 5   76  1   163 5   64  1   163 5   64  1   159 5   60  1   159 5   60  1   136 5   
                                           60  1   136 5   60  1   131 5   64  1   7   255 131 5   98  1   131 5   110 1   131 5   110 1   136 5   113 1   136 5   113 1   159 5   113 1   159 5   113 1   163 5   110 1   163 5   110 1   163 5   98  1   163 5   98  1   159 5   94  1   159 5   94  1   
                                           136 5   94  1   136 5   94  1   131 5   98  1   7   255 131 5   125 1   131 5   137 1   131 5   137 1   136 5   140 1   136 5   140 1   159 5   140 1   159 5   140 1   163 5   137 1   163 5   137 1   163 5   125 1   163 5   125 1   159 5   121 1   159 5   
                                           121 1   136 5   121 1   136 5   121 1   131 5   125 1   7   255 131 5   159 1   131 5   171 1   131 5   171 1   136 5   175 1   136 5   175 1   159 5   175 1   159 5   175 1   163 5   171 1   163 5   171 1   163 5   159 1   163 5   159 1   159 5   156 1   
                                           159 5   156 1   136 5   156 1   136 5   156 1   131 5   159 1   7   255 131 5   193 1   131 5   205 1   131 5   205 1   136 5   209 1   136 5   209 1   159 5   209 1   159 5   209 1   163 5   205 1   163 5   205 1   163 5   193 1   163 5   193 1   159 5   
                                           190 1   159 5   190 1   136 5   190 1   136 5   190 1   131 5   193 1   0   252 65  117 116 111 67  65  68  32  83  108 105 100 101 13  10  26  0   86  2   73  6   247 2   97  120 67  1   2   0   52  18  7   255 7   255 72  6   155 1   69  6   148 1   69  
                                           6   148 1   65  6   137 1   65  6   137 1   65  6   120 1   65  6   120 1   69  6   109 1   69  6   109 1   72  6   102 1   51  255 51  255 88  1   32  1   227 4   32  1   227 4   32  1   227 4   225 1   227 4   225 1   88  1   225 1   88  1   225 1   88  
                                           1   32  1   7   255 7   255 88  1   32  1   227 4   32  1   227 4   32  1   227 4   225 1   7   255 227 4   225 1   88  1   225 1   7   255 88  1   225 1   88  1   32  1   7   255 88  1   32  1   88  1   32  1   7   255 88  1   32  1   88  1   32  1   7   
                                           255 88  1   32  1   88  1   32  1   7   255 8   4   36  1   8   4   48  1   8   4   48  1   18  4   51  1   18  4   51  1   72  4   51  1   72  4   51  1   83  4   48  1   83  4   48  1   83  4   36  1   83  4   36  1   72  4   32  1   72  4   32  1   18  
                                           4   32  1   18  4   32  1   8   4   36  1   7   255 8   4   209 1   8   4   221 1   8   4   221 1   18  4   225 1   18  4   225 1   72  4   225 1   72  4   225 1   83  4   221 1   83  4   221 1   83  4   209 1   83  4   209 1   72  4   206 1   72  4   206 
                                           1   18  4   206 1   18  4   206 1   8   4   209 1   7   255 90  1   32  1   90  1   34  1   90  1   34  1   88  1   35  1   88  1   35  1   87  1   34  1   87  1   34  1   86  1   32  1   86  1   32  1   87  1   31  1   87  1   31  1   88  1   30  1   88  
                                           1   30  1   90  1   31  1   90  1   31  1   90  1   32  1   7   255 84  1   32  1   93  1   32  1   7   255 88  1   28  1   88  1   37  1   7   255 229 4   32  1   228 4   34  1   228 4   34  1   227 4   35  1   227 4   35  1   225 4   34  1   225 4   34  
                                           1   224 4   32  1   224 4   32  1   225 4   31  1   225 4   31  1   227 4   30  1   227 4   30  1   228 4   31  1   228 4   31  1   229 4   32  1   7   255 222 4   32  1   231 4   32  1   7   255 227 4   28  1   227 4   37  1   7   255 90  1   225 1   90  
                                           1   226 1   90  1   226 1   88  1   227 1   88  1   227 1   87  1   226 1   87  1   226 1   86  1   225 1   86  1   225 1   87  1   223 1   87  1   223 1   88  1   222 1   88  1   222 1   90  1   223 1   90  1   223 1   90  1   225 1   7   255 84  1   225 
                                           1   93  1   225 1   7   255 88  1   220 1   88  1   229 1   7   255 229 4   225 1   228 4   226 1   228 4   226 1   227 4   227 1   227 4   227 1   225 4   226 1   225 4   226 1   224 4   225 1   224 4   225 1   225 4   223 1   225 4   223 1   227 4   222 
                                           1   227 4   222 1   228 4   223 1   228 4   223 1   229 4   225 1   7   255 222 4   225 1   231 4   225 1   7   255 227 4   220 1   227 4   229 1   7   255 249 1   225 1   248 1   226 1   248 1   226 1   247 1   227 1   247 1   227 1   245 1   226 1   245 
                                           1   226 1   245 1   225 1   245 1   225 1   245 1   223 1   245 1   223 1   247 1   222 1   247 1   222 1   248 1   223 1   248 1   223 1   249 1   225 1   7   255 242 1   225 1   251 1   225 1   7   255 247 1   220 1   247 1   229 1   7   255 48  4   225 
                                           1   47  4   226 1   47  4   226 1   45  4   227 1   45  4   227 1   44  4   226 1   44  4   226 1   43  4   225 1   43  4   225 1   44  4   223 1   44  4   223 1   45  4   222 1   45  4   222 1   47  4   223 1   47  4   223 1   48  4   225 1   7   255 41  
                                           4   225 1   50  4   225 1   7   255 45  4   220 1   45  4   229 1   7   255 48  4   32  1   47  4   34  1   47  4   34  1   45  4   35  1   45  4   35  1   44  4   34  1   44  4   34  1   43  4   32  1   43  4   32  1   44  4   31  1   44  4   31  1   45  
                                           4   30  1   45  4   30  1   47  4   31  1   47  4   31  1   48  4   32  1   7   255 41  4   32  1   50  4   32  1   7   255 45  4   28  1   45  4   37  1   7   255 249 1   32  1   248 1   34  1   248 1   34  1   247 1   35  1   247 1   35  1   245 1   34  
                                           1   245 1   34  1   245 1   32  1   245 1   32  1   245 1   31  1   245 1   31  1   247 1   30  1   247 1   30  1   248 1   31  1   248 1   31  1   249 1   32  1   7   255 242 1   32  1   251 1   32  1   7   255 247 1   28  1   247 1   37  1   7   255 249 
                                           1   129 1   248 1   130 1   248 1   130 1   247 1   131 1   247 1   131 1   245 1   130 1   245 1   130 1   245 1   129 1   245 1   129 1   245 1   127 1   245 1   127 1   247 1   126 1   247 1   126 1   248 1   127 1   248 1   127 1   249 1   129 1   7   
                                           255 242 1   129 1   251 1   129 1   7   255 247 1   124 1   247 1   133 1   7   255 209 1   36  1   209 1   48  1   209 1   48  1   220 1   51  1   220 1   51  1   18  2   51  1   18  2   51  1   29  2   48  1   29  2   48  1   29  2   36  1   29  2   36  
                                           1   18  2   32  1   18  2   32  1   220 1   32  1   220 1   32  1   209 1   36  1   7   255 209 1   209 1   209 1   221 1   209 1   221 1   220 1   225 1   220 1   225 1   18  2   225 1   18  2   225 1   29  2   221 1   29  2   221 1   29  2   209 1   29  
                                           2   209 1   18  2   206 1   18  2   206 1   220 1   206 1   220 1   206 1   209 1   209 1   0   252 
                                           )) "a")
)
