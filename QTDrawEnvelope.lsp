;
;
;     Program written by Robert Livingston, 2015-11-13
;
;     QT:DRAWENVELOPE draws the vehicle envelope
;
;
(defun QT:DRAWENVELOPE (/ ANG1 ANG2 BLOCKNAME C C2 CECOLOR COLOR ENT ENTLIST ENTLISTNEW GETBLOCKNAME
                          NODE P P1 P2 PA PB PC PD TMP VINC VLIST)

 (defun GETBLOCKNAME (/ C)
  (setq C 1)
  (while (/= nil (tblsearch "BLOCK" (strcat "QTENVELOPE" (itoa C))))
   (setq C (+ C 1))
  )
  (strcat "QTENVELOPE" (itoa C))
 )
 (setq ENTLISTNEW (list (list (cons 0 "BLOCK")
                              (cons 2 "*U")
                              (cons 8 "0")
                              (cons 70 1)
                              (list 10 0.0 0.0 0.0)
                        )
                  )
 )
    
 (setq VINC 1)
 (setq CECOLOR (getvar "CECOLOR"))
 (setvar "OSMODE" 0)
 (setq COLOR (getint "\nEnter colour for block (0-256, 0=ByBlock, 256=ByLayer) <0> : "))
 (if (= nil COLOR) (setq COLOR 0))
 (if (or (< COLOR 0) (> COLOR 256)) (setq COLOR 0))
 (setvar "CECOLOR" (itoa COLOR))
 (foreach NODE QTVLIST
  (progn
   (setq ENT (car NODE))
   (setq VLIST (QT:GETENVELOPE ENT))
   (if (/= nil VLIST)
    (progn
     (setq C 0)
     (while (< C CMAX)
      (setq ANG1 (nth C (nth 1 NODE)))
      (setq P1 (nth C (nth 2 NODE)))
      (setq ANG2 (nth (min (+ C VINC) CMAX) (nth 1 NODE)))
      (setq P2 (nth (min (+ C VINC) CMAX) (nth 2 NODE)))
      (setq C2 0)
      (while (< C2 (length VLIST))
       (setq P (nth C2 VLIST))
       (setq PA (list (+ (nth 0 P1) (* (nth 0 P) (cos ANG1)) (* -1.0 (nth 1 P) (sin ANG1)))
                      (+ (nth 1 P1) (* (nth 0 P) (sin ANG1)) (* (nth 1 P) (cos ANG1)))))
       (setq PC (list (+ (nth 0 P2) (* (nth 0 P) (cos ANG2)) (* -1.0 (nth 1 P) (sin ANG2)))
                      (+ (nth 1 P2) (* (nth 0 P) (sin ANG2)) (* (nth 1 P) (cos ANG2)))))
       (if (= C2 (- (length VLIST) 1))
        (setq P (nth 0 VLIST))
        (setq P (nth (+ C2 1) VLIST))
       )
       (setq PB (list (+ (nth 0 P1) (* (nth 0 P) (cos ANG1)) (* -1.0 (nth 1 P) (sin ANG1)))
                      (+ (nth 1 P1) (* (nth 0 P) (sin ANG1)) (* (nth 1 P) (cos ANG1)))))
       (setq PD (list (+ (nth 0 P2) (* (nth 0 P) (cos ANG2)) (* -1.0 (nth 1 P) (sin ANG2)))
                      (+ (nth 1 P2) (* (nth 0 P) (sin ANG2)) (* (nth 1 P) (cos ANG2)))))
       (setq ENTLISTNEW (append ENTLISTNEW
                               (list (list (cons 0 "SOLID")
                                           (cons 8 "0")
                                           (list 10 (car PA) (cadr PA) 0.0)
                                           (list 11 (car PB) (cadr PB) 0.0)
                                           (list 12 (car PC) (cadr PC) 0.0)
                                           (list 13 (car PD) (cadr PD) 0.0)
                                     )
                               )
                        )
       )
       (setq C2 (+ C2 1))
      )
      (setq C (+ C VINC))
     )
    )
   )
  )
 )
 (setq ENTLISTNEW (append ENTLISTNEW (list (list (cons 0 "ENDBLK")))))
 (entmake)
 (foreach NODE ENTLISTNEW
  (setq TMP (entmake NODE))
 )
 (entmake (list (cons 0 "INSERT")
                (cons 2 TMP)
                (list 10 0.0 0.0 0.0)
                (cons 41 1.0)
                (cons 42 1.0)
                (cons 43 1.0)
                (cons 50 0.0)
          )
 )
 (command-s "._DRAWORDER" (entlast) "" "BACK")
 (setvar "CECOLOR" CECOLOR)
 (setvar "OSMODE" OSMODE)
)
