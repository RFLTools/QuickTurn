(defun QT:MAKE (BLKNAME / )
 (cond
       ((= (strcase BLKNAME) (strcase "TRANSLINK-2013-TRAINBUS"))
        (progn
         (entmake)
         (entmake
          (list
           (cons 0 "BLOCK")
           (cons 2 "TRANSLINK-2013-TRAINBUS")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 13.71 -1.3)
           (cons 40 0)
           (cons 41 0)
           (cons 42 0)
           (cons 91 0)
           (list 10 13.71 1.3)
           (cons 40 0)
           (cons 41 0)
           (cons 42 0)
           (cons 91 0)
           (list 10 0 1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.262 -1.252248)
           (cons 40 0)
           (cons 41 0)
           (cons 42 0)
           (cons 91 0)
           (list 10 9.262 -1.093752)
           (cons 40 0)
           (cons 41 0)
           (cons 42 0)
           (cons 91 0)
           (list 10 9.40424 -1.046)
           (cons 40 0)
           (cons 41 0)
           (cons 42 0)
           (cons 91 0)
           (list 10 10.13576 -1.046)
           (cons 40 0)
           (cons 41 0)
           (cons 42 0)
           (cons 91 0)
           (list 10 10.278 -1.093752)
           (cons 40 0)
           (cons 41 0)
           (cons 42 0)
           (cons 91 0)
           (list 10 10.278 -1.252248)
           (cons 40 0)
           (cons 41 0)
           (cons 42 0)
           (cons 91 0)
           (list 10 10.13576 -1.3)
           (cons 40 0)
           (cons 41 0)
           (cons 42 0)
           (cons 91 0)
           (list 10 9.40424 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.262 1.093752)
           (cons 40 0)
           (cons 41 0)
           (cons 42 0)
           (cons 91 0)
           (list 10 9.262 1.252248)
           (cons 40 0)
           (cons 41 0)
           (cons 42 0)
           (cons 91 0)
           (list 10 9.40424 1.3)
           (cons 40 0)
           (cons 41 0)
           (cons 42 0)
           (cons 91 0)
           (list 10 10.13576 1.3)
           (cons 40 0)
           (cons 41 0)
           (cons 42 0)
           (cons 91 0)
           (list 10 10.278 1.252248)
           (cons 40 0)
           (cons 41 0)
           (cons 42 0)
           (cons 91 0)
           (list 10 10.278 1.093752)
           (cons 40 0)
           (cons 41 0)
           (cons 42 0)
           (cons 91 0)
           (list 10 10.13576 1.046)
           (cons 40 0)
           (cons 41 0)
           (cons 42 0)
           (cons 91 0)
           (list 10 9.40424 1.046)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 13.71 1.3 0)
           (cons 50 0)
          )
         )
         (entmake
          (list
           (cons 0 "POINT")
           (cons 100 "AcDbEntity")
           (cons 67 0)
           (cons 8 "0")
           (cons 100 "AcDbPoint")
           (list 10 13.71 -1.3 0)
           (cons 50 0)
          )
         )
         (entmake
          (list
           (cons 0 "POINT")
           (cons 100 "AcDbEntity")
           (cons 67 0)
           (cons 8 "0")
           (cons 100 "AcDbPoint")
           (list 10 1.8 0 0)
           (cons 50 0)
          )
         )
         (entmake
          (list
           (cons 0 "POINT")
           (cons 100 "AcDbEntity")
           (cons 67 0)
           (cons 8 "0")
           (cons 100 "AcDbPoint")
           (list 10 1.8 1.3 0)
           (cons 50 0)
          )
         )
         (entmake
          (list
           (cons 0 "POINT")
           (cons 100 "AcDbEntity")
           (cons 67 0)
           (cons 8 "0")
           (cons 100 "AcDbPoint")
           (list 10 1.8 -1.3 0)
           (cons 50 0)
          )
         )
         (entmake
          (list
           (cons 0 "INSERT")
           (cons 100 "AcDbEntity")
           (cons 67 0)
           (cons 8 "0")
           (cons 100 "AcDbBlockReference")
           (cons 2 "WheelLeftM2")
           (list 10 1.8 -1.046 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM2")
           (list 10 1.8 1.046 0)
           (cons 41 1)
           (cons 42 1)
           (cons 43 1)
           (cons 50 0)
           (cons 70 0)
           (cons 71 0)
           (cons 44 0)
           (cons 45 0)
          )
         )
         (entmake
          (list
           (cons 0 "LINE")
           (cons 100 "AcDbEntity")
           (cons 67 0)
           (cons 8 "0")
           (cons 100 "AcDbLine")
           (list 10 0 -1.3 0)
           (list 11 0 1.3 0)
          )
         )
         (entmake
          (list
           (cons 0 "LINE")
           (cons 100 "AcDbEntity")
           (cons 67 0)
           (cons 8 "0")
           (cons 100 "AcDbLine")
           (list 10 0.2 1.3 0)
           (list 11 0.2 1.2 0)
          )
         )
         (entmake
          (list
           (cons 0 "LINE")
           (cons 100 "AcDbEntity")
           (cons 67 0)
           (cons 8 "0")
           (cons 100 "AcDbLine")
           (list 10 0.2 1.2 0)
           (list 11 1.1 1.2 0)
          )
         )
         (entmake
          (list
           (cons 0 "LINE")
           (cons 100 "AcDbEntity")
           (cons 67 0)
           (cons 8 "0")
           (cons 100 "AcDbLine")
           (list 10 1.1 1.2 0)
           (list 11 1.1 1.3 0)
          )
         )
         (entmake
          (list
           (cons 0 "LWPOLYLINE")
           (cons 100 "AcDbEntity")
           (cons 67 0)
           (cons 8 "0")
           (cons 100 "AcDbPolyline")
           (cons 90 6)
           (cons 70 128)
           (cons 43 0)
           (cons 38 0)
           (cons 39 0)
           (list 10 0 -1.3)
           (cons 40 0)
           (cons 41 0)
           (cons 42 0)
           (cons 91 0)
           (list 10 13.71 -1.3)
           (cons 40 0)
           (cons 41 0)
           (cons 42 0)
           (cons 91 0)
           (list 10 13.71 1.3)
           (cons 40 0)
           (cons 41 0)
           (cons 42 0)
           (cons 91 0)
           (list 10 0 1.3)
           (cons 40 0)
           (cons 41 0)
           (cons 42 0)
           (cons 91 0)
           (list 10 0 -1.3)
           (cons 40 0)
           (cons 41 0)
           (cons 42 0)
           (cons 91 0)
           (list 10 0 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.262 0.693752)
           (cons 40 0)
           (cons 41 0)
           (cons 42 0)
           (cons 91 0)
           (list 10 9.262 0.852248)
           (cons 40 0)
           (cons 41 0)
           (cons 42 0)
           (cons 91 0)
           (list 10 9.40424 0.9)
           (cons 40 0)
           (cons 41 0)
           (cons 42 0)
           (cons 91 0)
           (list 10 10.13576 0.9)
           (cons 40 0)
           (cons 41 0)
           (cons 42 0)
           (cons 91 0)
           (list 10 10.278 0.852248)
           (cons 40 0)
           (cons 41 0)
           (cons 42 0)
           (cons 91 0)
           (list 10 10.278 0.693752)
           (cons 40 0)
           (cons 41 0)
           (cons 42 0)
           (cons 91 0)
           (list 10 10.13576 0.646)
           (cons 40 0)
           (cons 41 0)
           (cons 42 0)
           (cons 91 0)
           (list 10 9.40424 0.646)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.262 -0.852248)
           (cons 40 0)
           (cons 41 0)
           (cons 42 0)
           (cons 91 0)
           (list 10 9.262 -0.693752)
           (cons 40 0)
           (cons 41 0)
           (cons 42 0)
           (cons 91 0)
           (list 10 9.40424 -0.646)
           (cons 40 0)
           (cons 41 0)
           (cons 42 0)
           (cons 91 0)
           (list 10 10.13576 -0.646)
           (cons 40 0)
           (cons 41 0)
           (cons 42 0)
           (cons 91 0)
           (list 10 10.278 -0.693752)
           (cons 40 0)
           (cons 41 0)
           (cons 42 0)
           (cons 91 0)
           (list 10 10.278 -0.852248)
           (cons 40 0)
           (cons 41 0)
           (cons 42 0)
           (cons 91 0)
           (list 10 10.13576 -0.9)
           (cons 40 0)
           (cons 41 0)
           (cons 42 0)
           (cons 91 0)
           (list 10 9.40424 -0.9)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.472 -1.252248)
           (cons 40 0)
           (cons 41 0)
           (cons 42 0)
           (cons 91 0)
           (list 10 10.472 -1.093752)
           (cons 40 0)
           (cons 41 0)
           (cons 42 0)
           (cons 91 0)
           (list 10 10.61424 -1.046)
           (cons 40 0)
           (cons 41 0)
           (cons 42 0)
           (cons 91 0)
           (list 10 11.34576 -1.046)
           (cons 40 0)
           (cons 41 0)
           (cons 42 0)
           (cons 91 0)
           (list 10 11.488 -1.093752)
           (cons 40 0)
           (cons 41 0)
           (cons 42 0)
           (cons 91 0)
           (list 10 11.488 -1.252248)
           (cons 40 0)
           (cons 41 0)
           (cons 42 0)
           (cons 91 0)
           (list 10 11.34576 -1.3)
           (cons 40 0)
           (cons 41 0)
           (cons 42 0)
           (cons 91 0)
           (list 10 10.61424 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.472 1.093752)
           (cons 40 0)
           (cons 41 0)
           (cons 42 0)
           (cons 91 0)
           (list 10 10.472 1.252248)
           (cons 40 0)
           (cons 41 0)
           (cons 42 0)
           (cons 91 0)
           (list 10 10.61424 1.3)
           (cons 40 0)
           (cons 41 0)
           (cons 42 0)
           (cons 91 0)
           (list 10 11.34576 1.3)
           (cons 40 0)
           (cons 41 0)
           (cons 42 0)
           (cons 91 0)
           (list 10 11.488 1.252248)
           (cons 40 0)
           (cons 41 0)
           (cons 42 0)
           (cons 91 0)
           (list 10 11.488 1.093752)
           (cons 40 0)
           (cons 41 0)
           (cons 42 0)
           (cons 91 0)
           (list 10 11.34576 1.046)
           (cons 40 0)
           (cons 41 0)
           (cons 42 0)
           (cons 91 0)
           (list 10 10.61424 1.046)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 10.375 1.3 0)
           (cons 50 0)
          )
         )
         (entmake
          (list
           (cons 0 "POINT")
           (cons 100 "AcDbEntity")
           (cons 67 0)
           (cons 8 "0")
           (cons 100 "AcDbPoint")
           (list 10 10.375 -1.3 0)
           (cons 50 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.472 0.693752)
           (cons 40 0)
           (cons 41 0)
           (cons 42 0)
           (cons 91 0)
           (list 10 10.472 0.852248)
           (cons 40 0)
           (cons 41 0)
           (cons 42 0)
           (cons 91 0)
           (list 10 10.61424 0.9)
           (cons 40 0)
           (cons 41 0)
           (cons 42 0)
           (cons 91 0)
           (list 10 11.34576 0.9)
           (cons 40 0)
           (cons 41 0)
           (cons 42 0)
           (cons 91 0)
           (list 10 11.488 0.852248)
           (cons 40 0)
           (cons 41 0)
           (cons 42 0)
           (cons 91 0)
           (list 10 11.488 0.693752)
           (cons 40 0)
           (cons 41 0)
           (cons 42 0)
           (cons 91 0)
           (list 10 11.34576 0.646)
           (cons 40 0)
           (cons 41 0)
           (cons 42 0)
           (cons 91 0)
           (list 10 10.61424 0.646)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.472 -0.852248)
           (cons 40 0)
           (cons 41 0)
           (cons 42 0)
           (cons 91 0)
           (list 10 10.472 -0.693752)
           (cons 40 0)
           (cons 41 0)
           (cons 42 0)
           (cons 91 0)
           (list 10 10.61424 -0.646)
           (cons 40 0)
           (cons 41 0)
           (cons 42 0)
           (cons 91 0)
           (list 10 11.34576 -0.646)
           (cons 40 0)
           (cons 41 0)
           (cons 42 0)
           (cons 91 0)
           (list 10 11.488 -0.693752)
           (cons 40 0)
           (cons 41 0)
           (cons 42 0)
           (cons 91 0)
           (list 10 11.488 -0.852248)
           (cons 40 0)
           (cons 41 0)
           (cons 42 0)
           (cons 91 0)
           (list 10 11.34576 -0.9)
           (cons 40 0)
           (cons 41 0)
           (cons 42 0)
           (cons 91 0)
           (list 10 10.61424 -0.9)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 1.1 0.56666667 0)
           (cons 40 0.2)
           (cons 1 "1.800")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.1 0.23333333 0)
           (cons 40 0.2)
           (cons 1 "1.800")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.1 -0.1 0)
           (cons 40 0.2)
           (cons 1 "10.375")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.1 -0.76666667 0)
           (cons 40 0.2)
           (cons 1 "46.986")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.1 -0.43333333 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake (list (cons 0 "ENDBLK")))
        )
       )
       ((= (strcase BLKNAME) (strcase "TRANSLINK-2013-HANDYDART"))
        (progn
         (entmake)
         (entmake
          (list
           (cons 0 "BLOCK")
           (cons 2 "TRANSLINK-2013-HANDYDART")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.2)
           (cons 40 0)
           (cons 41 0)
           (cons 42 0)
           (cons 91 0)
           (list 10 8.08 -1.2)
           (cons 40 0)
           (cons 41 0)
           (cons 42 0)
           (cons 91 0)
           (list 10 8.08 1.2)
           (cons 40 0)
           (cons 41 0)
           (cons 42 0)
           (cons 91 0)
           (list 10 0 1.2)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.08 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.08 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.072 -1.152248)
           (cons 40 0)
           (cons 41 0)
           (cons 42 0)
           (cons 91 0)
           (list 10 5.072 -0.993752)
           (cons 40 0)
           (cons 41 0)
           (cons 42 0)
           (cons 91 0)
           (list 10 5.21424 -0.946)
           (cons 40 0)
           (cons 41 0)
           (cons 42 0)
           (cons 91 0)
           (list 10 5.94576 -0.946)
           (cons 40 0)
           (cons 41 0)
           (cons 42 0)
           (cons 91 0)
           (list 10 6.088 -0.993752)
           (cons 40 0)
           (cons 41 0)
           (cons 42 0)
           (cons 91 0)
           (list 10 6.088 -1.152248)
           (cons 40 0)
           (cons 41 0)
           (cons 42 0)
           (cons 91 0)
           (list 10 5.94576 -1.2)
           (cons 40 0)
           (cons 41 0)
           (cons 42 0)
           (cons 91 0)
           (list 10 5.21424 -1.2)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.072 0.993752)
           (cons 40 0)
           (cons 41 0)
           (cons 42 0)
           (cons 91 0)
           (list 10 5.072 1.152248)
           (cons 40 0)
           (cons 41 0)
           (cons 42 0)
           (cons 91 0)
           (list 10 5.21424 1.2)
           (cons 40 0)
           (cons 41 0)
           (cons 42 0)
           (cons 91 0)
           (list 10 5.94576 1.2)
           (cons 40 0)
           (cons 41 0)
           (cons 42 0)
           (cons 91 0)
           (list 10 6.088 1.152248)
           (cons 40 0)
           (cons 41 0)
           (cons 42 0)
           (cons 91 0)
           (list 10 6.088 0.993752)
           (cons 40 0)
           (cons 41 0)
           (cons 42 0)
           (cons 91 0)
           (list 10 5.94576 0.946)
           (cons 40 0)
           (cons 41 0)
           (cons 42 0)
           (cons 91 0)
           (list 10 5.21424 0.946)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -1.2 0)
           (cons 50 0)
          )
         )
         (entmake
          (list
           (cons 0 "POINT")
           (cons 100 "AcDbEntity")
           (cons 67 0)
           (cons 8 "0")
           (cons 100 "AcDbPoint")
           (list 10 0 1.2 0)
           (cons 50 0)
          )
         )
         (entmake
          (list
           (cons 0 "POINT")
           (cons 100 "AcDbEntity")
           (cons 67 0)
           (cons 8 "0")
           (cons 100 "AcDbPoint")
           (list 10 8.08 1.2 0)
           (cons 50 0)
          )
         )
         (entmake
          (list
           (cons 0 "POINT")
           (cons 100 "AcDbEntity")
           (cons 67 0)
           (cons 8 "0")
           (cons 100 "AcDbPoint")
           (list 10 8.08 -1.2 0)
           (cons 50 0)
          )
         )
         (entmake
          (list
           (cons 0 "POINT")
           (cons 100 "AcDbEntity")
           (cons 67 0)
           (cons 8 "0")
           (cons 100 "AcDbPoint")
           (list 10 0.88 0 0)
           (cons 50 0)
          )
         )
         (entmake
          (list
           (cons 0 "POINT")
           (cons 100 "AcDbEntity")
           (cons 67 0)
           (cons 8 "0")
           (cons 100 "AcDbPoint")
           (list 10 0.88 1.2 0)
           (cons 50 0)
          )
         )
         (entmake
          (list
           (cons 0 "POINT")
           (cons 100 "AcDbEntity")
           (cons 67 0)
           (cons 8 "0")
           (cons 100 "AcDbPoint")
           (list 10 5.58 1.2 0)
           (cons 50 0)
          )
         )
         (entmake
          (list
           (cons 0 "POINT")
           (cons 100 "AcDbEntity")
           (cons 67 0)
           (cons 8 "0")
           (cons 100 "AcDbPoint")
           (list 10 5.58 -1.2 0)
           (cons 50 0)
          )
         )
         (entmake
          (list
           (cons 0 "POINT")
           (cons 100 "AcDbEntity")
           (cons 67 0)
           (cons 8 "0")
           (cons 100 "AcDbPoint")
           (list 10 0.88 -1.2 0)
           (cons 50 0)
          )
         )
         (entmake
          (list
           (cons 0 "INSERT")
           (cons 100 "AcDbEntity")
           (cons 67 0)
           (cons 8 "0")
           (cons 100 "AcDbBlockReference")
           (cons 2 "WheelLeftM2")
           (list 10 0.88 -0.946 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM2")
           (list 10 0.88 0.946 0)
           (cons 41 1)
           (cons 42 1)
           (cons 43 1)
           (cons 50 0)
           (cons 70 0)
           (cons 71 0)
           (cons 44 0)
           (cons 45 0)
          )
         )
         (entmake
          (list
           (cons 0 "LINE")
           (cons 100 "AcDbEntity")
           (cons 67 0)
           (cons 8 "0")
           (cons 100 "AcDbLine")
           (list 10 0 -1.2 0)
           (list 11 0 1.2 0)
          )
         )
         (entmake
          (list
           (cons 0 "LINE")
           (cons 100 "AcDbEntity")
           (cons 67 0)
           (cons 8 "0")
           (cons 100 "AcDbLine")
           (list 10 2 1.2 0)
           (list 11 2 1.1 0)
          )
         )
         (entmake
          (list
           (cons 0 "LINE")
           (cons 100 "AcDbEntity")
           (cons 67 0)
           (cons 8 "0")
           (cons 100 "AcDbLine")
           (list 10 2 1.1 0)
           (list 11 3 1.1 0)
          )
         )
         (entmake
          (list
           (cons 0 "LINE")
           (cons 100 "AcDbEntity")
           (cons 67 0)
           (cons 8 "0")
           (cons 100 "AcDbLine")
           (list 10 3 1.1 0)
           (list 11 3 1.2 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.072 0.593752)
           (cons 40 0)
           (cons 41 0)
           (cons 42 0)
           (cons 91 0)
           (list 10 5.072 0.752248)
           (cons 40 0)
           (cons 41 0)
           (cons 42 0)
           (cons 91 0)
           (list 10 5.21424 0.8)
           (cons 40 0)
           (cons 41 0)
           (cons 42 0)
           (cons 91 0)
           (list 10 5.94576 0.8)
           (cons 40 0)
           (cons 41 0)
           (cons 42 0)
           (cons 91 0)
           (list 10 6.088 0.752248)
           (cons 40 0)
           (cons 41 0)
           (cons 42 0)
           (cons 91 0)
           (list 10 6.088 0.593752)
           (cons 40 0)
           (cons 41 0)
           (cons 42 0)
           (cons 91 0)
           (list 10 5.94576 0.546)
           (cons 40 0)
           (cons 41 0)
           (cons 42 0)
           (cons 91 0)
           (list 10 5.21424 0.546)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.072 -0.752248)
           (cons 40 0)
           (cons 41 0)
           (cons 42 0)
           (cons 91 0)
           (list 10 5.072 -0.593752)
           (cons 40 0)
           (cons 41 0)
           (cons 42 0)
           (cons 91 0)
           (list 10 5.21424 -0.546)
           (cons 40 0)
           (cons 41 0)
           (cons 42 0)
           (cons 91 0)
           (list 10 5.94576 -0.546)
           (cons 40 0)
           (cons 41 0)
           (cons 42 0)
           (cons 91 0)
           (list 10 6.088 -0.593752)
           (cons 40 0)
           (cons 41 0)
           (cons 42 0)
           (cons 91 0)
           (list 10 6.088 -0.752248)
           (cons 40 0)
           (cons 41 0)
           (cons 42 0)
           (cons 91 0)
           (list 10 5.94576 -0.8)
           (cons 40 0)
           (cons 41 0)
           (cons 42 0)
           (cons 91 0)
           (list 10 5.21424 -0.8)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.18 0.56666667 0)
           (cons 40 0.2)
           (cons 1 "0.880")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.18 0.23333333 0)
           (cons 40 0.2)
           (cons 1 "0.880")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.18 -0.1 0)
           (cons 40 0.2)
           (cons 1 "5.580")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.18 -0.43333333 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.18 -0.76666667 0)
           (cons 40 0.2)
           (cons 1 "38.126")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "TRANSLINK-2013-COMMUNITY-SHUTTLE"))
        (progn
         (entmake)
         (entmake
          (list
           (cons 0 "BLOCK")
           (cons 2 "TRANSLINK-2013-COMMUNITY-SHUTTLE")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.2)
           (cons 40 0)
           (cons 41 0)
           (cons 42 0)
           (cons 91 0)
           (list 10 8.2 -1.2)
           (cons 40 0)
           (cons 41 0)
           (cons 42 0)
           (cons 91 0)
           (list 10 8.2 1.2)
           (cons 40 0)
           (cons 41 0)
           (cons 42 0)
           (cons 91 0)
           (list 10 0 1.2)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.2 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.2 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.352 -1.152248)
           (cons 40 0)
           (cons 41 0)
           (cons 42 0)
           (cons 91 0)
           (list 10 5.352 -0.993752)
           (cons 40 0)
           (cons 41 0)
           (cons 42 0)
           (cons 91 0)
           (list 10 5.49424 -0.946)
           (cons 40 0)
           (cons 41 0)
           (cons 42 0)
           (cons 91 0)
           (list 10 6.22576 -0.946)
           (cons 40 0)
           (cons 41 0)
           (cons 42 0)
           (cons 91 0)
           (list 10 6.368 -0.993752)
           (cons 40 0)
           (cons 41 0)
           (cons 42 0)
           (cons 91 0)
           (list 10 6.368 -1.152248)
           (cons 40 0)
           (cons 41 0)
           (cons 42 0)
           (cons 91 0)
           (list 10 6.22576 -1.2)
           (cons 40 0)
           (cons 41 0)
           (cons 42 0)
           (cons 91 0)
           (list 10 5.49424 -1.2)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.352 0.993752)
           (cons 40 0)
           (cons 41 0)
           (cons 42 0)
           (cons 91 0)
           (list 10 5.352 1.152248)
           (cons 40 0)
           (cons 41 0)
           (cons 42 0)
           (cons 91 0)
           (list 10 5.49424 1.2)
           (cons 40 0)
           (cons 41 0)
           (cons 42 0)
           (cons 91 0)
           (list 10 6.22576 1.2)
           (cons 40 0)
           (cons 41 0)
           (cons 42 0)
           (cons 91 0)
           (list 10 6.368 1.152248)
           (cons 40 0)
           (cons 41 0)
           (cons 42 0)
           (cons 91 0)
           (list 10 6.368 0.993752)
           (cons 40 0)
           (cons 41 0)
           (cons 42 0)
           (cons 91 0)
           (list 10 6.22576 0.946)
           (cons 40 0)
           (cons 41 0)
           (cons 42 0)
           (cons 91 0)
           (list 10 5.49424 0.946)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -1.2 0)
           (cons 50 0)
          )
         )
         (entmake
          (list
           (cons 0 "POINT")
           (cons 100 "AcDbEntity")
           (cons 67 0)
           (cons 8 "0")
           (cons 100 "AcDbPoint")
           (list 10 0 1.2 0)
           (cons 50 0)
          )
         )
         (entmake
          (list
           (cons 0 "POINT")
           (cons 100 "AcDbEntity")
           (cons 67 0)
           (cons 8 "0")
           (cons 100 "AcDbPoint")
           (list 10 8.2 1.2 0)
           (cons 50 0)
          )
         )
         (entmake
          (list
           (cons 0 "POINT")
           (cons 100 "AcDbEntity")
           (cons 67 0)
           (cons 8 "0")
           (cons 100 "AcDbPoint")
           (list 10 8.2 -1.2 0)
           (cons 50 0)
          )
         )
         (entmake
          (list
           (cons 0 "POINT")
           (cons 100 "AcDbEntity")
           (cons 67 0)
           (cons 8 "0")
           (cons 100 "AcDbPoint")
           (list 10 0.88 0 0)
           (cons 50 0)
          )
         )
         (entmake
          (list
           (cons 0 "POINT")
           (cons 100 "AcDbEntity")
           (cons 67 0)
           (cons 8 "0")
           (cons 100 "AcDbPoint")
           (list 10 0.88 1.2 0)
           (cons 50 0)
          )
         )
         (entmake
          (list
           (cons 0 "POINT")
           (cons 100 "AcDbEntity")
           (cons 67 0)
           (cons 8 "0")
           (cons 100 "AcDbPoint")
           (list 10 5.86 1.2 0)
           (cons 50 0)
          )
         )
         (entmake
          (list
           (cons 0 "POINT")
           (cons 100 "AcDbEntity")
           (cons 67 0)
           (cons 8 "0")
           (cons 100 "AcDbPoint")
           (list 10 5.86 -1.2 0)
           (cons 50 0)
          )
         )
         (entmake
          (list
           (cons 0 "POINT")
           (cons 100 "AcDbEntity")
           (cons 67 0)
           (cons 8 "0")
           (cons 100 "AcDbPoint")
           (list 10 0.88 -1.2 0)
           (cons 50 0)
          )
         )
         (entmake
          (list
           (cons 0 "INSERT")
           (cons 100 "AcDbEntity")
           (cons 67 0)
           (cons 8 "0")
           (cons 100 "AcDbBlockReference")
           (cons 2 "WheelLeftM2")
           (list 10 0.88 -0.946 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM2")
           (list 10 0.88 0.946 0)
           (cons 41 1)
           (cons 42 1)
           (cons 43 1)
           (cons 50 0)
           (cons 70 0)
           (cons 71 0)
           (cons 44 0)
           (cons 45 0)
          )
         )
         (entmake
          (list
           (cons 0 "LINE")
           (cons 100 "AcDbEntity")
           (cons 67 0)
           (cons 8 "0")
           (cons 100 "AcDbLine")
           (list 10 0 -1.2 0)
           (list 11 0 1.2 0)
          )
         )
         (entmake
          (list
           (cons 0 "LINE")
           (cons 100 "AcDbEntity")
           (cons 67 0)
           (cons 8 "0")
           (cons 100 "AcDbLine")
           (list 10 2 1.2 0)
           (list 11 2 1.1 0)
          )
         )
         (entmake
          (list
           (cons 0 "LINE")
           (cons 100 "AcDbEntity")
           (cons 67 0)
           (cons 8 "0")
           (cons 100 "AcDbLine")
           (list 10 2 1.1 0)
           (list 11 3 1.1 0)
          )
         )
         (entmake
          (list
           (cons 0 "LINE")
           (cons 100 "AcDbEntity")
           (cons 67 0)
           (cons 8 "0")
           (cons 100 "AcDbLine")
           (list 10 3 1.1 0)
           (list 11 3 1.2 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.352 0.593752)
           (cons 40 0)
           (cons 41 0)
           (cons 42 0)
           (cons 91 0)
           (list 10 5.352 0.752248)
           (cons 40 0)
           (cons 41 0)
           (cons 42 0)
           (cons 91 0)
           (list 10 5.49424 0.8)
           (cons 40 0)
           (cons 41 0)
           (cons 42 0)
           (cons 91 0)
           (list 10 6.22576 0.8)
           (cons 40 0)
           (cons 41 0)
           (cons 42 0)
           (cons 91 0)
           (list 10 6.368 0.752248)
           (cons 40 0)
           (cons 41 0)
           (cons 42 0)
           (cons 91 0)
           (list 10 6.368 0.593752)
           (cons 40 0)
           (cons 41 0)
           (cons 42 0)
           (cons 91 0)
           (list 10 6.22576 0.546)
           (cons 40 0)
           (cons 41 0)
           (cons 42 0)
           (cons 91 0)
           (list 10 5.49424 0.546)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.352 -0.752248)
           (cons 40 0)
           (cons 41 0)
           (cons 42 0)
           (cons 91 0)
           (list 10 5.352 -0.593752)
           (cons 40 0)
           (cons 41 0)
           (cons 42 0)
           (cons 91 0)
           (list 10 5.49424 -0.546)
           (cons 40 0)
           (cons 41 0)
           (cons 42 0)
           (cons 91 0)
           (list 10 6.22576 -0.546)
           (cons 40 0)
           (cons 41 0)
           (cons 42 0)
           (cons 91 0)
           (list 10 6.368 -0.593752)
           (cons 40 0)
           (cons 41 0)
           (cons 42 0)
           (cons 91 0)
           (list 10 6.368 -0.752248)
           (cons 40 0)
           (cons 41 0)
           (cons 42 0)
           (cons 91 0)
           (list 10 6.22576 -0.8)
           (cons 40 0)
           (cons 41 0)
           (cons 42 0)
           (cons 91 0)
           (list 10 5.49424 -0.8)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.18 0.56666667 0)
           (cons 40 0.2)
           (cons 1 "0.880")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.18 0.23333333 0)
           (cons 40 0.2)
           (cons 1 "0.880")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.18 -0.1 0)
           (cons 40 0.2)
           (cons 1 "5.860")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.18 -0.43333333 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.18 -0.76666667 0)
           (cons 40 0.2)
           (cons 1 "40.836")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "TRANSLINK-2013-HIGHWAY-COACH"))
        (progn
         (entmake)
         (entmake
          (list
           (cons 0 "BLOCK")
           (cons 2 "TRANSLINK-2013-HIGHWAY-COACH")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.25)
           (cons 40 0)
           (cons 41 0)
           (cons 42 0)
           (cons 91 0)
           (list 10 12.44 -1.25)
           (cons 40 0)
           (cons 41 0)
           (cons 42 0)
           (cons 91 0)
           (list 10 12.44 1.25)
           (cons 40 0)
           (cons 41 0)
           (cons 42 0)
           (cons 91 0)
           (list 10 0 1.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.922 -1.202248)
           (cons 40 0)
           (cons 41 0)
           (cons 42 0)
           (cons 91 0)
           (list 10 8.922 -1.043752)
           (cons 40 0)
           (cons 41 0)
           (cons 42 0)
           (cons 91 0)
           (list 10 9.06424 -0.996)
           (cons 40 0)
           (cons 41 0)
           (cons 42 0)
           (cons 91 0)
           (list 10 9.79576 -0.996)
           (cons 40 0)
           (cons 41 0)
           (cons 42 0)
           (cons 91 0)
           (list 10 9.938 -1.043752)
           (cons 40 0)
           (cons 41 0)
           (cons 42 0)
           (cons 91 0)
           (list 10 9.938 -1.202248)
           (cons 40 0)
           (cons 41 0)
           (cons 42 0)
           (cons 91 0)
           (list 10 9.79576 -1.25)
           (cons 40 0)
           (cons 41 0)
           (cons 42 0)
           (cons 91 0)
           (list 10 9.06424 -1.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.922 1.043752)
           (cons 40 0)
           (cons 41 0)
           (cons 42 0)
           (cons 91 0)
           (list 10 8.922 1.202248)
           (cons 40 0)
           (cons 41 0)
           (cons 42 0)
           (cons 91 0)
           (list 10 9.06424 1.25)
           (cons 40 0)
           (cons 41 0)
           (cons 42 0)
           (cons 91 0)
           (list 10 9.79576 1.25)
           (cons 40 0)
           (cons 41 0)
           (cons 42 0)
           (cons 91 0)
           (list 10 9.938 1.202248)
           (cons 40 0)
           (cons 41 0)
           (cons 42 0)
           (cons 91 0)
           (list 10 9.938 1.043752)
           (cons 40 0)
           (cons 41 0)
           (cons 42 0)
           (cons 91 0)
           (list 10 9.79576 0.996)
           (cons 40 0)
           (cons 41 0)
           (cons 42 0)
           (cons 91 0)
           (list 10 9.06424 0.996)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -1.25 0)
           (cons 50 0)
          )
         )
         (entmake
          (list
           (cons 0 "POINT")
           (cons 100 "AcDbEntity")
           (cons 67 0)
           (cons 8 "0")
           (cons 100 "AcDbPoint")
           (list 10 0 1.25 0)
           (cons 50 0)
          )
         )
         (entmake
          (list
           (cons 0 "POINT")
           (cons 100 "AcDbEntity")
           (cons 67 0)
           (cons 8 "0")
           (cons 100 "AcDbPoint")
           (list 10 12.44 1.25 0)
           (cons 50 0)
          )
         )
         (entmake
          (list
           (cons 0 "POINT")
           (cons 100 "AcDbEntity")
           (cons 67 0)
           (cons 8 "0")
           (cons 100 "AcDbPoint")
           (list 10 12.44 -1.25 0)
           (cons 50 0)
          )
         )
         (entmake
          (list
           (cons 0 "POINT")
           (cons 100 "AcDbEntity")
           (cons 67 0)
           (cons 8 "0")
           (cons 100 "AcDbPoint")
           (list 10 2.32 0 0)
           (cons 50 0)
          )
         )
         (entmake
          (list
           (cons 0 "POINT")
           (cons 100 "AcDbEntity")
           (cons 67 0)
           (cons 8 "0")
           (cons 100 "AcDbPoint")
           (list 10 2.32 1.25 0)
           (cons 50 0)
          )
         )
         (entmake
          (list
           (cons 0 "POINT")
           (cons 100 "AcDbEntity")
           (cons 67 0)
           (cons 8 "0")
           (cons 100 "AcDbPoint")
           (list 10 9.43 1.25 0)
           (cons 50 0)
          )
         )
         (entmake
          (list
           (cons 0 "POINT")
           (cons 100 "AcDbEntity")
           (cons 67 0)
           (cons 8 "0")
           (cons 100 "AcDbPoint")
           (list 10 9.43 -1.25 0)
           (cons 50 0)
          )
         )
         (entmake
          (list
           (cons 0 "POINT")
           (cons 100 "AcDbEntity")
           (cons 67 0)
           (cons 8 "0")
           (cons 100 "AcDbPoint")
           (list 10 2.32 -1.25 0)
           (cons 50 0)
          )
         )
         (entmake
          (list
           (cons 0 "INSERT")
           (cons 100 "AcDbEntity")
           (cons 67 0)
           (cons 8 "0")
           (cons 100 "AcDbBlockReference")
           (cons 2 "WheelLeftM2")
           (list 10 2.32 -0.996 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM2")
           (list 10 2.32 0.996 0)
           (cons 41 1)
           (cons 42 1)
           (cons 43 1)
           (cons 50 0)
           (cons 70 0)
           (cons 71 0)
           (cons 44 0)
           (cons 45 0)
          )
         )
         (entmake
          (list
           (cons 0 "LINE")
           (cons 100 "AcDbEntity")
           (cons 67 0)
           (cons 8 "0")
           (cons 100 "AcDbLine")
           (list 10 0 -1.25 0)
           (list 11 0 1.25 0)
          )
         )
         (entmake
          (list
           (cons 0 "LINE")
           (cons 100 "AcDbEntity")
           (cons 67 0)
           (cons 8 "0")
           (cons 100 "AcDbLine")
           (list 10 0.5 1.25 0)
           (list 11 0.5 1.15 0)
          )
         )
         (entmake
          (list
           (cons 0 "LINE")
           (cons 100 "AcDbEntity")
           (cons 67 0)
           (cons 8 "0")
           (cons 100 "AcDbLine")
           (list 10 0.5 1.15 0)
           (list 11 1.6 1.15 0)
          )
         )
         (entmake
          (list
           (cons 0 "LINE")
           (cons 100 "AcDbEntity")
           (cons 67 0)
           (cons 8 "0")
           (cons 100 "AcDbLine")
           (list 10 1.6 1.15 0)
           (list 11 1.6 1.25 0)
          )
         )
         (entmake
          (list
           (cons 0 "LWPOLYLINE")
           (cons 100 "AcDbEntity")
           (cons 67 0)
           (cons 8 "0")
           (cons 100 "AcDbPolyline")
           (cons 90 6)
           (cons 70 128)
           (cons 43 0)
           (cons 38 0)
           (cons 39 0)
           (list 10 0 -1.25)
           (cons 40 0)
           (cons 41 0)
           (cons 42 0)
           (cons 91 0)
           (list 10 12.44 -1.25)
           (cons 40 0)
           (cons 41 0)
           (cons 42 0)
           (cons 91 0)
           (list 10 12.44 1.25)
           (cons 40 0)
           (cons 41 0)
           (cons 42 0)
           (cons 91 0)
           (list 10 0 1.25)
           (cons 40 0)
           (cons 41 0)
           (cons 42 0)
           (cons 91 0)
           (list 10 0 -1.25)
           (cons 40 0)
           (cons 41 0)
           (cons 42 0)
           (cons 91 0)
           (list 10 0 -1.25)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 1.62 0.56666667 0)
           (cons 40 0.2)
           (cons 1 "2.320")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.62 0.23333333 0)
           (cons 40 0.2)
           (cons 1 "2.320")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.62 -0.1 0)
           (cons 40 0.2)
           (cons 1 "9.430")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.62 -0.43333333 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.62 -0.76666667 0)
           (cons 40 0.2)
           (cons 1 "46.713")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.922 0.643752)
           (cons 40 0)
           (cons 41 0)
           (cons 42 0)
           (cons 91 0)
           (list 10 8.922 0.802248)
           (cons 40 0)
           (cons 41 0)
           (cons 42 0)
           (cons 91 0)
           (list 10 9.06424 0.85)
           (cons 40 0)
           (cons 41 0)
           (cons 42 0)
           (cons 91 0)
           (list 10 9.79576 0.85)
           (cons 40 0)
           (cons 41 0)
           (cons 42 0)
           (cons 91 0)
           (list 10 9.938 0.802248)
           (cons 40 0)
           (cons 41 0)
           (cons 42 0)
           (cons 91 0)
           (list 10 9.938 0.643752)
           (cons 40 0)
           (cons 41 0)
           (cons 42 0)
           (cons 91 0)
           (list 10 9.79576 0.596)
           (cons 40 0)
           (cons 41 0)
           (cons 42 0)
           (cons 91 0)
           (list 10 9.06424 0.596)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.922 -0.802248)
           (cons 40 0)
           (cons 41 0)
           (cons 42 0)
           (cons 91 0)
           (list 10 8.922 -0.643752)
           (cons 40 0)
           (cons 41 0)
           (cons 42 0)
           (cons 91 0)
           (list 10 9.06424 -0.596)
           (cons 40 0)
           (cons 41 0)
           (cons 42 0)
           (cons 91 0)
           (list 10 9.79576 -0.596)
           (cons 40 0)
           (cons 41 0)
           (cons 42 0)
           (cons 91 0)
           (list 10 9.938 -0.643752)
           (cons 40 0)
           (cons 41 0)
           (cons 42 0)
           (cons 91 0)
           (list 10 9.938 -0.802248)
           (cons 40 0)
           (cons 41 0)
           (cons 42 0)
           (cons 91 0)
           (list 10 9.79576 -0.85)
           (cons 40 0)
           (cons 41 0)
           (cons 42 0)
           (cons 91 0)
           (list 10 9.06424 -0.85)
           (cons 40 0)
           (cons 41 0)
           (cons 42 0)
           (cons 91 0)
          )
         )
         (entmake (list (cons 0 "ENDBLK")))
        )
       )
       ((= (strcase BLKNAME) (strcase "TRANSLINK-2013-ARTICULATED-NEW-FLYER-FRONT"))
        (progn
         (entmake)
         (entmake
          (list
           (cons 0 "BLOCK")
           (cons 2 "TRANSLINK-2013-ARTICULATED-NEW-FLYER-FRONT")
           (cons 70 2)
           (cons 4 "")
           (list 10 0 0 0)
          )
         )
         (entmake
          (list
           (cons 0 "POLYLINE")
           (cons 100 "AcDbEntity")
           (cons 67 0)
           (cons 8 "Defpoints")
           (cons 100 "AcDb2dPolyline")
           (cons 66 1)
           (list 10 0 0 0)
           (cons 70 129)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "Defpoints")
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 9.09 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 9.69 0 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 9.09 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "Defpoints")
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.09 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.09 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 9.09 0 0)
           (list 11 9.69 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 9.69 0 0)
           (cons 40 0.1016)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.382 -1.252248)
           (cons 40 0)
           (cons 41 0)
           (cons 42 0)
           (cons 91 0)
           (list 10 7.382 -1.093752)
           (cons 40 0)
           (cons 41 0)
           (cons 42 0)
           (cons 91 0)
           (list 10 7.52424 -1.046)
           (cons 40 0)
           (cons 41 0)
           (cons 42 0)
           (cons 91 0)
           (list 10 8.25576 -1.046)
           (cons 40 0)
           (cons 41 0)
           (cons 42 0)
           (cons 91 0)
           (list 10 8.398 -1.093752)
           (cons 40 0)
           (cons 41 0)
           (cons 42 0)
           (cons 91 0)
           (list 10 8.398 -1.252248)
           (cons 40 0)
           (cons 41 0)
           (cons 42 0)
           (cons 91 0)
           (list 10 8.25576 -1.3)
           (cons 40 0)
           (cons 41 0)
           (cons 42 0)
           (cons 91 0)
           (list 10 7.52424 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.382 1.093752)
           (cons 40 0)
           (cons 41 0)
           (cons 42 0)
           (cons 91 0)
           (list 10 7.382 1.252248)
           (cons 40 0)
           (cons 41 0)
           (cons 42 0)
           (cons 91 0)
           (list 10 7.52424 1.3)
           (cons 40 0)
           (cons 41 0)
           (cons 42 0)
           (cons 91 0)
           (list 10 8.25576 1.3)
           (cons 40 0)
           (cons 41 0)
           (cons 42 0)
           (cons 91 0)
           (list 10 8.398 1.252248)
           (cons 40 0)
           (cons 41 0)
           (cons 42 0)
           (cons 91 0)
           (list 10 8.398 1.093752)
           (cons 40 0)
           (cons 41 0)
           (cons 42 0)
           (cons 91 0)
           (list 10 8.25576 1.046)
           (cons 40 0)
           (cons 41 0)
           (cons 42 0)
           (cons 91 0)
           (list 10 7.52424 1.046)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 2.1 0 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 9.09 1.3 0)
           (cons 50 0)
          )
         )
         (entmake
          (list
           (cons 0 "POINT")
           (cons 100 "AcDbEntity")
           (cons 67 0)
           (cons 8 "0")
           (cons 100 "AcDbPoint")
           (list 10 9.09 -1.3 0)
           (cons 50 0)
          )
         )
         (entmake
          (list
           (cons 0 "POINT")
           (cons 100 "AcDbEntity")
           (cons 67 0)
           (cons 8 "0")
           (cons 100 "AcDbPoint")
           (list 10 2.1 1.3 0)
           (cons 50 0)
          )
         )
         (entmake
          (list
           (cons 0 "POINT")
           (cons 100 "AcDbEntity")
           (cons 67 0)
           (cons 8 "0")
           (cons 100 "AcDbPoint")
           (list 10 2.1 -1.3 0)
           (cons 50 0)
          )
         )
         (entmake
          (list
           (cons 0 "POINT")
           (cons 100 "AcDbEntity")
           (cons 67 0)
           (cons 8 "0")
           (cons 100 "AcDbPoint")
           (list 10 7.89 -1.3 0)
           (cons 50 0)
          )
         )
         (entmake
          (list
           (cons 0 "POINT")
           (cons 100 "AcDbEntity")
           (cons 67 0)
           (cons 8 "0")
           (cons 100 "AcDbPoint")
           (list 10 7.89 1.3 0)
           (cons 50 0)
          )
         )
         (entmake
          (list
           (cons 0 "POINT")
           (cons 100 "AcDbEntity")
           (cons 67 0)
           (cons 8 "0")
           (cons 100 "AcDbPoint")
           (list 10 9.69 0 0)
           (cons 50 0)
          )
         )
         (entmake
          (list
           (cons 0 "INSERT")
           (cons 100 "AcDbEntity")
           (cons 67 0)
           (cons 8 "0")
           (cons 100 "AcDbBlockReference")
           (cons 2 "WheelRightM2")
           (list 10 2.1 1.046 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM2")
           (list 10 2.1 -1.046 0)
           (cons 41 1)
           (cons 42 1)
           (cons 43 1)
           (cons 50 0)
           (cons 70 0)
           (cons 71 0)
           (cons 44 0)
           (cons 45 0)
          )
         )
         (entmake
          (list
           (cons 0 "LINE")
           (cons 100 "AcDbEntity")
           (cons 67 0)
           (cons 8 "0")
           (cons 100 "AcDbLine")
           (list 10 0.5 1.2 0)
           (list 11 0.5 1.3 0)
          )
         )
         (entmake
          (list
           (cons 0 "LINE")
           (cons 100 "AcDbEntity")
           (cons 67 0)
           (cons 8 "0")
           (cons 100 "AcDbLine")
           (list 10 1.4 1.2 0)
           (list 11 1.4 1.3 0)
          )
         )
         (entmake
          (list
           (cons 0 "LINE")
           (cons 100 "AcDbEntity")
           (cons 67 0)
           (cons 8 "0")
           (cons 100 "AcDbLine")
           (list 10 0.5 1.2 0)
           (list 11 1.4 1.2 0)
          )
         )
         (entmake
          (list
           (cons 0 "LINE")
           (cons 100 "AcDbEntity")
           (cons 67 0)
           (cons 8 "0")
           (cons 100 "AcDbLine")
           (list 10 4.8 1.2 0)
           (list 11 4.8 1.3 0)
          )
         )
         (entmake
          (list
           (cons 0 "LINE")
           (cons 100 "AcDbEntity")
           (cons 67 0)
           (cons 8 "0")
           (cons 100 "AcDbLine")
           (list 10 6.2 1.2 0)
           (list 11 6.2 1.3 0)
          )
         )
         (entmake
          (list
           (cons 0 "LINE")
           (cons 100 "AcDbEntity")
           (cons 67 0)
           (cons 8 "0")
           (cons 100 "AcDbLine")
           (list 10 4.8 1.2 0)
           (list 11 6.2 1.2 0)
          )
         )
         (entmake
          (list
           (cons 0 "LINE")
           (cons 100 "AcDbEntity")
           (cons 67 0)
           (cons 8 "0")
           (cons 100 "AcDbLine")
           (list 10 2.1 0 0)
           (list 11 2.1 0 0)
          )
         )
         (entmake
          (list
           (cons 0 "ATTDEF")
           (cons 100 "AcDbEntity")
           (cons 67 0)
           (cons 8 "0")
           (cons 100 "AcDbText")
           (list 10 1.4 0.56666667 0)
           (cons 40 0.2)
           (cons 1 "2.100")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.4 0.23333333 0)
           (cons 40 0.2)
           (cons 1 "2.100")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.4 -0.1 0)
           (cons 40 0.2)
           (cons 1 "7.890")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.4 -0.43333333 0)
           (cons 40 0.2)
           (cons 1 "9.690")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.4 -0.76666667 0)
           (cons 40 0.2)
           (cons 1 "32.738")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.382 0.693752)
           (cons 40 0)
           (cons 41 0)
           (cons 42 0)
           (cons 91 0)
           (list 10 7.382 0.852248)
           (cons 40 0)
           (cons 41 0)
           (cons 42 0)
           (cons 91 0)
           (list 10 7.52424 0.9)
           (cons 40 0)
           (cons 41 0)
           (cons 42 0)
           (cons 91 0)
           (list 10 8.25576 0.9)
           (cons 40 0)
           (cons 41 0)
           (cons 42 0)
           (cons 91 0)
           (list 10 8.398 0.852248)
           (cons 40 0)
           (cons 41 0)
           (cons 42 0)
           (cons 91 0)
           (list 10 8.398 0.693752)
           (cons 40 0)
           (cons 41 0)
           (cons 42 0)
           (cons 91 0)
           (list 10 8.25576 0.646)
           (cons 40 0)
           (cons 41 0)
           (cons 42 0)
           (cons 91 0)
           (list 10 7.52424 0.646)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.382 -0.852248)
           (cons 40 0)
           (cons 41 0)
           (cons 42 0)
           (cons 91 0)
           (list 10 7.382 -0.693752)
           (cons 40 0)
           (cons 41 0)
           (cons 42 0)
           (cons 91 0)
           (list 10 7.52424 -0.646)
           (cons 40 0)
           (cons 41 0)
           (cons 42 0)
           (cons 91 0)
           (list 10 8.25576 -0.646)
           (cons 40 0)
           (cons 41 0)
           (cons 42 0)
           (cons 91 0)
           (list 10 8.398 -0.693752)
           (cons 40 0)
           (cons 41 0)
           (cons 42 0)
           (cons 91 0)
           (list 10 8.398 -0.852248)
           (cons 40 0)
           (cons 41 0)
           (cons 42 0)
           (cons 91 0)
           (list 10 8.25576 -0.9)
           (cons 40 0)
           (cons 41 0)
           (cons 42 0)
           (cons 91 0)
           (list 10 7.52424 -0.9)
           (cons 40 0)
           (cons 41 0)
           (cons 42 0)
           (cons 91 0)
          )
         )
         (entmake (list (cons 0 "ENDBLK")))
        )
       )
       ((= (strcase BLKNAME) (strcase "TRANSLINK-2013-ARTICULATED-NEW-FLYER-REAR"))
        (progn
         (entmake)
         (entmake
          (list
           (cons 0 "BLOCK")
           (cons 2 "TRANSLINK-2013-ARTICULATED-NEW-FLYER-REAR")
           (cons 70 2)
           (cons 4 "")
           (list 10 0 0 0)
          )
         )
         (entmake
          (list
           (cons 0 "POLYLINE")
           (cons 100 "AcDbEntity")
           (cons 67 0)
           (cons 8 "Defpoints")
           (cons 100 "AcDb2dPolyline")
           (cons 66 1)
           (list 10 0 0 0)
           (cons 70 129)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "Defpoints")
           (cons 100 "AcDbVertex")
           (cons 100 "AcDb2dVertex")
           (list 10 0 0 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 0.6 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 8 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 8 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 0.6 1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "Defpoints")
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0.6 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0.6 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0.6 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0.6 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 0.6 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.16)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.572 -1.252248)
           (cons 40 0)
           (cons 41 0)
           (cons 42 0)
           (cons 91 0)
           (list 10 4.572 -1.093752)
           (cons 40 0)
           (cons 41 0)
           (cons 42 0)
           (cons 91 0)
           (list 10 4.71424 -1.046)
           (cons 40 0)
           (cons 41 0)
           (cons 42 0)
           (cons 91 0)
           (list 10 5.44576 -1.046)
           (cons 40 0)
           (cons 41 0)
           (cons 42 0)
           (cons 91 0)
           (list 10 5.588 -1.093752)
           (cons 40 0)
           (cons 41 0)
           (cons 42 0)
           (cons 91 0)
           (list 10 5.588 -1.252248)
           (cons 40 0)
           (cons 41 0)
           (cons 42 0)
           (cons 91 0)
           (list 10 5.44576 -1.3)
           (cons 40 0)
           (cons 41 0)
           (cons 42 0)
           (cons 91 0)
           (list 10 4.71424 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.572 1.093752)
           (cons 40 0)
           (cons 41 0)
           (cons 42 0)
           (cons 91 0)
           (list 10 4.572 1.252248)
           (cons 40 0)
           (cons 41 0)
           (cons 42 0)
           (cons 91 0)
           (list 10 4.71424 1.3)
           (cons 40 0)
           (cons 41 0)
           (cons 42 0)
           (cons 91 0)
           (list 10 5.44576 1.3)
           (cons 40 0)
           (cons 41 0)
           (cons 42 0)
           (cons 91 0)
           (list 10 5.588 1.252248)
           (cons 40 0)
           (cons 41 0)
           (cons 42 0)
           (cons 91 0)
           (list 10 5.588 1.093752)
           (cons 40 0)
           (cons 41 0)
           (cons 42 0)
           (cons 91 0)
           (list 10 5.44576 1.046)
           (cons 40 0)
           (cons 41 0)
           (cons 42 0)
           (cons 91 0)
           (list 10 4.71424 1.046)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 5.08 -1.3 0)
           (cons 50 0)
          )
         )
         (entmake
          (list
           (cons 0 "POINT")
           (cons 100 "AcDbEntity")
           (cons 67 0)
           (cons 8 "0")
           (cons 100 "AcDbPoint")
           (list 10 5.08 1.3 0)
           (cons 50 0)
          )
         )
         (entmake
          (list
           (cons 0 "POINT")
           (cons 100 "AcDbEntity")
           (cons 67 0)
           (cons 8 "0")
           (cons 100 "AcDbPoint")
           (list 10 8 1.3 0)
           (cons 50 0)
          )
         )
         (entmake
          (list
           (cons 0 "POINT")
           (cons 100 "AcDbEntity")
           (cons 67 0)
           (cons 8 "0")
           (cons 100 "AcDbPoint")
           (list 10 8 -1.3 0)
           (cons 50 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "5.080")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.572 -0.852248)
           (cons 40 0)
           (cons 41 0)
           (cons 42 0)
           (cons 91 0)
           (list 10 4.572 -0.693752)
           (cons 40 0)
           (cons 41 0)
           (cons 42 0)
           (cons 91 0)
           (list 10 4.71424 -0.646)
           (cons 40 0)
           (cons 41 0)
           (cons 42 0)
           (cons 91 0)
           (list 10 5.44576 -0.646)
           (cons 40 0)
           (cons 41 0)
           (cons 42 0)
           (cons 91 0)
           (list 10 5.588 -0.693752)
           (cons 40 0)
           (cons 41 0)
           (cons 42 0)
           (cons 91 0)
           (list 10 5.588 -0.852248)
           (cons 40 0)
           (cons 41 0)
           (cons 42 0)
           (cons 91 0)
           (list 10 5.44576 -0.9)
           (cons 40 0)
           (cons 41 0)
           (cons 42 0)
           (cons 91 0)
           (list 10 4.71424 -0.9)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.572 0.693752)
           (cons 40 0)
           (cons 41 0)
           (cons 42 0)
           (cons 91 0)
           (list 10 4.572 0.852248)
           (cons 40 0)
           (cons 41 0)
           (cons 42 0)
           (cons 91 0)
           (list 10 4.71424 0.9)
           (cons 40 0)
           (cons 41 0)
           (cons 42 0)
           (cons 91 0)
           (list 10 5.44576 0.9)
           (cons 40 0)
           (cons 41 0)
           (cons 42 0)
           (cons 91 0)
           (list 10 5.588 0.852248)
           (cons 40 0)
           (cons 41 0)
           (cons 42 0)
           (cons 91 0)
           (list 10 5.588 0.693752)
           (cons 40 0)
           (cons 41 0)
           (cons 42 0)
           (cons 91 0)
           (list 10 5.44576 0.646)
           (cons 40 0)
           (cons 41 0)
           (cons 42 0)
           (cons 91 0)
           (list 10 4.71424 0.646)
           (cons 40 0)
           (cons 41 0)
           (cons 42 0)
           (cons 91 0)
          )
         )
         (entmake
          (list
           (cons 0 "LINE")
           (cons 100 "AcDbEntity")
           (cons 67 0)
           (cons 8 "0")
           (cons 100 "AcDbLine")
           (list 10 2.81 1.2 0)
           (list 11 2.81 1.3 0)
          )
         )
         (entmake
          (list
           (cons 0 "LINE")
           (cons 100 "AcDbEntity")
           (cons 67 0)
           (cons 8 "0")
           (cons 100 "AcDbLine")
           (list 10 4.21 1.2 0)
           (list 11 4.21 1.3 0)
          )
         )
         (entmake
          (list
           (cons 0 "LINE")
           (cons 100 "AcDbEntity")
           (cons 67 0)
           (cons 8 "0")
           (cons 100 "AcDbLine")
           (list 10 2.81 1.2 0)
           (list 11 4.21 1.2 0)
          )
         )
         (entmake (list (cons 0 "ENDBLK")))
        )
       )
       ((= (strcase BLKNAME) (strcase "TRANSLINK-2013-STANDARD-NOVA"))
        (progn
         (entmake)
         (entmake
          (list
           (cons 0 "BLOCK")
           (cons 2 "TRANSLINK-2013-STANDARD-NOVA")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 12.30778379 -1.3)
           (cons 40 0)
           (cons 41 0)
           (cons 42 0)
           (cons 91 0)
           (list 10 12.30778379 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 12.30778379 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 12.30778379 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.592 -1.252248)
           (cons 40 0)
           (cons 41 0)
           (cons 42 0)
           (cons 91 0)
           (list 10 8.592 -1.093752)
           (cons 40 0)
           (cons 41 0)
           (cons 42 0)
           (cons 91 0)
           (list 10 8.73424 -1.046)
           (cons 40 0)
           (cons 41 0)
           (cons 42 0)
           (cons 91 0)
           (list 10 9.46576 -1.046)
           (cons 40 0)
           (cons 41 0)
           (cons 42 0)
           (cons 91 0)
           (list 10 9.608 -1.093752)
           (cons 40 0)
           (cons 41 0)
           (cons 42 0)
           (cons 91 0)
           (list 10 9.608 -1.252248)
           (cons 40 0)
           (cons 41 0)
           (cons 42 0)
           (cons 91 0)
           (list 10 9.46576 -1.3)
           (cons 40 0)
           (cons 41 0)
           (cons 42 0)
           (cons 91 0)
           (list 10 8.73424 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.592 1.093752)
           (cons 40 0)
           (cons 41 0)
           (cons 42 0)
           (cons 91 0)
           (list 10 8.592 1.252248)
           (cons 40 0)
           (cons 41 0)
           (cons 42 0)
           (cons 91 0)
           (list 10 8.73424 1.3)
           (cons 40 0)
           (cons 41 0)
           (cons 42 0)
           (cons 91 0)
           (list 10 9.46576 1.3)
           (cons 40 0)
           (cons 41 0)
           (cons 42 0)
           (cons 91 0)
           (list 10 9.608 1.252248)
           (cons 40 0)
           (cons 41 0)
           (cons 42 0)
           (cons 91 0)
           (list 10 9.608 1.093752)
           (cons 40 0)
           (cons 41 0)
           (cons 42 0)
           (cons 91 0)
           (list 10 9.46576 1.046)
           (cons 40 0)
           (cons 41 0)
           (cons 42 0)
           (cons 91 0)
           (list 10 8.73424 1.046)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 12.30778379 1.3 0)
           (cons 50 0)
          )
         )
         (entmake
          (list
           (cons 0 "POINT")
           (cons 100 "AcDbEntity")
           (cons 67 0)
           (cons 8 "0")
           (cons 100 "AcDbPoint")
           (list 10 12.30778379 -1.3 0)
           (cons 50 0)
          )
         )
         (entmake
          (list
           (cons 0 "POINT")
           (cons 100 "AcDbEntity")
           (cons 67 0)
           (cons 8 "0")
           (cons 100 "AcDbPoint")
           (list 10 2.9 0 0)
           (cons 50 0)
          )
         )
         (entmake
          (list
           (cons 0 "POINT")
           (cons 100 "AcDbEntity")
           (cons 67 0)
           (cons 8 "0")
           (cons 100 "AcDbPoint")
           (list 10 2.9 1.3 0)
           (cons 50 0)
          )
         )
         (entmake
          (list
           (cons 0 "POINT")
           (cons 100 "AcDbEntity")
           (cons 67 0)
           (cons 8 "0")
           (cons 100 "AcDbPoint")
           (list 10 9.1 1.3 0)
           (cons 50 0)
          )
         )
         (entmake
          (list
           (cons 0 "POINT")
           (cons 100 "AcDbEntity")
           (cons 67 0)
           (cons 8 "0")
           (cons 100 "AcDbPoint")
           (list 10 9.1 -1.3 0)
           (cons 50 0)
          )
         )
         (entmake
          (list
           (cons 0 "POINT")
           (cons 100 "AcDbEntity")
           (cons 67 0)
           (cons 8 "0")
           (cons 100 "AcDbPoint")
           (list 10 2.9 -1.3 0)
           (cons 50 0)
          )
         )
         (entmake
          (list
           (cons 0 "INSERT")
           (cons 100 "AcDbEntity")
           (cons 67 0)
           (cons 8 "0")
           (cons 100 "AcDbBlockReference")
           (cons 2 "WheelLeftM2")
           (list 10 2.9 -1.046 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM2")
           (list 10 2.9 1.046 0)
           (cons 41 1)
           (cons 42 1)
           (cons 43 1)
           (cons 50 0)
           (cons 70 0)
           (cons 71 0)
           (cons 44 0)
           (cons 45 0)
          )
         )
         (entmake
          (list
           (cons 0 "LINE")
           (cons 100 "AcDbEntity")
           (cons 67 0)
           (cons 8 "0")
           (cons 100 "AcDbLine")
           (list 10 0 -1.3 0)
           (list 11 0 1.3 0)
          )
         )
         (entmake
          (list
           (cons 0 "LINE")
           (cons 100 "AcDbEntity")
           (cons 67 0)
           (cons 8 "0")
           (cons 100 "AcDbLine")
           (list 10 0.9 1.3 0)
           (list 11 0.9 1.2 0)
          )
         )
         (entmake
          (list
           (cons 0 "LINE")
           (cons 100 "AcDbEntity")
           (cons 67 0)
           (cons 8 "0")
           (cons 100 "AcDbLine")
           (list 10 0.9 1.2 0)
           (list 11 2.13 1.2 0)
          )
         )
         (entmake
          (list
           (cons 0 "LINE")
           (cons 100 "AcDbEntity")
           (cons 67 0)
           (cons 8 "0")
           (cons 100 "AcDbLine")
           (list 10 2.13 1.2 0)
           (list 11 2.13 1.3 0)
          )
         )
         (entmake
          (list
           (cons 0 "LINE")
           (cons 100 "AcDbEntity")
           (cons 67 0)
           (cons 8 "0")
           (cons 100 "AcDbLine")
           (list 10 7.36 1.2 0)
           (list 11 7.36 1.3 0)
          )
         )
         (entmake
          (list
           (cons 0 "LINE")
           (cons 100 "AcDbEntity")
           (cons 67 0)
           (cons 8 "0")
           (cons 100 "AcDbLine")
           (list 10 8.3 1.2 0)
           (list 11 8.3 1.3 0)
          )
         )
         (entmake
          (list
           (cons 0 "LINE")
           (cons 100 "AcDbEntity")
           (cons 67 0)
           (cons 8 "0")
           (cons 100 "AcDbLine")
           (list 10 7.36 1.2 0)
           (list 11 8.3 1.2 0)
          )
         )
         (entmake
          (list
           (cons 0 "ATTDEF")
           (cons 100 "AcDbEntity")
           (cons 67 0)
           (cons 8 "0")
           (cons 100 "AcDbText")
           (list 10 2.2 0.56666667 0)
           (cons 40 0.2)
           (cons 1 "2.900")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 2.2 0.23333333 0)
           (cons 40 0.2)
           (cons 1 "2.900")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 2.2 -0.1 0)
           (cons 40 0.2)
           (cons 1 "9.100")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 2.2 -0.43333333 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 2.2 -0.76666667 0)
           (cons 40 0.2)
           (cons 1 "40.073")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.592 0.693752)
           (cons 40 0)
           (cons 41 0)
           (cons 42 0)
           (cons 91 0)
           (list 10 8.592 0.852248)
           (cons 40 0)
           (cons 41 0)
           (cons 42 0)
           (cons 91 0)
           (list 10 8.73424 0.9)
           (cons 40 0)
           (cons 41 0)
           (cons 42 0)
           (cons 91 0)
           (list 10 9.46576 0.9)
           (cons 40 0)
           (cons 41 0)
           (cons 42 0)
           (cons 91 0)
           (list 10 9.608 0.852248)
           (cons 40 0)
           (cons 41 0)
           (cons 42 0)
           (cons 91 0)
           (list 10 9.608 0.693752)
           (cons 40 0)
           (cons 41 0)
           (cons 42 0)
           (cons 91 0)
           (list 10 9.46576 0.646)
           (cons 40 0)
           (cons 41 0)
           (cons 42 0)
           (cons 91 0)
           (list 10 8.73424 0.646)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.592 -0.852248)
           (cons 40 0)
           (cons 41 0)
           (cons 42 0)
           (cons 91 0)
           (list 10 8.592 -0.693752)
           (cons 40 0)
           (cons 41 0)
           (cons 42 0)
           (cons 91 0)
           (list 10 8.73424 -0.646)
           (cons 40 0)
           (cons 41 0)
           (cons 42 0)
           (cons 91 0)
           (list 10 9.46576 -0.646)
           (cons 40 0)
           (cons 41 0)
           (cons 42 0)
           (cons 91 0)
           (list 10 9.608 -0.693752)
           (cons 40 0)
           (cons 41 0)
           (cons 42 0)
           (cons 91 0)
           (list 10 9.608 -0.852248)
           (cons 40 0)
           (cons 41 0)
           (cons 42 0)
           (cons 91 0)
           (list 10 9.46576 -0.9)
           (cons 40 0)
           (cons 41 0)
           (cons 42 0)
           (cons 91 0)
           (list 10 8.73424 -0.9)
           (cons 40 0)
           (cons 41 0)
           (cons 42 0)
           (cons 91 0)
          )
         )
         (entmake (list (cons 0 "ENDBLK")))
        )
       )
       ((= (strcase BLKNAME) (strcase "TRANSLINK-2013-STANDARD-NEW-FLYER"))
        (progn
         (entmake)
         (entmake
          (list
           (cons 0 "BLOCK")
           (cons 2 "TRANSLINK-2013-STANDARD-NEW-FLYER")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 12.44 -1.3)
           (cons 40 0)
           (cons 41 0)
           (cons 42 0)
           (cons 91 0)
           (list 10 12.44 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 12.44 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 12.44 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.132 -1.252248)
           (cons 40 0)
           (cons 41 0)
           (cons 42 0)
           (cons 91 0)
           (list 10 9.132 -1.093752)
           (cons 40 0)
           (cons 41 0)
           (cons 42 0)
           (cons 91 0)
           (list 10 9.27424 -1.046)
           (cons 40 0)
           (cons 41 0)
           (cons 42 0)
           (cons 91 0)
           (list 10 10.00576 -1.046)
           (cons 40 0)
           (cons 41 0)
           (cons 42 0)
           (cons 91 0)
           (list 10 10.148 -1.093752)
           (cons 40 0)
           (cons 41 0)
           (cons 42 0)
           (cons 91 0)
           (list 10 10.148 -1.252248)
           (cons 40 0)
           (cons 41 0)
           (cons 42 0)
           (cons 91 0)
           (list 10 10.00576 -1.3)
           (cons 40 0)
           (cons 41 0)
           (cons 42 0)
           (cons 91 0)
           (list 10 9.27424 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.132 1.093752)
           (cons 40 0)
           (cons 41 0)
           (cons 42 0)
           (cons 91 0)
           (list 10 9.132 1.252248)
           (cons 40 0)
           (cons 41 0)
           (cons 42 0)
           (cons 91 0)
           (list 10 9.27424 1.3)
           (cons 40 0)
           (cons 41 0)
           (cons 42 0)
           (cons 91 0)
           (list 10 10.00576 1.3)
           (cons 40 0)
           (cons 41 0)
           (cons 42 0)
           (cons 91 0)
           (list 10 10.148 1.252248)
           (cons 40 0)
           (cons 41 0)
           (cons 42 0)
           (cons 91 0)
           (list 10 10.148 1.093752)
           (cons 40 0)
           (cons 41 0)
           (cons 42 0)
           (cons 91 0)
           (list 10 10.00576 1.046)
           (cons 40 0)
           (cons 41 0)
           (cons 42 0)
           (cons 91 0)
           (list 10 9.27424 1.046)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 12.44 1.3 0)
           (cons 50 0)
          )
         )
         (entmake
          (list
           (cons 0 "POINT")
           (cons 100 "AcDbEntity")
           (cons 67 0)
           (cons 8 "0")
           (cons 100 "AcDbPoint")
           (list 10 12.44 -1.3 0)
           (cons 50 0)
          )
         )
         (entmake
          (list
           (cons 0 "POINT")
           (cons 100 "AcDbEntity")
           (cons 67 0)
           (cons 8 "0")
           (cons 100 "AcDbPoint")
           (list 10 2.2 0 0)
           (cons 50 0)
          )
         )
         (entmake
          (list
           (cons 0 "POINT")
           (cons 100 "AcDbEntity")
           (cons 67 0)
           (cons 8 "0")
           (cons 100 "AcDbPoint")
           (list 10 2.2 1.3 0)
           (cons 50 0)
          )
         )
         (entmake
          (list
           (cons 0 "POINT")
           (cons 100 "AcDbEntity")
           (cons 67 0)
           (cons 8 "0")
           (cons 100 "AcDbPoint")
           (list 10 9.64 1.3 0)
           (cons 50 0)
          )
         )
         (entmake
          (list
           (cons 0 "POINT")
           (cons 100 "AcDbEntity")
           (cons 67 0)
           (cons 8 "0")
           (cons 100 "AcDbPoint")
           (list 10 9.64 -1.3 0)
           (cons 50 0)
          )
         )
         (entmake
          (list
           (cons 0 "POINT")
           (cons 100 "AcDbEntity")
           (cons 67 0)
           (cons 8 "0")
           (cons 100 "AcDbPoint")
           (list 10 2.2 -1.3 0)
           (cons 50 0)
          )
         )
         (entmake
          (list
           (cons 0 "INSERT")
           (cons 100 "AcDbEntity")
           (cons 67 0)
           (cons 8 "0")
           (cons 100 "AcDbBlockReference")
           (cons 2 "WheelLeftM2")
           (list 10 2.2 -1.046 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM2")
           (list 10 2.2 1.046 0)
           (cons 41 1)
           (cons 42 1)
           (cons 43 1)
           (cons 50 0)
           (cons 70 0)
           (cons 71 0)
           (cons 44 0)
           (cons 45 0)
          )
         )
         (entmake
          (list
           (cons 0 "LINE")
           (cons 100 "AcDbEntity")
           (cons 67 0)
           (cons 8 "0")
           (cons 100 "AcDbLine")
           (list 10 0 -1.3 0)
           (list 11 0 1.3 0)
          )
         )
         (entmake
          (list
           (cons 0 "LINE")
           (cons 100 "AcDbEntity")
           (cons 67 0)
           (cons 8 "0")
           (cons 100 "AcDbLine")
           (list 10 0.4 1.3 0)
           (list 11 0.4 1.2 0)
          )
         )
         (entmake
          (list
           (cons 0 "LINE")
           (cons 100 "AcDbEntity")
           (cons 67 0)
           (cons 8 "0")
           (cons 100 "AcDbLine")
           (list 10 0.4 1.2 0)
           (list 11 1.4 1.2 0)
          )
         )
         (entmake
          (list
           (cons 0 "LINE")
           (cons 100 "AcDbEntity")
           (cons 67 0)
           (cons 8 "0")
           (cons 100 "AcDbLine")
           (list 10 1.4 1.2 0)
           (list 11 1.4 1.3 0)
          )
         )
         (entmake
          (list
           (cons 0 "LINE")
           (cons 100 "AcDbEntity")
           (cons 67 0)
           (cons 8 "0")
           (cons 100 "AcDbLine")
           (list 10 6.6 1.2 0)
           (list 11 6.6 1.3 0)
          )
         )
         (entmake
          (list
           (cons 0 "LINE")
           (cons 100 "AcDbEntity")
           (cons 67 0)
           (cons 8 "0")
           (cons 100 "AcDbLine")
           (list 10 7.9 1.2 0)
           (list 11 7.9 1.3 0)
          )
         )
         (entmake
          (list
           (cons 0 "LINE")
           (cons 100 "AcDbEntity")
           (cons 67 0)
           (cons 8 "0")
           (cons 100 "AcDbLine")
           (list 10 6.6 1.2 0)
           (list 11 7.9 1.2 0)
          )
         )
         (entmake
          (list
           (cons 0 "ATTDEF")
           (cons 100 "AcDbEntity")
           (cons 67 0)
           (cons 8 "0")
           (cons 100 "AcDbText")
           (list 10 1.5 0.56666667 0)
           (cons 40 0.2)
           (cons 1 "2.200")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.5 0.23333333 0)
           (cons 40 0.2)
           (cons 1 "2.200")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.5 -0.1 0)
           (cons 40 0.2)
           (cons 1 "9.640")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.5 -0.43333333 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.5 -0.76666667 0)
           (cons 40 0.2)
           (cons 1 "42.541")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.132 0.693752)
           (cons 40 0)
           (cons 41 0)
           (cons 42 0)
           (cons 91 0)
           (list 10 9.132 0.852248)
           (cons 40 0)
           (cons 41 0)
           (cons 42 0)
           (cons 91 0)
           (list 10 9.27424 0.9)
           (cons 40 0)
           (cons 41 0)
           (cons 42 0)
           (cons 91 0)
           (list 10 10.00576 0.9)
           (cons 40 0)
           (cons 41 0)
           (cons 42 0)
           (cons 91 0)
           (list 10 10.148 0.852248)
           (cons 40 0)
           (cons 41 0)
           (cons 42 0)
           (cons 91 0)
           (list 10 10.148 0.693752)
           (cons 40 0)
           (cons 41 0)
           (cons 42 0)
           (cons 91 0)
           (list 10 10.00576 0.646)
           (cons 40 0)
           (cons 41 0)
           (cons 42 0)
           (cons 91 0)
           (list 10 9.27424 0.646)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.132 -0.852248)
           (cons 40 0)
           (cons 41 0)
           (cons 42 0)
           (cons 91 0)
           (list 10 9.132 -0.693752)
           (cons 40 0)
           (cons 41 0)
           (cons 42 0)
           (cons 91 0)
           (list 10 9.27424 -0.646)
           (cons 40 0)
           (cons 41 0)
           (cons 42 0)
           (cons 91 0)
           (list 10 10.00576 -0.646)
           (cons 40 0)
           (cons 41 0)
           (cons 42 0)
           (cons 91 0)
           (list 10 10.148 -0.693752)
           (cons 40 0)
           (cons 41 0)
           (cons 42 0)
           (cons 91 0)
           (list 10 10.148 -0.852248)
           (cons 40 0)
           (cons 41 0)
           (cons 42 0)
           (cons 91 0)
           (list 10 10.00576 -0.9)
           (cons 40 0)
           (cons 41 0)
           (cons 42 0)
           (cons 91 0)
           (list 10 9.27424 -0.9)
           (cons 40 0)
           (cons 41 0)
           (cons 42 0)
           (cons 91 0)
          )
         )
         (entmake (list (cons 0 "ENDBLK")))
        )
       )
       ((= (strcase BLKNAME) (strcase "TRANSLINK-2013-STANDARD-TROLLY"))
        (progn
         (entmake)
         (entmake
          (list
           (cons 0 "BLOCK")
           (cons 2 "TRANSLINK-2013-STANDARD-TROLLY")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 12.44 -1.3)
           (cons 40 0)
           (cons 41 0)
           (cons 42 0)
           (cons 91 0)
           (list 10 12.44 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 12.44 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 12.44 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.032 -1.252248)
           (cons 40 0)
           (cons 41 0)
           (cons 42 0)
           (cons 91 0)
           (list 10 9.032 -1.093752)
           (cons 40 0)
           (cons 41 0)
           (cons 42 0)
           (cons 91 0)
           (list 10 9.17424 -1.046)
           (cons 40 0)
           (cons 41 0)
           (cons 42 0)
           (cons 91 0)
           (list 10 9.90576 -1.046)
           (cons 40 0)
           (cons 41 0)
           (cons 42 0)
           (cons 91 0)
           (list 10 10.048 -1.093752)
           (cons 40 0)
           (cons 41 0)
           (cons 42 0)
           (cons 91 0)
           (list 10 10.048 -1.252248)
           (cons 40 0)
           (cons 41 0)
           (cons 42 0)
           (cons 91 0)
           (list 10 9.90576 -1.3)
           (cons 40 0)
           (cons 41 0)
           (cons 42 0)
           (cons 91 0)
           (list 10 9.17424 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.032 1.093752)
           (cons 40 0)
           (cons 41 0)
           (cons 42 0)
           (cons 91 0)
           (list 10 9.032 1.252248)
           (cons 40 0)
           (cons 41 0)
           (cons 42 0)
           (cons 91 0)
           (list 10 9.17424 1.3)
           (cons 40 0)
           (cons 41 0)
           (cons 42 0)
           (cons 91 0)
           (list 10 9.90576 1.3)
           (cons 40 0)
           (cons 41 0)
           (cons 42 0)
           (cons 91 0)
           (list 10 10.048 1.252248)
           (cons 40 0)
           (cons 41 0)
           (cons 42 0)
           (cons 91 0)
           (list 10 10.048 1.093752)
           (cons 40 0)
           (cons 41 0)
           (cons 42 0)
           (cons 91 0)
           (list 10 9.90576 1.046)
           (cons 40 0)
           (cons 41 0)
           (cons 42 0)
           (cons 91 0)
           (list 10 9.17424 1.046)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 12.44 1.3 0)
           (cons 50 0)
          )
         )
         (entmake
          (list
           (cons 0 "POINT")
           (cons 100 "AcDbEntity")
           (cons 67 0)
           (cons 8 "0")
           (cons 100 "AcDbPoint")
           (list 10 12.44 -1.3 0)
           (cons 50 0)
          )
         )
         (entmake
          (list
           (cons 0 "POINT")
           (cons 100 "AcDbEntity")
           (cons 67 0)
           (cons 8 "0")
           (cons 100 "AcDbPoint")
           (list 10 2.1 0 0)
           (cons 50 0)
          )
         )
         (entmake
          (list
           (cons 0 "POINT")
           (cons 100 "AcDbEntity")
           (cons 67 0)
           (cons 8 "0")
           (cons 100 "AcDbPoint")
           (list 10 2.1 1.3 0)
           (cons 50 0)
          )
         )
         (entmake
          (list
           (cons 0 "POINT")
           (cons 100 "AcDbEntity")
           (cons 67 0)
           (cons 8 "0")
           (cons 100 "AcDbPoint")
           (list 10 9.54 1.3 0)
           (cons 50 0)
          )
         )
         (entmake
          (list
           (cons 0 "POINT")
           (cons 100 "AcDbEntity")
           (cons 67 0)
           (cons 8 "0")
           (cons 100 "AcDbPoint")
           (list 10 9.54 -1.3 0)
           (cons 50 0)
          )
         )
         (entmake
          (list
           (cons 0 "POINT")
           (cons 100 "AcDbEntity")
           (cons 67 0)
           (cons 8 "0")
           (cons 100 "AcDbPoint")
           (list 10 2.1 -1.3 0)
           (cons 50 0)
          )
         )
         (entmake
          (list
           (cons 0 "INSERT")
           (cons 100 "AcDbEntity")
           (cons 67 0)
           (cons 8 "0")
           (cons 100 "AcDbBlockReference")
           (cons 2 "WheelLeftM2")
           (list 10 2.1 -1.046 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM2")
           (list 10 2.1 1.046 0)
           (cons 41 1)
           (cons 42 1)
           (cons 43 1)
           (cons 50 0)
           (cons 70 0)
           (cons 71 0)
           (cons 44 0)
           (cons 45 0)
          )
         )
         (entmake
          (list
           (cons 0 "LINE")
           (cons 100 "AcDbEntity")
           (cons 67 0)
           (cons 8 "0")
           (cons 100 "AcDbLine")
           (list 10 0 -1.3 0)
           (list 11 0 1.3 0)
          )
         )
         (entmake
          (list
           (cons 0 "LINE")
           (cons 100 "AcDbEntity")
           (cons 67 0)
           (cons 8 "0")
           (cons 100 "AcDbLine")
           (list 10 0.4 1.3 0)
           (list 11 0.4 1.2 0)
          )
         )
         (entmake
          (list
           (cons 0 "LINE")
           (cons 100 "AcDbEntity")
           (cons 67 0)
           (cons 8 "0")
           (cons 100 "AcDbLine")
           (list 10 0.4 1.2 0)
           (list 11 1.4 1.2 0)
          )
         )
         (entmake
          (list
           (cons 0 "LINE")
           (cons 100 "AcDbEntity")
           (cons 67 0)
           (cons 8 "0")
           (cons 100 "AcDbLine")
           (list 10 1.4 1.2 0)
           (list 11 1.4 1.3 0)
          )
         )
         (entmake
          (list
           (cons 0 "LINE")
           (cons 100 "AcDbEntity")
           (cons 67 0)
           (cons 8 "0")
           (cons 100 "AcDbLine")
           (list 10 6.6 1.2 0)
           (list 11 6.6 1.3 0)
          )
         )
         (entmake
          (list
           (cons 0 "LINE")
           (cons 100 "AcDbEntity")
           (cons 67 0)
           (cons 8 "0")
           (cons 100 "AcDbLine")
           (list 10 7.9 1.2 0)
           (list 11 7.9 1.3 0)
          )
         )
         (entmake
          (list
           (cons 0 "LINE")
           (cons 100 "AcDbEntity")
           (cons 67 0)
           (cons 8 "0")
           (cons 100 "AcDbLine")
           (list 10 6.6 1.2 0)
           (list 11 7.9 1.2 0)
          )
         )
         (entmake
          (list
           (cons 0 "ATTDEF")
           (cons 100 "AcDbEntity")
           (cons 67 0)
           (cons 8 "0")
           (cons 100 "AcDbText")
           (list 10 1.4 0.56666667 0)
           (cons 40 0.2)
           (cons 1 "2.100")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.4 0.23333333 0)
           (cons 40 0.2)
           (cons 1 "2.100")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.4 -0.1 0)
           (cons 40 0.2)
           (cons 1 "9.540")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.4 -0.43333333 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.4 -0.76666667 0)
           (cons 40 0.2)
           (cons 1 "42.183")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.032 0.693752)
           (cons 40 0)
           (cons 41 0)
           (cons 42 0)
           (cons 91 0)
           (list 10 9.032 0.852248)
           (cons 40 0)
           (cons 41 0)
           (cons 42 0)
           (cons 91 0)
           (list 10 9.17424 0.9)
           (cons 40 0)
           (cons 41 0)
           (cons 42 0)
           (cons 91 0)
           (list 10 9.90576 0.9)
           (cons 40 0)
           (cons 41 0)
           (cons 42 0)
           (cons 91 0)
           (list 10 10.048 0.852248)
           (cons 40 0)
           (cons 41 0)
           (cons 42 0)
           (cons 91 0)
           (list 10 10.048 0.693752)
           (cons 40 0)
           (cons 41 0)
           (cons 42 0)
           (cons 91 0)
           (list 10 9.90576 0.646)
           (cons 40 0)
           (cons 41 0)
           (cons 42 0)
           (cons 91 0)
           (list 10 9.17424 0.646)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.032 -0.852248)
           (cons 40 0)
           (cons 41 0)
           (cons 42 0)
           (cons 91 0)
           (list 10 9.032 -0.693752)
           (cons 40 0)
           (cons 41 0)
           (cons 42 0)
           (cons 91 0)
           (list 10 9.17424 -0.646)
           (cons 40 0)
           (cons 41 0)
           (cons 42 0)
           (cons 91 0)
           (list 10 9.90576 -0.646)
           (cons 40 0)
           (cons 41 0)
           (cons 42 0)
           (cons 91 0)
           (list 10 10.048 -0.693752)
           (cons 40 0)
           (cons 41 0)
           (cons 42 0)
           (cons 91 0)
           (list 10 10.048 -0.852248)
           (cons 40 0)
           (cons 41 0)
           (cons 42 0)
           (cons 91 0)
           (list 10 9.90576 -0.9)
           (cons 40 0)
           (cons 41 0)
           (cons 42 0)
           (cons 91 0)
           (list 10 9.17424 -0.9)
           (cons 40 0)
           (cons 41 0)
           (cons 42 0)
           (cons 91 0)
          )
         )
         (entmake (list (cons 0 "ENDBLK")))
        )
       )
       ((= (strcase BLKNAME) (strcase "TAC-2017-WB-20-TRAILER"))
        (progn
         (entmake)
         (entmake
          (list
           (cons 0 "BLOCK")
           (cons 2 "TAC-2017-WB-20-TRAILER")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 17 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 17 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 1.3 0 0)
           (cons 40 0.104)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.5062 -0.7445528)
           (cons 40 0)
           (cons 41 0)
           (cons 42 0)
           (cons 91 0)
           (list 10 12.5062 -0.5702072)
           (cons 40 0)
           (cons 41 0)
           (cons 42 0)
           (cons 91 0)
           (list 10 12.662664 -0.51768)
           (cons 40 0)
           (cons 41 0)
           (cons 42 0)
           (cons 91 0)
           (list 10 13.467336 -0.51768)
           (cons 40 0)
           (cons 41 0)
           (cons 42 0)
           (cons 91 0)
           (list 10 13.6238 -0.5702072)
           (cons 40 0)
           (cons 41 0)
           (cons 42 0)
           (cons 91 0)
           (list 10 13.6238 -0.7445528)
           (cons 40 0)
           (cons 41 0)
           (cons 42 0)
           (cons 91 0)
           (list 10 13.467336 -0.79708)
           (cons 40 0)
           (cons 41 0)
           (cons 42 0)
           (cons 91 0)
           (list 10 12.662664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.5062 -1.2474728)
           (cons 40 0)
           (cons 41 0)
           (cons 42 0)
           (cons 91 0)
           (list 10 12.5062 -1.0731272)
           (cons 40 0)
           (cons 41 0)
           (cons 42 0)
           (cons 91 0)
           (list 10 12.662664 -1.0206)
           (cons 40 0)
           (cons 41 0)
           (cons 42 0)
           (cons 91 0)
           (list 10 13.467336 -1.0206)
           (cons 40 0)
           (cons 41 0)
           (cons 42 0)
           (cons 91 0)
           (list 10 13.6238 -1.0731272)
           (cons 40 0)
           (cons 41 0)
           (cons 42 0)
           (cons 91 0)
           (list 10 13.6238 -1.2474728)
           (cons 40 0)
           (cons 41 0)
           (cons 42 0)
           (cons 91 0)
           (list 10 13.467336 -1.3)
           (cons 40 0)
           (cons 41 0)
           (cons 42 0)
           (cons 91 0)
           (list 10 12.662664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.5062 0.5702072)
           (cons 40 0)
           (cons 41 0)
           (cons 42 0)
           (cons 91 0)
           (list 10 12.5062 0.7445528)
           (cons 40 0)
           (cons 41 0)
           (cons 42 0)
           (cons 91 0)
           (list 10 12.662664 0.79708)
           (cons 40 0)
           (cons 41 0)
           (cons 42 0)
           (cons 91 0)
           (list 10 13.467336 0.79708)
           (cons 40 0)
           (cons 41 0)
           (cons 42 0)
           (cons 91 0)
           (list 10 13.6238 0.7445528)
           (cons 40 0)
           (cons 41 0)
           (cons 42 0)
           (cons 91 0)
           (list 10 13.6238 0.5702072)
           (cons 40 0)
           (cons 41 0)
           (cons 42 0)
           (cons 91 0)
           (list 10 13.467336 0.51768)
           (cons 40 0)
           (cons 41 0)
           (cons 42 0)
           (cons 91 0)
           (list 10 12.662664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.5062 1.0731272)
           (cons 40 0)
           (cons 41 0)
           (cons 42 0)
           (cons 91 0)
           (list 10 12.5062 1.2474728)
           (cons 40 0)
           (cons 41 0)
           (cons 42 0)
           (cons 91 0)
           (list 10 12.662664 1.3)
           (cons 40 0)
           (cons 41 0)
           (cons 42 0)
           (cons 91 0)
           (list 10 13.467336 1.3)
           (cons 40 0)
           (cons 41 0)
           (cons 42 0)
           (cons 91 0)
           (list 10 13.6238 1.2474728)
           (cons 40 0)
           (cons 41 0)
           (cons 42 0)
           (cons 91 0)
           (list 10 13.6238 1.0731272)
           (cons 40 0)
           (cons 41 0)
           (cons 42 0)
           (cons 91 0)
           (list 10 13.467336 1.0206)
           (cons 40 0)
           (cons 41 0)
           (cons 42 0)
           (cons 91 0)
           (list 10 12.662664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.7762 -0.7445528)
           (cons 40 0)
           (cons 41 0)
           (cons 42 0)
           (cons 91 0)
           (list 10 13.7762 -0.5702072)
           (cons 40 0)
           (cons 41 0)
           (cons 42 0)
           (cons 91 0)
           (list 10 13.932664 -0.51768)
           (cons 40 0)
           (cons 41 0)
           (cons 42 0)
           (cons 91 0)
           (list 10 14.737336 -0.51768)
           (cons 40 0)
           (cons 41 0)
           (cons 42 0)
           (cons 91 0)
           (list 10 14.8938 -0.5702072)
           (cons 40 0)
           (cons 41 0)
           (cons 42 0)
           (cons 91 0)
           (list 10 14.8938 -0.7445528)
           (cons 40 0)
           (cons 41 0)
           (cons 42 0)
           (cons 91 0)
           (list 10 14.737336 -0.79708)
           (cons 40 0)
           (cons 41 0)
           (cons 42 0)
           (cons 91 0)
           (list 10 13.932664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.7762 -1.2474728)
           (cons 40 0)
           (cons 41 0)
           (cons 42 0)
           (cons 91 0)
           (list 10 13.7762 -1.0731272)
           (cons 40 0)
           (cons 41 0)
           (cons 42 0)
           (cons 91 0)
           (list 10 13.932664 -1.0206)
           (cons 40 0)
           (cons 41 0)
           (cons 42 0)
           (cons 91 0)
           (list 10 14.737336 -1.0206)
           (cons 40 0)
           (cons 41 0)
           (cons 42 0)
           (cons 91 0)
           (list 10 14.8938 -1.0731272)
           (cons 40 0)
           (cons 41 0)
           (cons 42 0)
           (cons 91 0)
           (list 10 14.8938 -1.2474728)
           (cons 40 0)
           (cons 41 0)
           (cons 42 0)
           (cons 91 0)
           (list 10 14.737336 -1.3)
           (cons 40 0)
           (cons 41 0)
           (cons 42 0)
           (cons 91 0)
           (list 10 13.932664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.7762 0.5702072)
           (cons 40 0)
           (cons 41 0)
           (cons 42 0)
           (cons 91 0)
           (list 10 13.7762 0.7445528)
           (cons 40 0)
           (cons 41 0)
           (cons 42 0)
           (cons 91 0)
           (list 10 13.932664 0.79708)
           (cons 40 0)
           (cons 41 0)
           (cons 42 0)
           (cons 91 0)
           (list 10 14.737336 0.79708)
           (cons 40 0)
           (cons 41 0)
           (cons 42 0)
           (cons 91 0)
           (list 10 14.8938 0.7445528)
           (cons 40 0)
           (cons 41 0)
           (cons 42 0)
           (cons 91 0)
           (list 10 14.8938 0.5702072)
           (cons 40 0)
           (cons 41 0)
           (cons 42 0)
           (cons 91 0)
           (list 10 14.737336 0.51768)
           (cons 40 0)
           (cons 41 0)
           (cons 42 0)
           (cons 91 0)
           (list 10 13.932664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.7762 1.0731272)
           (cons 40 0)
           (cons 41 0)
           (cons 42 0)
           (cons 91 0)
           (list 10 13.7762 1.2474728)
           (cons 40 0)
           (cons 41 0)
           (cons 42 0)
           (cons 91 0)
           (list 10 13.932664 1.3)
           (cons 40 0)
           (cons 41 0)
           (cons 42 0)
           (cons 91 0)
           (list 10 14.737336 1.3)
           (cons 40 0)
           (cons 41 0)
           (cons 42 0)
           (cons 91 0)
           (list 10 14.8938 1.2474728)
           (cons 40 0)
           (cons 41 0)
           (cons 42 0)
           (cons 91 0)
           (list 10 14.8938 1.0731272)
           (cons 40 0)
           (cons 41 0)
           (cons 42 0)
           (cons 91 0)
           (list 10 14.737336 1.0206)
           (cons 40 0)
           (cons 41 0)
           (cons 42 0)
           (cons 91 0)
           (list 10 13.932664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 1.3 0 0)
           (cons 50 0)
          )
         )
         (entmake
          (list
           (cons 0 "POINT")
           (cons 100 "AcDbEntity")
           (cons 67 0)
           (cons 8 "0")
           (cons 100 "AcDbPoint")
           (list 10 13.7 -1.3 0)
           (cons 50 0)
          )
         )
         (entmake
          (list
           (cons 0 "POINT")
           (cons 100 "AcDbEntity")
           (cons 67 0)
           (cons 8 "0")
           (cons 100 "AcDbPoint")
           (list 10 13.7 1.3 0)
           (cons 50 0)
          )
         )
         (entmake
          (list
           (cons 0 "POINT")
           (cons 100 "AcDbEntity")
           (cons 67 0)
           (cons 8 "0")
           (cons 100 "AcDbPoint")
           (list 10 17 1.3 0)
           (cons 50 0)
          )
         )
         (entmake
          (list
           (cons 0 "POINT")
           (cons 100 "AcDbEntity")
           (cons 67 0)
           (cons 8 "0")
           (cons 100 "AcDbPoint")
           (list 10 17 -1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 17 -1.3)
           (cons 40 0)
           (cons 41 0)
           (cons 42 0)
           (cons 91 0)
           (list 10 17 1.3)
           (cons 40 0)
           (cons 41 0)
           (cons 42 0)
           (cons 91 0)
           (list 10 0 1.3)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.6 0.56666667 0)
           (cons 40 0.2)
           (cons 1 "1.30")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 0.23333333 0)
           (cons 40 0.2)
           (cons 1 "1.30")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.1 0)
           (cons 40 0.2)
           (cons 1 "13.70")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.43333333 0)
           (cons 40 0.2)
           (cons 1 "0.00")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "TAC-2017-WB-20-TRUCK"))
        (progn
         (entmake)
         (entmake
          (list
           (cons 0 "BLOCK")
           (cons 2 "TAC-2017-WB-20-TRUCK")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.635 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.635 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 7 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 7.26263966 -0.26263966 0)
           (list 11 7.26263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.8062 -0.7445528)
           (cons 40 0)
           (cons 41 0)
           (cons 42 0)
           (cons 91 0)
           (list 10 5.8062 -0.5702072)
           (cons 40 0)
           (cons 41 0)
           (cons 42 0)
           (cons 91 0)
           (list 10 5.962664 -0.51768)
           (cons 40 0)
           (cons 41 0)
           (cons 42 0)
           (cons 91 0)
           (list 10 6.767336 -0.51768)
           (cons 40 0)
           (cons 41 0)
           (cons 42 0)
           (cons 91 0)
           (list 10 6.9238 -0.5702072)
           (cons 40 0)
           (cons 41 0)
           (cons 42 0)
           (cons 91 0)
           (list 10 6.9238 -0.7445528)
           (cons 40 0)
           (cons 41 0)
           (cons 42 0)
           (cons 91 0)
           (list 10 6.767336 -0.79708)
           (cons 40 0)
           (cons 41 0)
           (cons 42 0)
           (cons 91 0)
           (list 10 5.962664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.8062 -1.2474728)
           (cons 40 0)
           (cons 41 0)
           (cons 42 0)
           (cons 91 0)
           (list 10 5.8062 -1.0731272)
           (cons 40 0)
           (cons 41 0)
           (cons 42 0)
           (cons 91 0)
           (list 10 5.962664 -1.0206)
           (cons 40 0)
           (cons 41 0)
           (cons 42 0)
           (cons 91 0)
           (list 10 6.767336 -1.0206)
           (cons 40 0)
           (cons 41 0)
           (cons 42 0)
           (cons 91 0)
           (list 10 6.9238 -1.0731272)
           (cons 40 0)
           (cons 41 0)
           (cons 42 0)
           (cons 91 0)
           (list 10 6.9238 -1.2474728)
           (cons 40 0)
           (cons 41 0)
           (cons 42 0)
           (cons 91 0)
           (list 10 6.767336 -1.3)
           (cons 40 0)
           (cons 41 0)
           (cons 42 0)
           (cons 91 0)
           (list 10 5.962664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.8062 0.5702072)
           (cons 40 0)
           (cons 41 0)
           (cons 42 0)
           (cons 91 0)
           (list 10 5.8062 0.7445528)
           (cons 40 0)
           (cons 41 0)
           (cons 42 0)
           (cons 91 0)
           (list 10 5.962664 0.79708)
           (cons 40 0)
           (cons 41 0)
           (cons 42 0)
           (cons 91 0)
           (list 10 6.767336 0.79708)
           (cons 40 0)
           (cons 41 0)
           (cons 42 0)
           (cons 91 0)
           (list 10 6.9238 0.7445528)
           (cons 40 0)
           (cons 41 0)
           (cons 42 0)
           (cons 91 0)
           (list 10 6.9238 0.5702072)
           (cons 40 0)
           (cons 41 0)
           (cons 42 0)
           (cons 91 0)
           (list 10 6.767336 0.51768)
           (cons 40 0)
           (cons 41 0)
           (cons 42 0)
           (cons 91 0)
           (list 10 5.962664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.8062 1.0731272)
           (cons 40 0)
           (cons 41 0)
           (cons 42 0)
           (cons 91 0)
           (list 10 5.8062 1.2474728)
           (cons 40 0)
           (cons 41 0)
           (cons 42 0)
           (cons 91 0)
           (list 10 5.962664 1.3)
           (cons 40 0)
           (cons 41 0)
           (cons 42 0)
           (cons 91 0)
           (list 10 6.767336 1.3)
           (cons 40 0)
           (cons 41 0)
           (cons 42 0)
           (cons 91 0)
           (list 10 6.9238 1.2474728)
           (cons 40 0)
           (cons 41 0)
           (cons 42 0)
           (cons 91 0)
           (list 10 6.9238 1.0731272)
           (cons 40 0)
           (cons 41 0)
           (cons 42 0)
           (cons 91 0)
           (list 10 6.767336 1.0206)
           (cons 40 0)
           (cons 41 0)
           (cons 42 0)
           (cons 91 0)
           (list 10 5.962664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.0762 -0.7445528)
           (cons 40 0)
           (cons 41 0)
           (cons 42 0)
           (cons 91 0)
           (list 10 7.0762 -0.5702072)
           (cons 40 0)
           (cons 41 0)
           (cons 42 0)
           (cons 91 0)
           (list 10 7.232664 -0.51768)
           (cons 40 0)
           (cons 41 0)
           (cons 42 0)
           (cons 91 0)
           (list 10 8.037336 -0.51768)
           (cons 40 0)
           (cons 41 0)
           (cons 42 0)
           (cons 91 0)
           (list 10 8.1938 -0.5702072)
           (cons 40 0)
           (cons 41 0)
           (cons 42 0)
           (cons 91 0)
           (list 10 8.1938 -0.7445528)
           (cons 40 0)
           (cons 41 0)
           (cons 42 0)
           (cons 91 0)
           (list 10 8.037336 -0.79708)
           (cons 40 0)
           (cons 41 0)
           (cons 42 0)
           (cons 91 0)
           (list 10 7.232664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.0762 -1.2474728)
           (cons 40 0)
           (cons 41 0)
           (cons 42 0)
           (cons 91 0)
           (list 10 7.0762 -1.0731272)
           (cons 40 0)
           (cons 41 0)
           (cons 42 0)
           (cons 91 0)
           (list 10 7.232664 -1.0206)
           (cons 40 0)
           (cons 41 0)
           (cons 42 0)
           (cons 91 0)
           (list 10 8.037336 -1.0206)
           (cons 40 0)
           (cons 41 0)
           (cons 42 0)
           (cons 91 0)
           (list 10 8.1938 -1.0731272)
           (cons 40 0)
           (cons 41 0)
           (cons 42 0)
           (cons 91 0)
           (list 10 8.1938 -1.2474728)
           (cons 40 0)
           (cons 41 0)
           (cons 42 0)
           (cons 91 0)
           (list 10 8.037336 -1.3)
           (cons 40 0)
           (cons 41 0)
           (cons 42 0)
           (cons 91 0)
           (list 10 7.232664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.0762 0.5702072)
           (cons 40 0)
           (cons 41 0)
           (cons 42 0)
           (cons 91 0)
           (list 10 7.0762 0.7445528)
           (cons 40 0)
           (cons 41 0)
           (cons 42 0)
           (cons 91 0)
           (list 10 7.232664 0.79708)
           (cons 40 0)
           (cons 41 0)
           (cons 42 0)
           (cons 91 0)
           (list 10 8.037336 0.79708)
           (cons 40 0)
           (cons 41 0)
           (cons 42 0)
           (cons 91 0)
           (list 10 8.1938 0.7445528)
           (cons 40 0)
           (cons 41 0)
           (cons 42 0)
           (cons 91 0)
           (list 10 8.1938 0.5702072)
           (cons 40 0)
           (cons 41 0)
           (cons 42 0)
           (cons 91 0)
           (list 10 8.037336 0.51768)
           (cons 40 0)
           (cons 41 0)
           (cons 42 0)
           (cons 91 0)
           (list 10 7.232664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.0762 1.0731272)
           (cons 40 0)
           (cons 41 0)
           (cons 42 0)
           (cons 91 0)
           (list 10 7.0762 1.2474728)
           (cons 40 0)
           (cons 41 0)
           (cons 42 0)
           (cons 91 0)
           (list 10 7.232664 1.3)
           (cons 40 0)
           (cons 41 0)
           (cons 42 0)
           (cons 91 0)
           (list 10 8.037336 1.3)
           (cons 40 0)
           (cons 41 0)
           (cons 42 0)
           (cons 91 0)
           (list 10 8.1938 1.2474728)
           (cons 40 0)
           (cons 41 0)
           (cons 42 0)
           (cons 91 0)
           (list 10 8.1938 1.0731272)
           (cons 40 0)
           (cons 41 0)
           (cons 42 0)
           (cons 91 0)
           (list 10 8.037336 1.0206)
           (cons 40 0)
           (cons 41 0)
           (cons 42 0)
           (cons 91 0)
           (list 10 7.232664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0.8 0 0)
           (cons 50 0)
          )
         )
         (entmake
          (list
           (cons 0 "POINT")
           (cons 100 "AcDbEntity")
           (cons 67 0)
           (cons 8 "0")
           (cons 100 "AcDbPoint")
           (list 10 7 -1.3 0)
           (cons 50 0)
          )
         )
         (entmake
          (list
           (cons 0 "POINT")
           (cons 100 "AcDbEntity")
           (cons 67 0)
           (cons 8 "0")
           (cons 100 "AcDbPoint")
           (list 10 7 1.3 0)
           (cons 50 0)
          )
         )
         (entmake
          (list
           (cons 0 "POINT")
           (cons 100 "AcDbEntity")
           (cons 67 0)
           (cons 8 "0")
           (cons 100 "AcDbPoint")
           (list 10 7 0 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0.8 -1.3 0)
           (cons 50 0)
          )
         )
         (entmake
          (list
           (cons 0 "POINT")
           (cons 100 "AcDbEntity")
           (cons 67 0)
           (cons 8 "0")
           (cons 100 "AcDbPoint")
           (list 10 0.8 1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 7.635 -1.3)
           (cons 40 0)
           (cons 41 0)
           (cons 42 0)
           (cons 91 0)
           (list 10 7.635 1.3)
           (cons 40 0)
           (cons 41 0)
           (cons 42 0)
           (cons 91 0)
           (list 10 0 1.3)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.1 0.56666667 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 0.23333333 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.1 0)
           (cons 40 0.2)
           (cons 1 "7.00")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.43333333 0)
           (cons 40 0.2)
           (cons 1 "7.00")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.76666667 0)
           (cons 40 0.2)
           (cons 1 "28.248")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelLeftM1")
           (list 10 0.8 -1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM1")
           (list 10 0.8 1.0206 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "TAC-2017-WB-19-TRAILER"))
        (progn
         (entmake)
         (entmake
          (list
           (cons 0 "BLOCK")
           (cons 2 "TAC-2017-WB-19-TRAILER")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 1.3 0 0)
           (cons 40 0.104)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.1062 -0.7445528)
           (cons 40 0)
           (cons 41 0)
           (cons 42 0)
           (cons 91 0)
           (list 10 12.1062 -0.5702072)
           (cons 40 0)
           (cons 41 0)
           (cons 42 0)
           (cons 91 0)
           (list 10 12.262664 -0.51768)
           (cons 40 0)
           (cons 41 0)
           (cons 42 0)
           (cons 91 0)
           (list 10 13.067336 -0.51768)
           (cons 40 0)
           (cons 41 0)
           (cons 42 0)
           (cons 91 0)
           (list 10 13.2238 -0.5702072)
           (cons 40 0)
           (cons 41 0)
           (cons 42 0)
           (cons 91 0)
           (list 10 13.2238 -0.7445528)
           (cons 40 0)
           (cons 41 0)
           (cons 42 0)
           (cons 91 0)
           (list 10 13.067336 -0.79708)
           (cons 40 0)
           (cons 41 0)
           (cons 42 0)
           (cons 91 0)
           (list 10 12.262664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.1062 -1.2474728)
           (cons 40 0)
           (cons 41 0)
           (cons 42 0)
           (cons 91 0)
           (list 10 12.1062 -1.0731272)
           (cons 40 0)
           (cons 41 0)
           (cons 42 0)
           (cons 91 0)
           (list 10 12.262664 -1.0206)
           (cons 40 0)
           (cons 41 0)
           (cons 42 0)
           (cons 91 0)
           (list 10 13.067336 -1.0206)
           (cons 40 0)
           (cons 41 0)
           (cons 42 0)
           (cons 91 0)
           (list 10 13.2238 -1.0731272)
           (cons 40 0)
           (cons 41 0)
           (cons 42 0)
           (cons 91 0)
           (list 10 13.2238 -1.2474728)
           (cons 40 0)
           (cons 41 0)
           (cons 42 0)
           (cons 91 0)
           (list 10 13.067336 -1.3)
           (cons 40 0)
           (cons 41 0)
           (cons 42 0)
           (cons 91 0)
           (list 10 12.262664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.1062 0.5702072)
           (cons 40 0)
           (cons 41 0)
           (cons 42 0)
           (cons 91 0)
           (list 10 12.1062 0.7445528)
           (cons 40 0)
           (cons 41 0)
           (cons 42 0)
           (cons 91 0)
           (list 10 12.262664 0.79708)
           (cons 40 0)
           (cons 41 0)
           (cons 42 0)
           (cons 91 0)
           (list 10 13.067336 0.79708)
           (cons 40 0)
           (cons 41 0)
           (cons 42 0)
           (cons 91 0)
           (list 10 13.2238 0.7445528)
           (cons 40 0)
           (cons 41 0)
           (cons 42 0)
           (cons 91 0)
           (list 10 13.2238 0.5702072)
           (cons 40 0)
           (cons 41 0)
           (cons 42 0)
           (cons 91 0)
           (list 10 13.067336 0.51768)
           (cons 40 0)
           (cons 41 0)
           (cons 42 0)
           (cons 91 0)
           (list 10 12.262664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.1062 1.0731272)
           (cons 40 0)
           (cons 41 0)
           (cons 42 0)
           (cons 91 0)
           (list 10 12.1062 1.2474728)
           (cons 40 0)
           (cons 41 0)
           (cons 42 0)
           (cons 91 0)
           (list 10 12.262664 1.3)
           (cons 40 0)
           (cons 41 0)
           (cons 42 0)
           (cons 91 0)
           (list 10 13.067336 1.3)
           (cons 40 0)
           (cons 41 0)
           (cons 42 0)
           (cons 91 0)
           (list 10 13.2238 1.2474728)
           (cons 40 0)
           (cons 41 0)
           (cons 42 0)
           (cons 91 0)
           (list 10 13.2238 1.0731272)
           (cons 40 0)
           (cons 41 0)
           (cons 42 0)
           (cons 91 0)
           (list 10 13.067336 1.0206)
           (cons 40 0)
           (cons 41 0)
           (cons 42 0)
           (cons 91 0)
           (list 10 12.262664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.3762 -0.7445528)
           (cons 40 0)
           (cons 41 0)
           (cons 42 0)
           (cons 91 0)
           (list 10 13.3762 -0.5702072)
           (cons 40 0)
           (cons 41 0)
           (cons 42 0)
           (cons 91 0)
           (list 10 13.532664 -0.51768)
           (cons 40 0)
           (cons 41 0)
           (cons 42 0)
           (cons 91 0)
           (list 10 14.337336 -0.51768)
           (cons 40 0)
           (cons 41 0)
           (cons 42 0)
           (cons 91 0)
           (list 10 14.4938 -0.5702072)
           (cons 40 0)
           (cons 41 0)
           (cons 42 0)
           (cons 91 0)
           (list 10 14.4938 -0.7445528)
           (cons 40 0)
           (cons 41 0)
           (cons 42 0)
           (cons 91 0)
           (list 10 14.337336 -0.79708)
           (cons 40 0)
           (cons 41 0)
           (cons 42 0)
           (cons 91 0)
           (list 10 13.532664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.3762 -1.2474728)
           (cons 40 0)
           (cons 41 0)
           (cons 42 0)
           (cons 91 0)
           (list 10 13.3762 -1.0731272)
           (cons 40 0)
           (cons 41 0)
           (cons 42 0)
           (cons 91 0)
           (list 10 13.532664 -1.0206)
           (cons 40 0)
           (cons 41 0)
           (cons 42 0)
           (cons 91 0)
           (list 10 14.337336 -1.0206)
           (cons 40 0)
           (cons 41 0)
           (cons 42 0)
           (cons 91 0)
           (list 10 14.4938 -1.0731272)
           (cons 40 0)
           (cons 41 0)
           (cons 42 0)
           (cons 91 0)
           (list 10 14.4938 -1.2474728)
           (cons 40 0)
           (cons 41 0)
           (cons 42 0)
           (cons 91 0)
           (list 10 14.337336 -1.3)
           (cons 40 0)
           (cons 41 0)
           (cons 42 0)
           (cons 91 0)
           (list 10 13.532664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.3762 0.5702072)
           (cons 40 0)
           (cons 41 0)
           (cons 42 0)
           (cons 91 0)
           (list 10 13.3762 0.7445528)
           (cons 40 0)
           (cons 41 0)
           (cons 42 0)
           (cons 91 0)
           (list 10 13.532664 0.79708)
           (cons 40 0)
           (cons 41 0)
           (cons 42 0)
           (cons 91 0)
           (list 10 14.337336 0.79708)
           (cons 40 0)
           (cons 41 0)
           (cons 42 0)
           (cons 91 0)
           (list 10 14.4938 0.7445528)
           (cons 40 0)
           (cons 41 0)
           (cons 42 0)
           (cons 91 0)
           (list 10 14.4938 0.5702072)
           (cons 40 0)
           (cons 41 0)
           (cons 42 0)
           (cons 91 0)
           (list 10 14.337336 0.51768)
           (cons 40 0)
           (cons 41 0)
           (cons 42 0)
           (cons 91 0)
           (list 10 13.532664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.3762 1.0731272)
           (cons 40 0)
           (cons 41 0)
           (cons 42 0)
           (cons 91 0)
           (list 10 13.3762 1.2474728)
           (cons 40 0)
           (cons 41 0)
           (cons 42 0)
           (cons 91 0)
           (list 10 13.532664 1.3)
           (cons 40 0)
           (cons 41 0)
           (cons 42 0)
           (cons 91 0)
           (list 10 14.337336 1.3)
           (cons 40 0)
           (cons 41 0)
           (cons 42 0)
           (cons 91 0)
           (list 10 14.4938 1.2474728)
           (cons 40 0)
           (cons 41 0)
           (cons 42 0)
           (cons 91 0)
           (list 10 14.4938 1.0731272)
           (cons 40 0)
           (cons 41 0)
           (cons 42 0)
           (cons 91 0)
           (list 10 14.337336 1.0206)
           (cons 40 0)
           (cons 41 0)
           (cons 42 0)
           (cons 91 0)
           (list 10 13.532664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 1.3 0 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 15 1.3 0)
           (cons 50 0)
          )
         )
         (entmake
          (list
           (cons 0 "POINT")
           (cons 100 "AcDbEntity")
           (cons 67 0)
           (cons 8 "0")
           (cons 100 "AcDbPoint")
           (list 10 15 -1.3 0)
           (cons 50 0)
          )
         )
         (entmake
          (list
           (cons 0 "POINT")
           (cons 100 "AcDbEntity")
           (cons 67 0)
           (cons 8 "0")
           (cons 100 "AcDbPoint")
           (list 10 13.3 1.3 0)
           (cons 50 0)
          )
         )
         (entmake
          (list
           (cons 0 "POINT")
           (cons 100 "AcDbEntity")
           (cons 67 0)
           (cons 8 "0")
           (cons 100 "AcDbPoint")
           (list 10 13.3 -1.3 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 15 -1.3)
           (cons 40 0)
           (cons 41 0)
           (cons 42 0)
           (cons 91 0)
           (list 10 15 1.3)
           (cons 40 0)
           (cons 41 0)
           (cons 42 0)
           (cons 91 0)
           (list 10 0 1.3)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.6 0.56666667 0)
           (cons 40 0.2)
           (cons 1 "1.30")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 0.23333333 0)
           (cons 40 0.2)
           (cons 1 "1.30")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.1 0)
           (cons 40 0.2)
           (cons 1 "13.30")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.43333333 0)
           (cons 40 0.2)
           (cons 1 "0.00")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "TAC-2017-WB-19-TRUCK"))
        (progn
         (entmake)
         (entmake
          (list
           (cons 0 "BLOCK")
           (cons 2 "TAC-2017-WB-19-TRUCK")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.635 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.635 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 7 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 7.26263966 -0.26263966 0)
           (list 11 7.26263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.8062 -0.7445528)
           (cons 40 0)
           (cons 41 0)
           (cons 42 0)
           (cons 91 0)
           (list 10 5.8062 -0.5702072)
           (cons 40 0)
           (cons 41 0)
           (cons 42 0)
           (cons 91 0)
           (list 10 5.962664 -0.51768)
           (cons 40 0)
           (cons 41 0)
           (cons 42 0)
           (cons 91 0)
           (list 10 6.767336 -0.51768)
           (cons 40 0)
           (cons 41 0)
           (cons 42 0)
           (cons 91 0)
           (list 10 6.9238 -0.5702072)
           (cons 40 0)
           (cons 41 0)
           (cons 42 0)
           (cons 91 0)
           (list 10 6.9238 -0.7445528)
           (cons 40 0)
           (cons 41 0)
           (cons 42 0)
           (cons 91 0)
           (list 10 6.767336 -0.79708)
           (cons 40 0)
           (cons 41 0)
           (cons 42 0)
           (cons 91 0)
           (list 10 5.962664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.8062 -1.2474728)
           (cons 40 0)
           (cons 41 0)
           (cons 42 0)
           (cons 91 0)
           (list 10 5.8062 -1.0731272)
           (cons 40 0)
           (cons 41 0)
           (cons 42 0)
           (cons 91 0)
           (list 10 5.962664 -1.0206)
           (cons 40 0)
           (cons 41 0)
           (cons 42 0)
           (cons 91 0)
           (list 10 6.767336 -1.0206)
           (cons 40 0)
           (cons 41 0)
           (cons 42 0)
           (cons 91 0)
           (list 10 6.9238 -1.0731272)
           (cons 40 0)
           (cons 41 0)
           (cons 42 0)
           (cons 91 0)
           (list 10 6.9238 -1.2474728)
           (cons 40 0)
           (cons 41 0)
           (cons 42 0)
           (cons 91 0)
           (list 10 6.767336 -1.3)
           (cons 40 0)
           (cons 41 0)
           (cons 42 0)
           (cons 91 0)
           (list 10 5.962664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.8062 0.5702072)
           (cons 40 0)
           (cons 41 0)
           (cons 42 0)
           (cons 91 0)
           (list 10 5.8062 0.7445528)
           (cons 40 0)
           (cons 41 0)
           (cons 42 0)
           (cons 91 0)
           (list 10 5.962664 0.79708)
           (cons 40 0)
           (cons 41 0)
           (cons 42 0)
           (cons 91 0)
           (list 10 6.767336 0.79708)
           (cons 40 0)
           (cons 41 0)
           (cons 42 0)
           (cons 91 0)
           (list 10 6.9238 0.7445528)
           (cons 40 0)
           (cons 41 0)
           (cons 42 0)
           (cons 91 0)
           (list 10 6.9238 0.5702072)
           (cons 40 0)
           (cons 41 0)
           (cons 42 0)
           (cons 91 0)
           (list 10 6.767336 0.51768)
           (cons 40 0)
           (cons 41 0)
           (cons 42 0)
           (cons 91 0)
           (list 10 5.962664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.8062 1.0731272)
           (cons 40 0)
           (cons 41 0)
           (cons 42 0)
           (cons 91 0)
           (list 10 5.8062 1.2474728)
           (cons 40 0)
           (cons 41 0)
           (cons 42 0)
           (cons 91 0)
           (list 10 5.962664 1.3)
           (cons 40 0)
           (cons 41 0)
           (cons 42 0)
           (cons 91 0)
           (list 10 6.767336 1.3)
           (cons 40 0)
           (cons 41 0)
           (cons 42 0)
           (cons 91 0)
           (list 10 6.9238 1.2474728)
           (cons 40 0)
           (cons 41 0)
           (cons 42 0)
           (cons 91 0)
           (list 10 6.9238 1.0731272)
           (cons 40 0)
           (cons 41 0)
           (cons 42 0)
           (cons 91 0)
           (list 10 6.767336 1.0206)
           (cons 40 0)
           (cons 41 0)
           (cons 42 0)
           (cons 91 0)
           (list 10 5.962664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.0762 -0.7445528)
           (cons 40 0)
           (cons 41 0)
           (cons 42 0)
           (cons 91 0)
           (list 10 7.0762 -0.5702072)
           (cons 40 0)
           (cons 41 0)
           (cons 42 0)
           (cons 91 0)
           (list 10 7.232664 -0.51768)
           (cons 40 0)
           (cons 41 0)
           (cons 42 0)
           (cons 91 0)
           (list 10 8.037336 -0.51768)
           (cons 40 0)
           (cons 41 0)
           (cons 42 0)
           (cons 91 0)
           (list 10 8.1938 -0.5702072)
           (cons 40 0)
           (cons 41 0)
           (cons 42 0)
           (cons 91 0)
           (list 10 8.1938 -0.7445528)
           (cons 40 0)
           (cons 41 0)
           (cons 42 0)
           (cons 91 0)
           (list 10 8.037336 -0.79708)
           (cons 40 0)
           (cons 41 0)
           (cons 42 0)
           (cons 91 0)
           (list 10 7.232664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.0762 -1.2474728)
           (cons 40 0)
           (cons 41 0)
           (cons 42 0)
           (cons 91 0)
           (list 10 7.0762 -1.0731272)
           (cons 40 0)
           (cons 41 0)
           (cons 42 0)
           (cons 91 0)
           (list 10 7.232664 -1.0206)
           (cons 40 0)
           (cons 41 0)
           (cons 42 0)
           (cons 91 0)
           (list 10 8.037336 -1.0206)
           (cons 40 0)
           (cons 41 0)
           (cons 42 0)
           (cons 91 0)
           (list 10 8.1938 -1.0731272)
           (cons 40 0)
           (cons 41 0)
           (cons 42 0)
           (cons 91 0)
           (list 10 8.1938 -1.2474728)
           (cons 40 0)
           (cons 41 0)
           (cons 42 0)
           (cons 91 0)
           (list 10 8.037336 -1.3)
           (cons 40 0)
           (cons 41 0)
           (cons 42 0)
           (cons 91 0)
           (list 10 7.232664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.0762 0.5702072)
           (cons 40 0)
           (cons 41 0)
           (cons 42 0)
           (cons 91 0)
           (list 10 7.0762 0.7445528)
           (cons 40 0)
           (cons 41 0)
           (cons 42 0)
           (cons 91 0)
           (list 10 7.232664 0.79708)
           (cons 40 0)
           (cons 41 0)
           (cons 42 0)
           (cons 91 0)
           (list 10 8.037336 0.79708)
           (cons 40 0)
           (cons 41 0)
           (cons 42 0)
           (cons 91 0)
           (list 10 8.1938 0.7445528)
           (cons 40 0)
           (cons 41 0)
           (cons 42 0)
           (cons 91 0)
           (list 10 8.1938 0.5702072)
           (cons 40 0)
           (cons 41 0)
           (cons 42 0)
           (cons 91 0)
           (list 10 8.037336 0.51768)
           (cons 40 0)
           (cons 41 0)
           (cons 42 0)
           (cons 91 0)
           (list 10 7.232664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.0762 1.0731272)
           (cons 40 0)
           (cons 41 0)
           (cons 42 0)
           (cons 91 0)
           (list 10 7.0762 1.2474728)
           (cons 40 0)
           (cons 41 0)
           (cons 42 0)
           (cons 91 0)
           (list 10 7.232664 1.3)
           (cons 40 0)
           (cons 41 0)
           (cons 42 0)
           (cons 91 0)
           (list 10 8.037336 1.3)
           (cons 40 0)
           (cons 41 0)
           (cons 42 0)
           (cons 91 0)
           (list 10 8.1938 1.2474728)
           (cons 40 0)
           (cons 41 0)
           (cons 42 0)
           (cons 91 0)
           (list 10 8.1938 1.0731272)
           (cons 40 0)
           (cons 41 0)
           (cons 42 0)
           (cons 91 0)
           (list 10 8.037336 1.0206)
           (cons 40 0)
           (cons 41 0)
           (cons 42 0)
           (cons 91 0)
           (list 10 7.232664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 7 0 0)
           (cons 50 0)
          )
         )
         (entmake
          (list
           (cons 0 "POINT")
           (cons 100 "AcDbEntity")
           (cons 67 0)
           (cons 8 "0")
           (cons 100 "AcDbPoint")
           (list 10 0.8 -1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0.8 1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 7 1.3 0)
           (cons 50 0)
          )
         )
         (entmake
          (list
           (cons 0 "POINT")
           (cons 100 "AcDbEntity")
           (cons 67 0)
           (cons 8 "0")
           (cons 100 "AcDbPoint")
           (list 10 7 -1.3 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 7.635 -1.3)
           (cons 40 0)
           (cons 41 0)
           (cons 42 0)
           (cons 91 0)
           (list 10 7.635 1.3)
           (cons 40 0)
           (cons 41 0)
           (cons 42 0)
           (cons 91 0)
           (list 10 0 1.3)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0.8 0 0)
           (cons 50 0)
          )
         )
         (entmake
          (list
           (cons 0 "ATTDEF")
           (cons 100 "AcDbEntity")
           (cons 67 0)
           (cons 8 "0")
           (cons 100 "AcDbText")
           (list 10 0.1 0.56666667 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 0.23333333 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.1 0)
           (cons 40 0.2)
           (cons 1 "7.00")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.43333333 0)
           (cons 40 0.2)
           (cons 1 "7.00")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.76666667 0)
           (cons 40 0.2)
           (cons 1 "28.972")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelRightM1")
           (list 10 0.8 1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM1")
           (list 10 0.8 -1.0206 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "TAC-2017-P"))
        (progn
         (entmake)
         (entmake
          (list
           (cons 0 "BLOCK")
           (cons 2 "TAC-2017-P")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.6 -1 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.6 1 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.9571 -0.9677674)
           (cons 40 0)
           (cons 41 0)
           (cons 42 0)
           (cons 91 0)
           (list 10 3.9571 -0.8607826)
           (cons 40 0)
           (cons 41 0)
           (cons 42 0)
           (cons 91 0)
           (list 10 4.053112 -0.82855)
           (cons 40 0)
           (cons 41 0)
           (cons 42 0)
           (cons 91 0)
           (list 10 4.546888 -0.82855)
           (cons 40 0)
           (cons 41 0)
           (cons 42 0)
           (cons 91 0)
           (list 10 4.6429 -0.8607826)
           (cons 40 0)
           (cons 41 0)
           (cons 42 0)
           (cons 91 0)
           (list 10 4.6429 -0.9677674)
           (cons 40 0)
           (cons 41 0)
           (cons 42 0)
           (cons 91 0)
           (list 10 4.546888 -1)
           (cons 40 0)
           (cons 41 0)
           (cons 42 0)
           (cons 91 0)
           (list 10 4.053112 -1)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.9571 0.8607826)
           (cons 40 0)
           (cons 41 0)
           (cons 42 0)
           (cons 91 0)
           (list 10 3.9571 0.9677674)
           (cons 40 0)
           (cons 41 0)
           (cons 42 0)
           (cons 91 0)
           (list 10 4.053112 1)
           (cons 40 0)
           (cons 41 0)
           (cons 42 0)
           (cons 91 0)
           (list 10 4.546888 1)
           (cons 40 0)
           (cons 41 0)
           (cons 42 0)
           (cons 91 0)
           (list 10 4.6429 0.9677674)
           (cons 40 0)
           (cons 41 0)
           (cons 42 0)
           (cons 91 0)
           (list 10 4.6429 0.8607826)
           (cons 40 0)
           (cons 41 0)
           (cons 42 0)
           (cons 91 0)
           (list 10 4.546888 0.82855)
           (cons 40 0)
           (cons 41 0)
           (cons 42 0)
           (cons 91 0)
           (list 10 4.053112 0.82855)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 1 0)
           (cons 50 0)
          )
         )
         (entmake
          (list
           (cons 0 "POINT")
           (cons 100 "AcDbEntity")
           (cons 67 0)
           (cons 8 "0")
           (cons 100 "AcDbPoint")
           (list 10 1.1 1 0)
           (cons 50 0)
          )
         )
         (entmake
          (list
           (cons 0 "POINT")
           (cons 100 "AcDbEntity")
           (cons 67 0)
           (cons 8 "0")
           (cons 100 "AcDbPoint")
           (list 10 4.3 1 0)
           (cons 50 0)
          )
         )
         (entmake
          (list
           (cons 0 "POINT")
           (cons 100 "AcDbEntity")
           (cons 67 0)
           (cons 8 "0")
           (cons 100 "AcDbPoint")
           (list 10 5.6 1 0)
           (cons 50 0)
          )
         )
         (entmake
          (list
           (cons 0 "POINT")
           (cons 100 "AcDbEntity")
           (cons 67 0)
           (cons 8 "0")
           (cons 100 "AcDbPoint")
           (list 10 5.6 -1 0)
           (cons 50 0)
          )
         )
         (entmake
          (list
           (cons 0 "POINT")
           (cons 100 "AcDbEntity")
           (cons 67 0)
           (cons 8 "0")
           (cons 100 "AcDbPoint")
           (list 10 4.3 -1 0)
           (cons 50 0)
          )
         )
         (entmake
          (list
           (cons 0 "POINT")
           (cons 100 "AcDbEntity")
           (cons 67 0)
           (cons 8 "0")
           (cons 100 "AcDbPoint")
           (list 10 1.1 -1 0)
           (cons 50 0)
          )
         )
         (entmake
          (list
           (cons 0 "POINT")
           (cons 100 "AcDbEntity")
           (cons 67 0)
           (cons 8 "0")
           (cons 100 "AcDbPoint")
           (list 10 0 -1 0)
           (cons 50 0)
          )
         )
         (entmake
          (list
           (cons 0 "POINT")
           (cons 100 "AcDbEntity")
           (cons 67 0)
           (cons 8 "0")
           (cons 100 "AcDbPoint")
           (list 10 1.1 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1)
           (cons 40 0)
           (cons 41 0)
           (cons 42 0)
           (cons 91 0)
           (list 10 5.6 -1)
           (cons 40 0)
           (cons 41 0)
           (cons 42 0)
           (cons 91 0)
           (list 10 5.6 1)
           (cons 40 0)
           (cons 41 0)
           (cons 42 0)
           (cons 91 0)
           (list 10 0 1)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.4 0.56666667 0)
           (cons 40 0.2)
           (cons 1 "1.10")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.4 0.23333333 0)
           (cons 40 0.2)
           (cons 1 "1.10")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.4 -0.1 0)
           (cons 40 0.2)
           (cons 1 "4.30")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.4 -0.43333333 0)
           (cons 40 0.2)
           (cons 1 "0.00")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.4 -0.76666667 0)
           (cons 40 0.2)
           (cons 1 "30.526")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelLeftM3")
           (list 10 1.1 -0.82855 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM3")
           (list 10 1.1 0.82855 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "TAC-2017-MSU"))
        (progn
         (entmake)
         (entmake
          (list
           (cons 0 "BLOCK")
           (cons 2 "TAC-2017-MSU")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 10 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 10 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.792 -0.795048)
           (cons 40 0)
           (cons 41 0)
           (cons 42 0)
           (cons 91 0)
           (list 10 6.792 -0.636552)
           (cons 40 0)
           (cons 41 0)
           (cons 42 0)
           (cons 91 0)
           (list 10 6.93424 -0.5888)
           (cons 40 0)
           (cons 41 0)
           (cons 42 0)
           (cons 91 0)
           (list 10 7.66576 -0.5888)
           (cons 40 0)
           (cons 41 0)
           (cons 42 0)
           (cons 91 0)
           (list 10 7.808 -0.636552)
           (cons 40 0)
           (cons 41 0)
           (cons 42 0)
           (cons 91 0)
           (list 10 7.808 -0.795048)
           (cons 40 0)
           (cons 41 0)
           (cons 42 0)
           (cons 91 0)
           (list 10 7.66576 -0.8428)
           (cons 40 0)
           (cons 41 0)
           (cons 42 0)
           (cons 91 0)
           (list 10 6.93424 -0.8428)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.792 -1.252248)
           (cons 40 0)
           (cons 41 0)
           (cons 42 0)
           (cons 91 0)
           (list 10 6.792 -1.093752)
           (cons 40 0)
           (cons 41 0)
           (cons 42 0)
           (cons 91 0)
           (list 10 6.93424 -1.046)
           (cons 40 0)
           (cons 41 0)
           (cons 42 0)
           (cons 91 0)
           (list 10 7.66576 -1.046)
           (cons 40 0)
           (cons 41 0)
           (cons 42 0)
           (cons 91 0)
           (list 10 7.808 -1.093752)
           (cons 40 0)
           (cons 41 0)
           (cons 42 0)
           (cons 91 0)
           (list 10 7.808 -1.252248)
           (cons 40 0)
           (cons 41 0)
           (cons 42 0)
           (cons 91 0)
           (list 10 7.66576 -1.3)
           (cons 40 0)
           (cons 41 0)
           (cons 42 0)
           (cons 91 0)
           (list 10 6.93424 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.792 0.636552)
           (cons 40 0)
           (cons 41 0)
           (cons 42 0)
           (cons 91 0)
           (list 10 6.792 0.795048)
           (cons 40 0)
           (cons 41 0)
           (cons 42 0)
           (cons 91 0)
           (list 10 6.93424 0.8428)
           (cons 40 0)
           (cons 41 0)
           (cons 42 0)
           (cons 91 0)
           (list 10 7.66576 0.8428)
           (cons 40 0)
           (cons 41 0)
           (cons 42 0)
           (cons 91 0)
           (list 10 7.808 0.795048)
           (cons 40 0)
           (cons 41 0)
           (cons 42 0)
           (cons 91 0)
           (list 10 7.808 0.636552)
           (cons 40 0)
           (cons 41 0)
           (cons 42 0)
           (cons 91 0)
           (list 10 7.66576 0.5888)
           (cons 40 0)
           (cons 41 0)
           (cons 42 0)
           (cons 91 0)
           (list 10 6.93424 0.5888)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.792 1.093752)
           (cons 40 0)
           (cons 41 0)
           (cons 42 0)
           (cons 91 0)
           (list 10 6.792 1.252248)
           (cons 40 0)
           (cons 41 0)
           (cons 42 0)
           (cons 91 0)
           (list 10 6.93424 1.3)
           (cons 40 0)
           (cons 41 0)
           (cons 42 0)
           (cons 91 0)
           (list 10 7.66576 1.3)
           (cons 40 0)
           (cons 41 0)
           (cons 42 0)
           (cons 91 0)
           (list 10 7.808 1.252248)
           (cons 40 0)
           (cons 41 0)
           (cons 42 0)
           (cons 91 0)
           (list 10 7.808 1.093752)
           (cons 40 0)
           (cons 41 0)
           (cons 42 0)
           (cons 91 0)
           (list 10 7.66576 1.046)
           (cons 40 0)
           (cons 41 0)
           (cons 42 0)
           (cons 91 0)
           (list 10 6.93424 1.046)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0.8 -1.3 0)
           (cons 50 0)
          )
         )
         (entmake
          (list
           (cons 0 "POINT")
           (cons 100 "AcDbEntity")
           (cons 67 0)
           (cons 8 "0")
           (cons 100 "AcDbPoint")
           (list 10 7.3 -1.3 0)
           (cons 50 0)
          )
         )
         (entmake
          (list
           (cons 0 "POINT")
           (cons 100 "AcDbEntity")
           (cons 67 0)
           (cons 8 "0")
           (cons 100 "AcDbPoint")
           (list 10 10 -1.3 0)
           (cons 50 0)
          )
         )
         (entmake
          (list
           (cons 0 "POINT")
           (cons 100 "AcDbEntity")
           (cons 67 0)
           (cons 8 "0")
           (cons 100 "AcDbPoint")
           (list 10 10 1.3 0)
           (cons 50 0)
          )
         )
         (entmake
          (list
           (cons 0 "POINT")
           (cons 100 "AcDbEntity")
           (cons 67 0)
           (cons 8 "0")
           (cons 100 "AcDbPoint")
           (list 10 7.3 1.3 0)
           (cons 50 0)
          )
         )
         (entmake
          (list
           (cons 0 "POINT")
           (cons 100 "AcDbEntity")
           (cons 67 0)
           (cons 8 "0")
           (cons 100 "AcDbPoint")
           (list 10 0.8 1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0.8 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 10 -1.3)
           (cons 40 0)
           (cons 41 0)
           (cons 42 0)
           (cons 91 0)
           (list 10 10 1.3)
           (cons 40 0)
           (cons 41 0)
           (cons 42 0)
           (cons 91 0)
           (list 10 0 1.3)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.1 0.56666667 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 0.23333333 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.1 0)
           (cons 40 0.2)
           (cons 1 "7.30")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.43333333 0)
           (cons 40 0.2)
           (cons 1 "0.00")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.76666667 0)
           (cons 40 0.2)
           (cons 1 "40.058")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelRightM2")
           (list 10 0.8 1.046 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM2")
           (list 10 0.8 -1.046 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "TAC-2017-LSU"))
        (progn
         (entmake)
         (entmake
          (list
           (cons 0 "BLOCK")
           (cons 2 "TAC-2017-LSU")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.4 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.4 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.692 -1.252248)
           (cons 40 0)
           (cons 41 0)
           (cons 42 0)
           (cons 91 0)
           (list 10 3.692 -1.093752)
           (cons 40 0)
           (cons 41 0)
           (cons 42 0)
           (cons 91 0)
           (list 10 3.83424 -1.046)
           (cons 40 0)
           (cons 41 0)
           (cons 42 0)
           (cons 91 0)
           (list 10 4.56576 -1.046)
           (cons 40 0)
           (cons 41 0)
           (cons 42 0)
           (cons 91 0)
           (list 10 4.708 -1.093752)
           (cons 40 0)
           (cons 41 0)
           (cons 42 0)
           (cons 91 0)
           (list 10 4.708 -1.252248)
           (cons 40 0)
           (cons 41 0)
           (cons 42 0)
           (cons 91 0)
           (list 10 4.56576 -1.3)
           (cons 40 0)
           (cons 41 0)
           (cons 42 0)
           (cons 91 0)
           (list 10 3.83424 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.692 1.093752)
           (cons 40 0)
           (cons 41 0)
           (cons 42 0)
           (cons 91 0)
           (list 10 3.692 1.252248)
           (cons 40 0)
           (cons 41 0)
           (cons 42 0)
           (cons 91 0)
           (list 10 3.83424 1.3)
           (cons 40 0)
           (cons 41 0)
           (cons 42 0)
           (cons 91 0)
           (list 10 4.56576 1.3)
           (cons 40 0)
           (cons 41 0)
           (cons 42 0)
           (cons 91 0)
           (list 10 4.708 1.252248)
           (cons 40 0)
           (cons 41 0)
           (cons 42 0)
           (cons 91 0)
           (list 10 4.708 1.093752)
           (cons 40 0)
           (cons 41 0)
           (cons 42 0)
           (cons 91 0)
           (list 10 4.56576 1.046)
           (cons 40 0)
           (cons 41 0)
           (cons 42 0)
           (cons 91 0)
           (list 10 3.83424 1.046)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0.8 -1.3 0)
           (cons 50 0)
          )
         )
         (entmake
          (list
           (cons 0 "POINT")
           (cons 100 "AcDbEntity")
           (cons 67 0)
           (cons 8 "0")
           (cons 100 "AcDbPoint")
           (list 10 4.2 -1.3 0)
           (cons 50 0)
          )
         )
         (entmake
          (list
           (cons 0 "POINT")
           (cons 100 "AcDbEntity")
           (cons 67 0)
           (cons 8 "0")
           (cons 100 "AcDbPoint")
           (list 10 6.4 -1.3 0)
           (cons 50 0)
          )
         )
         (entmake
          (list
           (cons 0 "POINT")
           (cons 100 "AcDbEntity")
           (cons 67 0)
           (cons 8 "0")
           (cons 100 "AcDbPoint")
           (list 10 6.4 1.3 0)
           (cons 50 0)
          )
         )
         (entmake
          (list
           (cons 0 "POINT")
           (cons 100 "AcDbEntity")
           (cons 67 0)
           (cons 8 "0")
           (cons 100 "AcDbPoint")
           (list 10 4.2 1.3 0)
           (cons 50 0)
          )
         )
         (entmake
          (list
           (cons 0 "POINT")
           (cons 100 "AcDbEntity")
           (cons 67 0)
           (cons 8 "0")
           (cons 100 "AcDbPoint")
           (list 10 0.8 1.3 0)
           (cons 50 0)
          )
         )
         (entmake
          (list
           (cons 0 "POINT")
           (cons 100 "AcDbEntity")
           (cons 67 0)
           (cons 8 "0")
           (cons 100 "AcDbPoint")
           (list 10 0.8 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 6.4 -1.3)
           (cons 40 0)
           (cons 41 0)
           (cons 42 0)
           (cons 91 0)
           (list 10 6.4 1.3)
           (cons 40 0)
           (cons 41 0)
           (cons 42 0)
           (cons 91 0)
           (list 10 0 1.3)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.1 0.56666667 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 0.23333333 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.1 0)
           (cons 40 0.2)
           (cons 1 "4.20")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.43333333 0)
           (cons 40 0.2)
           (cons 1 "0.00")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.76666667 0)
           (cons 40 0.2)
           (cons 1 "39.904")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelLeftM2")
           (list 10 0.8 -1.046 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM2")
           (list 10 0.8 1.046 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "TAC-2017-I-BUS"))
        (progn
         (entmake)
         (entmake
          (list
           (cons 0 "BLOCK")
           (cons 2 "TAC-2017-I-BUS")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 14 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 14 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.492 -1.152248)
           (cons 40 0)
           (cons 41 0)
           (cons 42 0)
           (cons 91 0)
           (list 10 9.492 -0.993752)
           (cons 40 0)
           (cons 41 0)
           (cons 42 0)
           (cons 91 0)
           (list 10 9.63424 -0.946)
           (cons 40 0)
           (cons 41 0)
           (cons 42 0)
           (cons 91 0)
           (list 10 10.36576 -0.946)
           (cons 40 0)
           (cons 41 0)
           (cons 42 0)
           (cons 91 0)
           (list 10 10.508 -0.993752)
           (cons 40 0)
           (cons 41 0)
           (cons 42 0)
           (cons 91 0)
           (list 10 10.508 -1.152248)
           (cons 40 0)
           (cons 41 0)
           (cons 42 0)
           (cons 91 0)
           (list 10 10.36576 -1.2)
           (cons 40 0)
           (cons 41 0)
           (cons 42 0)
           (cons 91 0)
           (list 10 9.63424 -1.2)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.492 0.993752)
           (cons 40 0)
           (cons 41 0)
           (cons 42 0)
           (cons 91 0)
           (list 10 9.492 1.152248)
           (cons 40 0)
           (cons 41 0)
           (cons 42 0)
           (cons 91 0)
           (list 10 9.63424 1.2)
           (cons 40 0)
           (cons 41 0)
           (cons 42 0)
           (cons 91 0)
           (list 10 10.36576 1.2)
           (cons 40 0)
           (cons 41 0)
           (cons 42 0)
           (cons 91 0)
           (list 10 10.508 1.152248)
           (cons 40 0)
           (cons 41 0)
           (cons 42 0)
           (cons 91 0)
           (list 10 10.508 0.993752)
           (cons 40 0)
           (cons 41 0)
           (cons 42 0)
           (cons 91 0)
           (list 10 10.36576 0.946)
           (cons 40 0)
           (cons 41 0)
           (cons 42 0)
           (cons 91 0)
           (list 10 9.63424 0.946)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -1.2 0)
           (cons 50 0)
          )
         )
         (entmake
          (list
           (cons 0 "POINT")
           (cons 100 "AcDbEntity")
           (cons 67 0)
           (cons 8 "0")
           (cons 100 "AcDbPoint")
           (list 10 0 1.2 0)
           (cons 50 0)
          )
         )
         (entmake
          (list
           (cons 0 "POINT")
           (cons 100 "AcDbEntity")
           (cons 67 0)
           (cons 8 "0")
           (cons 100 "AcDbPoint")
           (list 10 14 1.2 0)
           (cons 50 0)
          )
         )
         (entmake
          (list
           (cons 0 "POINT")
           (cons 100 "AcDbEntity")
           (cons 67 0)
           (cons 8 "0")
           (cons 100 "AcDbPoint")
           (list 10 14 -1.2 0)
           (cons 50 0)
          )
         )
         (entmake
          (list
           (cons 0 "POINT")
           (cons 100 "AcDbEntity")
           (cons 67 0)
           (cons 8 "0")
           (cons 100 "AcDbPoint")
           (list 10 1.8 -1.2 0)
           (cons 50 0)
          )
         )
         (entmake
          (list
           (cons 0 "POINT")
           (cons 100 "AcDbEntity")
           (cons 67 0)
           (cons 8 "0")
           (cons 100 "AcDbPoint")
           (list 10 1.8 1.2 0)
           (cons 50 0)
          )
         )
         (entmake
          (list
           (cons 0 "POINT")
           (cons 100 "AcDbEntity")
           (cons 67 0)
           (cons 8 "0")
           (cons 100 "AcDbPoint")
           (list 10 10 1.2 0)
           (cons 50 0)
          )
         )
         (entmake
          (list
           (cons 0 "POINT")
           (cons 100 "AcDbEntity")
           (cons 67 0)
           (cons 8 "0")
           (cons 100 "AcDbPoint")
           (list 10 10 -1.2 0)
           (cons 50 0)
          )
         )
         (entmake
          (list
           (cons 0 "POINT")
           (cons 100 "AcDbEntity")
           (cons 67 0)
           (cons 8 "0")
           (cons 100 "AcDbPoint")
           (list 10 1.8 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.2)
           (cons 40 0)
           (cons 41 0)
           (cons 42 0)
           (cons 91 0)
           (list 10 14 -1.2)
           (cons 40 0)
           (cons 41 0)
           (cons 42 0)
           (cons 91 0)
           (list 10 14 1.2)
           (cons 40 0)
           (cons 41 0)
           (cons 42 0)
           (cons 91 0)
           (list 10 0 1.2)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 1.1 0.56666667 0)
           (cons 40 0.2)
           (cons 1 "1.80")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.1 0.23333333 0)
           (cons 40 0.2)
           (cons 1 "1.80")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.1 -0.1 0)
           (cons 40 0.2)
           (cons 1 "10.00")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.1 -0.43333333 0)
           (cons 40 0.2)
           (cons 1 "0.00")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.1 -0.76666667 0)
           (cons 40 0.2)
           (cons 1 "36.152")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelRightM2")
           (list 10 1.8 0.946 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM2")
           (list 10 1.8 -0.946 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "TAC-2017-HSU"))
        (progn
         (entmake)
         (entmake
          (list
           (cons 0 "BLOCK")
           (cons 2 "TAC-2017-HSU")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 11.5 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 11.5 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.057 -0.795048)
           (cons 40 0)
           (cons 41 0)
           (cons 42 0)
           (cons 91 0)
           (list 10 8.057 -0.636552)
           (cons 40 0)
           (cons 41 0)
           (cons 42 0)
           (cons 91 0)
           (list 10 8.19924 -0.5888)
           (cons 40 0)
           (cons 41 0)
           (cons 42 0)
           (cons 91 0)
           (list 10 8.93076 -0.5888)
           (cons 40 0)
           (cons 41 0)
           (cons 42 0)
           (cons 91 0)
           (list 10 9.073 -0.636552)
           (cons 40 0)
           (cons 41 0)
           (cons 42 0)
           (cons 91 0)
           (list 10 9.073 -0.795048)
           (cons 40 0)
           (cons 41 0)
           (cons 42 0)
           (cons 91 0)
           (list 10 8.93076 -0.8428)
           (cons 40 0)
           (cons 41 0)
           (cons 42 0)
           (cons 91 0)
           (list 10 8.19924 -0.8428)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.057 -1.252248)
           (cons 40 0)
           (cons 41 0)
           (cons 42 0)
           (cons 91 0)
           (list 10 8.057 -1.093752)
           (cons 40 0)
           (cons 41 0)
           (cons 42 0)
           (cons 91 0)
           (list 10 8.19924 -1.046)
           (cons 40 0)
           (cons 41 0)
           (cons 42 0)
           (cons 91 0)
           (list 10 8.93076 -1.046)
           (cons 40 0)
           (cons 41 0)
           (cons 42 0)
           (cons 91 0)
           (list 10 9.073 -1.093752)
           (cons 40 0)
           (cons 41 0)
           (cons 42 0)
           (cons 91 0)
           (list 10 9.073 -1.252248)
           (cons 40 0)
           (cons 41 0)
           (cons 42 0)
           (cons 91 0)
           (list 10 8.93076 -1.3)
           (cons 40 0)
           (cons 41 0)
           (cons 42 0)
           (cons 91 0)
           (list 10 8.19924 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.057 0.636552)
           (cons 40 0)
           (cons 41 0)
           (cons 42 0)
           (cons 91 0)
           (list 10 8.057 0.795048)
           (cons 40 0)
           (cons 41 0)
           (cons 42 0)
           (cons 91 0)
           (list 10 8.19924 0.8428)
           (cons 40 0)
           (cons 41 0)
           (cons 42 0)
           (cons 91 0)
           (list 10 8.93076 0.8428)
           (cons 40 0)
           (cons 41 0)
           (cons 42 0)
           (cons 91 0)
           (list 10 9.073 0.795048)
           (cons 40 0)
           (cons 41 0)
           (cons 42 0)
           (cons 91 0)
           (list 10 9.073 0.636552)
           (cons 40 0)
           (cons 41 0)
           (cons 42 0)
           (cons 91 0)
           (list 10 8.93076 0.5888)
           (cons 40 0)
           (cons 41 0)
           (cons 42 0)
           (cons 91 0)
           (list 10 8.19924 0.5888)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.057 1.093752)
           (cons 40 0)
           (cons 41 0)
           (cons 42 0)
           (cons 91 0)
           (list 10 8.057 1.252248)
           (cons 40 0)
           (cons 41 0)
           (cons 42 0)
           (cons 91 0)
           (list 10 8.19924 1.3)
           (cons 40 0)
           (cons 41 0)
           (cons 42 0)
           (cons 91 0)
           (list 10 8.93076 1.3)
           (cons 40 0)
           (cons 41 0)
           (cons 42 0)
           (cons 91 0)
           (list 10 9.073 1.252248)
           (cons 40 0)
           (cons 41 0)
           (cons 42 0)
           (cons 91 0)
           (list 10 9.073 1.093752)
           (cons 40 0)
           (cons 41 0)
           (cons 42 0)
           (cons 91 0)
           (list 10 8.93076 1.046)
           (cons 40 0)
           (cons 41 0)
           (cons 42 0)
           (cons 91 0)
           (list 10 8.19924 1.046)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.327 -0.795048)
           (cons 40 0)
           (cons 41 0)
           (cons 42 0)
           (cons 91 0)
           (list 10 9.327 -0.636552)
           (cons 40 0)
           (cons 41 0)
           (cons 42 0)
           (cons 91 0)
           (list 10 9.46924 -0.5888)
           (cons 40 0)
           (cons 41 0)
           (cons 42 0)
           (cons 91 0)
           (list 10 10.20076 -0.5888)
           (cons 40 0)
           (cons 41 0)
           (cons 42 0)
           (cons 91 0)
           (list 10 10.343 -0.636552)
           (cons 40 0)
           (cons 41 0)
           (cons 42 0)
           (cons 91 0)
           (list 10 10.343 -0.795048)
           (cons 40 0)
           (cons 41 0)
           (cons 42 0)
           (cons 91 0)
           (list 10 10.20076 -0.8428)
           (cons 40 0)
           (cons 41 0)
           (cons 42 0)
           (cons 91 0)
           (list 10 9.46924 -0.8428)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.327 -1.252248)
           (cons 40 0)
           (cons 41 0)
           (cons 42 0)
           (cons 91 0)
           (list 10 9.327 -1.093752)
           (cons 40 0)
           (cons 41 0)
           (cons 42 0)
           (cons 91 0)
           (list 10 9.46924 -1.046)
           (cons 40 0)
           (cons 41 0)
           (cons 42 0)
           (cons 91 0)
           (list 10 10.20076 -1.046)
           (cons 40 0)
           (cons 41 0)
           (cons 42 0)
           (cons 91 0)
           (list 10 10.343 -1.093752)
           (cons 40 0)
           (cons 41 0)
           (cons 42 0)
           (cons 91 0)
           (list 10 10.343 -1.252248)
           (cons 40 0)
           (cons 41 0)
           (cons 42 0)
           (cons 91 0)
           (list 10 10.20076 -1.3)
           (cons 40 0)
           (cons 41 0)
           (cons 42 0)
           (cons 91 0)
           (list 10 9.46924 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.327 0.636552)
           (cons 40 0)
           (cons 41 0)
           (cons 42 0)
           (cons 91 0)
           (list 10 9.327 0.795048)
           (cons 40 0)
           (cons 41 0)
           (cons 42 0)
           (cons 91 0)
           (list 10 9.46924 0.8428)
           (cons 40 0)
           (cons 41 0)
           (cons 42 0)
           (cons 91 0)
           (list 10 10.20076 0.8428)
           (cons 40 0)
           (cons 41 0)
           (cons 42 0)
           (cons 91 0)
           (list 10 10.343 0.795048)
           (cons 40 0)
           (cons 41 0)
           (cons 42 0)
           (cons 91 0)
           (list 10 10.343 0.636552)
           (cons 40 0)
           (cons 41 0)
           (cons 42 0)
           (cons 91 0)
           (list 10 10.20076 0.5888)
           (cons 40 0)
           (cons 41 0)
           (cons 42 0)
           (cons 91 0)
           (list 10 9.46924 0.5888)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.327 1.093752)
           (cons 40 0)
           (cons 41 0)
           (cons 42 0)
           (cons 91 0)
           (list 10 9.327 1.252248)
           (cons 40 0)
           (cons 41 0)
           (cons 42 0)
           (cons 91 0)
           (list 10 9.46924 1.3)
           (cons 40 0)
           (cons 41 0)
           (cons 42 0)
           (cons 91 0)
           (list 10 10.20076 1.3)
           (cons 40 0)
           (cons 41 0)
           (cons 42 0)
           (cons 91 0)
           (list 10 10.343 1.252248)
           (cons 40 0)
           (cons 41 0)
           (cons 42 0)
           (cons 91 0)
           (list 10 10.343 1.093752)
           (cons 40 0)
           (cons 41 0)
           (cons 42 0)
           (cons 91 0)
           (list 10 10.20076 1.046)
           (cons 40 0)
           (cons 41 0)
           (cons 42 0)
           (cons 91 0)
           (list 10 9.46924 1.046)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 11.5 1.3 0)
           (cons 50 0)
          )
         )
         (entmake
          (list
           (cons 0 "POINT")
           (cons 100 "AcDbEntity")
           (cons 67 0)
           (cons 8 "0")
           (cons 100 "AcDbPoint")
           (list 10 11.5 -1.3 0)
           (cons 50 0)
          )
         )
         (entmake
          (list
           (cons 0 "POINT")
           (cons 100 "AcDbEntity")
           (cons 67 0)
           (cons 8 "0")
           (cons 100 "AcDbPoint")
           (list 10 0.8 -1.3 0)
           (cons 50 0)
          )
         )
         (entmake
          (list
           (cons 0 "POINT")
           (cons 100 "AcDbEntity")
           (cons 67 0)
           (cons 8 "0")
           (cons 100 "AcDbPoint")
           (list 10 0.8 1.3 0)
           (cons 50 0)
          )
         )
         (entmake
          (list
           (cons 0 "POINT")
           (cons 100 "AcDbEntity")
           (cons 67 0)
           (cons 8 "0")
           (cons 100 "AcDbPoint")
           (list 10 0.8 0 0)
           (cons 50 0)
          )
         )
         (entmake
          (list
           (cons 0 "POINT")
           (cons 100 "AcDbEntity")
           (cons 67 0)
           (cons 8 "0")
           (cons 100 "AcDbPoint")
           (list 10 9.2 1.3 0)
           (cons 50 0)
          )
         )
         (entmake
          (list
           (cons 0 "POINT")
           (cons 100 "AcDbEntity")
           (cons 67 0)
           (cons 8 "0")
           (cons 100 "AcDbPoint")
           (list 10 9.2 -1.3 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 11.5 -1.3)
           (cons 40 0)
           (cons 41 0)
           (cons 42 0)
           (cons 91 0)
           (list 10 11.5 1.3)
           (cons 40 0)
           (cons 41 0)
           (cons 42 0)
           (cons 91 0)
           (list 10 0 1.3)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.1 0.56666667 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 0.23333333 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.1 0)
           (cons 40 0.2)
           (cons 1 "9.20")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.43333333 0)
           (cons 40 0.2)
           (cons 1 "0.00")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.76666667 0)
           (cons 40 0.2)
           (cons 1 "39.883")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelLeftM2")
           (list 10 0.8 -1.046 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM2")
           (list 10 0.8 1.046 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "TAC-2017-BTD-TRAILER2"))
        (progn
         (entmake)
         (entmake
          (list
           (cons 0 "BLOCK")
           (cons 2 "TAC-2017-BTD-TRAILER2")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.6 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.6 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 1.3 0 0)
           (cons 40 0.104)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1062 -0.7445528)
           (cons 40 0)
           (cons 41 0)
           (cons 42 0)
           (cons 91 0)
           (list 10 7.1062 -0.5702072)
           (cons 40 0)
           (cons 41 0)
           (cons 42 0)
           (cons 91 0)
           (list 10 7.262664 -0.51768)
           (cons 40 0)
           (cons 41 0)
           (cons 42 0)
           (cons 91 0)
           (list 10 8.067336 -0.51768)
           (cons 40 0)
           (cons 41 0)
           (cons 42 0)
           (cons 91 0)
           (list 10 8.2238 -0.5702072)
           (cons 40 0)
           (cons 41 0)
           (cons 42 0)
           (cons 91 0)
           (list 10 8.2238 -0.7445528)
           (cons 40 0)
           (cons 41 0)
           (cons 42 0)
           (cons 91 0)
           (list 10 8.067336 -0.79708)
           (cons 40 0)
           (cons 41 0)
           (cons 42 0)
           (cons 91 0)
           (list 10 7.262664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1062 -1.2474728)
           (cons 40 0)
           (cons 41 0)
           (cons 42 0)
           (cons 91 0)
           (list 10 7.1062 -1.0731272)
           (cons 40 0)
           (cons 41 0)
           (cons 42 0)
           (cons 91 0)
           (list 10 7.262664 -1.0206)
           (cons 40 0)
           (cons 41 0)
           (cons 42 0)
           (cons 91 0)
           (list 10 8.067336 -1.0206)
           (cons 40 0)
           (cons 41 0)
           (cons 42 0)
           (cons 91 0)
           (list 10 8.2238 -1.0731272)
           (cons 40 0)
           (cons 41 0)
           (cons 42 0)
           (cons 91 0)
           (list 10 8.2238 -1.2474728)
           (cons 40 0)
           (cons 41 0)
           (cons 42 0)
           (cons 91 0)
           (list 10 8.067336 -1.3)
           (cons 40 0)
           (cons 41 0)
           (cons 42 0)
           (cons 91 0)
           (list 10 7.262664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1062 0.5702072)
           (cons 40 0)
           (cons 41 0)
           (cons 42 0)
           (cons 91 0)
           (list 10 7.1062 0.7445528)
           (cons 40 0)
           (cons 41 0)
           (cons 42 0)
           (cons 91 0)
           (list 10 7.262664 0.79708)
           (cons 40 0)
           (cons 41 0)
           (cons 42 0)
           (cons 91 0)
           (list 10 8.067336 0.79708)
           (cons 40 0)
           (cons 41 0)
           (cons 42 0)
           (cons 91 0)
           (list 10 8.2238 0.7445528)
           (cons 40 0)
           (cons 41 0)
           (cons 42 0)
           (cons 91 0)
           (list 10 8.2238 0.5702072)
           (cons 40 0)
           (cons 41 0)
           (cons 42 0)
           (cons 91 0)
           (list 10 8.067336 0.51768)
           (cons 40 0)
           (cons 41 0)
           (cons 42 0)
           (cons 91 0)
           (list 10 7.262664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1062 1.0731272)
           (cons 40 0)
           (cons 41 0)
           (cons 42 0)
           (cons 91 0)
           (list 10 7.1062 1.2474728)
           (cons 40 0)
           (cons 41 0)
           (cons 42 0)
           (cons 91 0)
           (list 10 7.262664 1.3)
           (cons 40 0)
           (cons 41 0)
           (cons 42 0)
           (cons 91 0)
           (list 10 8.067336 1.3)
           (cons 40 0)
           (cons 41 0)
           (cons 42 0)
           (cons 91 0)
           (list 10 8.2238 1.2474728)
           (cons 40 0)
           (cons 41 0)
           (cons 42 0)
           (cons 91 0)
           (list 10 8.2238 1.0731272)
           (cons 40 0)
           (cons 41 0)
           (cons 42 0)
           (cons 91 0)
           (list 10 8.067336 1.0206)
           (cons 40 0)
           (cons 41 0)
           (cons 42 0)
           (cons 91 0)
           (list 10 7.262664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.3762 -0.7445528)
           (cons 40 0)
           (cons 41 0)
           (cons 42 0)
           (cons 91 0)
           (list 10 8.3762 -0.5702072)
           (cons 40 0)
           (cons 41 0)
           (cons 42 0)
           (cons 91 0)
           (list 10 8.532664 -0.51768)
           (cons 40 0)
           (cons 41 0)
           (cons 42 0)
           (cons 91 0)
           (list 10 9.337336 -0.51768)
           (cons 40 0)
           (cons 41 0)
           (cons 42 0)
           (cons 91 0)
           (list 10 9.4938 -0.5702072)
           (cons 40 0)
           (cons 41 0)
           (cons 42 0)
           (cons 91 0)
           (list 10 9.4938 -0.7445528)
           (cons 40 0)
           (cons 41 0)
           (cons 42 0)
           (cons 91 0)
           (list 10 9.337336 -0.79708)
           (cons 40 0)
           (cons 41 0)
           (cons 42 0)
           (cons 91 0)
           (list 10 8.532664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.3762 -1.2474728)
           (cons 40 0)
           (cons 41 0)
           (cons 42 0)
           (cons 91 0)
           (list 10 8.3762 -1.0731272)
           (cons 40 0)
           (cons 41 0)
           (cons 42 0)
           (cons 91 0)
           (list 10 8.532664 -1.0206)
           (cons 40 0)
           (cons 41 0)
           (cons 42 0)
           (cons 91 0)
           (list 10 9.337336 -1.0206)
           (cons 40 0)
           (cons 41 0)
           (cons 42 0)
           (cons 91 0)
           (list 10 9.4938 -1.0731272)
           (cons 40 0)
           (cons 41 0)
           (cons 42 0)
           (cons 91 0)
           (list 10 9.4938 -1.2474728)
           (cons 40 0)
           (cons 41 0)
           (cons 42 0)
           (cons 91 0)
           (list 10 9.337336 -1.3)
           (cons 40 0)
           (cons 41 0)
           (cons 42 0)
           (cons 91 0)
           (list 10 8.532664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.3762 0.5702072)
           (cons 40 0)
           (cons 41 0)
           (cons 42 0)
           (cons 91 0)
           (list 10 8.3762 0.7445528)
           (cons 40 0)
           (cons 41 0)
           (cons 42 0)
           (cons 91 0)
           (list 10 8.532664 0.79708)
           (cons 40 0)
           (cons 41 0)
           (cons 42 0)
           (cons 91 0)
           (list 10 9.337336 0.79708)
           (cons 40 0)
           (cons 41 0)
           (cons 42 0)
           (cons 91 0)
           (list 10 9.4938 0.7445528)
           (cons 40 0)
           (cons 41 0)
           (cons 42 0)
           (cons 91 0)
           (list 10 9.4938 0.5702072)
           (cons 40 0)
           (cons 41 0)
           (cons 42 0)
           (cons 91 0)
           (list 10 9.337336 0.51768)
           (cons 40 0)
           (cons 41 0)
           (cons 42 0)
           (cons 91 0)
           (list 10 8.532664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.3762 1.0731272)
           (cons 40 0)
           (cons 41 0)
           (cons 42 0)
           (cons 91 0)
           (list 10 8.3762 1.2474728)
           (cons 40 0)
           (cons 41 0)
           (cons 42 0)
           (cons 91 0)
           (list 10 8.532664 1.3)
           (cons 40 0)
           (cons 41 0)
           (cons 42 0)
           (cons 91 0)
           (list 10 9.337336 1.3)
           (cons 40 0)
           (cons 41 0)
           (cons 42 0)
           (cons 91 0)
           (list 10 9.4938 1.2474728)
           (cons 40 0)
           (cons 41 0)
           (cons 42 0)
           (cons 91 0)
           (list 10 9.4938 1.0731272)
           (cons 40 0)
           (cons 41 0)
           (cons 42 0)
           (cons 91 0)
           (list 10 9.337336 1.0206)
           (cons 40 0)
           (cons 41 0)
           (cons 42 0)
           (cons 91 0)
           (list 10 8.532664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 1.3 0 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 8.3 1.3 0)
           (cons 50 0)
          )
         )
         (entmake
          (list
           (cons 0 "POINT")
           (cons 100 "AcDbEntity")
           (cons 67 0)
           (cons 8 "0")
           (cons 100 "AcDbPoint")
           (list 10 8.3 -1.3 0)
           (cons 50 0)
          )
         )
         (entmake
          (list
           (cons 0 "POINT")
           (cons 100 "AcDbEntity")
           (cons 67 0)
           (cons 8 "0")
           (cons 100 "AcDbPoint")
           (list 10 9.6 1.3 0)
           (cons 50 0)
          )
         )
         (entmake
          (list
           (cons 0 "POINT")
           (cons 100 "AcDbEntity")
           (cons 67 0)
           (cons 8 "0")
           (cons 100 "AcDbPoint")
           (list 10 9.6 -1.3 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 9.6 -1.3)
           (cons 40 0)
           (cons 41 0)
           (cons 42 0)
           (cons 91 0)
           (list 10 9.6 1.3)
           (cons 40 0)
           (cons 41 0)
           (cons 42 0)
           (cons 91 0)
           (list 10 0 1.3)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.6 0.56666667 0)
           (cons 40 0.2)
           (cons 1 "1.30")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 0.23333333 0)
           (cons 40 0.2)
           (cons 1 "1.30")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.1 0)
           (cons 40 0.2)
           (cons 1 "8.30")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.43333333 0)
           (cons 40 0.2)
           (cons 1 "0.00")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "TAC-2017-BTD-TRAILER1"))
        (progn
         (entmake)
         (entmake
          (list
           (cons 0 "BLOCK")
           (cons 2 "TAC-2017-BTD-TRAILER1")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.5 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.5 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 11.57 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 11.57 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.5 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.5 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 1.3 0 0)
           (cons 40 0.104)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 11.1 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 11.36263966 -0.26263966 0)
           (list 11 11.36263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.4712 -0.7445528)
           (cons 40 0)
           (cons 41 0)
           (cons 42 0)
           (cons 91 0)
           (list 10 8.4712 -0.5702072)
           (cons 40 0)
           (cons 41 0)
           (cons 42 0)
           (cons 91 0)
           (list 10 8.627664 -0.51768)
           (cons 40 0)
           (cons 41 0)
           (cons 42 0)
           (cons 91 0)
           (list 10 9.432336 -0.51768)
           (cons 40 0)
           (cons 41 0)
           (cons 42 0)
           (cons 91 0)
           (list 10 9.5888 -0.5702072)
           (cons 40 0)
           (cons 41 0)
           (cons 42 0)
           (cons 91 0)
           (list 10 9.5888 -0.7445528)
           (cons 40 0)
           (cons 41 0)
           (cons 42 0)
           (cons 91 0)
           (list 10 9.432336 -0.79708)
           (cons 40 0)
           (cons 41 0)
           (cons 42 0)
           (cons 91 0)
           (list 10 8.627664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.4712 -1.2474728)
           (cons 40 0)
           (cons 41 0)
           (cons 42 0)
           (cons 91 0)
           (list 10 8.4712 -1.0731272)
           (cons 40 0)
           (cons 41 0)
           (cons 42 0)
           (cons 91 0)
           (list 10 8.627664 -1.0206)
           (cons 40 0)
           (cons 41 0)
           (cons 42 0)
           (cons 91 0)
           (list 10 9.432336 -1.0206)
           (cons 40 0)
           (cons 41 0)
           (cons 42 0)
           (cons 91 0)
           (list 10 9.5888 -1.0731272)
           (cons 40 0)
           (cons 41 0)
           (cons 42 0)
           (cons 91 0)
           (list 10 9.5888 -1.2474728)
           (cons 40 0)
           (cons 41 0)
           (cons 42 0)
           (cons 91 0)
           (list 10 9.432336 -1.3)
           (cons 40 0)
           (cons 41 0)
           (cons 42 0)
           (cons 91 0)
           (list 10 8.627664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.4712 0.5702072)
           (cons 40 0)
           (cons 41 0)
           (cons 42 0)
           (cons 91 0)
           (list 10 8.4712 0.7445528)
           (cons 40 0)
           (cons 41 0)
           (cons 42 0)
           (cons 91 0)
           (list 10 8.627664 0.79708)
           (cons 40 0)
           (cons 41 0)
           (cons 42 0)
           (cons 91 0)
           (list 10 9.432336 0.79708)
           (cons 40 0)
           (cons 41 0)
           (cons 42 0)
           (cons 91 0)
           (list 10 9.5888 0.7445528)
           (cons 40 0)
           (cons 41 0)
           (cons 42 0)
           (cons 91 0)
           (list 10 9.5888 0.5702072)
           (cons 40 0)
           (cons 41 0)
           (cons 42 0)
           (cons 91 0)
           (list 10 9.432336 0.51768)
           (cons 40 0)
           (cons 41 0)
           (cons 42 0)
           (cons 91 0)
           (list 10 8.627664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.4712 1.0731272)
           (cons 40 0)
           (cons 41 0)
           (cons 42 0)
           (cons 91 0)
           (list 10 8.4712 1.2474728)
           (cons 40 0)
           (cons 41 0)
           (cons 42 0)
           (cons 91 0)
           (list 10 8.627664 1.3)
           (cons 40 0)
           (cons 41 0)
           (cons 42 0)
           (cons 91 0)
           (list 10 9.432336 1.3)
           (cons 40 0)
           (cons 41 0)
           (cons 42 0)
           (cons 91 0)
           (list 10 9.5888 1.2474728)
           (cons 40 0)
           (cons 41 0)
           (cons 42 0)
           (cons 91 0)
           (list 10 9.5888 1.0731272)
           (cons 40 0)
           (cons 41 0)
           (cons 42 0)
           (cons 91 0)
           (list 10 9.432336 1.0206)
           (cons 40 0)
           (cons 41 0)
           (cons 42 0)
           (cons 91 0)
           (list 10 8.627664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.7412 -0.7445528)
           (cons 40 0)
           (cons 41 0)
           (cons 42 0)
           (cons 91 0)
           (list 10 9.7412 -0.5702072)
           (cons 40 0)
           (cons 41 0)
           (cons 42 0)
           (cons 91 0)
           (list 10 9.897664 -0.51768)
           (cons 40 0)
           (cons 41 0)
           (cons 42 0)
           (cons 91 0)
           (list 10 10.702336 -0.51768)
           (cons 40 0)
           (cons 41 0)
           (cons 42 0)
           (cons 91 0)
           (list 10 10.8588 -0.5702072)
           (cons 40 0)
           (cons 41 0)
           (cons 42 0)
           (cons 91 0)
           (list 10 10.8588 -0.7445528)
           (cons 40 0)
           (cons 41 0)
           (cons 42 0)
           (cons 91 0)
           (list 10 10.702336 -0.79708)
           (cons 40 0)
           (cons 41 0)
           (cons 42 0)
           (cons 91 0)
           (list 10 9.897664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.7412 -1.2474728)
           (cons 40 0)
           (cons 41 0)
           (cons 42 0)
           (cons 91 0)
           (list 10 9.7412 -1.0731272)
           (cons 40 0)
           (cons 41 0)
           (cons 42 0)
           (cons 91 0)
           (list 10 9.897664 -1.0206)
           (cons 40 0)
           (cons 41 0)
           (cons 42 0)
           (cons 91 0)
           (list 10 10.702336 -1.0206)
           (cons 40 0)
           (cons 41 0)
           (cons 42 0)
           (cons 91 0)
           (list 10 10.8588 -1.0731272)
           (cons 40 0)
           (cons 41 0)
           (cons 42 0)
           (cons 91 0)
           (list 10 10.8588 -1.2474728)
           (cons 40 0)
           (cons 41 0)
           (cons 42 0)
           (cons 91 0)
           (list 10 10.702336 -1.3)
           (cons 40 0)
           (cons 41 0)
           (cons 42 0)
           (cons 91 0)
           (list 10 9.897664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.7412 0.5702072)
           (cons 40 0)
           (cons 41 0)
           (cons 42 0)
           (cons 91 0)
           (list 10 9.7412 0.7445528)
           (cons 40 0)
           (cons 41 0)
           (cons 42 0)
           (cons 91 0)
           (list 10 9.897664 0.79708)
           (cons 40 0)
           (cons 41 0)
           (cons 42 0)
           (cons 91 0)
           (list 10 10.702336 0.79708)
           (cons 40 0)
           (cons 41 0)
           (cons 42 0)
           (cons 91 0)
           (list 10 10.8588 0.7445528)
           (cons 40 0)
           (cons 41 0)
           (cons 42 0)
           (cons 91 0)
           (list 10 10.8588 0.5702072)
           (cons 40 0)
           (cons 41 0)
           (cons 42 0)
           (cons 91 0)
           (list 10 10.702336 0.51768)
           (cons 40 0)
           (cons 41 0)
           (cons 42 0)
           (cons 91 0)
           (list 10 9.897664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.7412 1.0731272)
           (cons 40 0)
           (cons 41 0)
           (cons 42 0)
           (cons 91 0)
           (list 10 9.7412 1.2474728)
           (cons 40 0)
           (cons 41 0)
           (cons 42 0)
           (cons 91 0)
           (list 10 9.897664 1.3)
           (cons 40 0)
           (cons 41 0)
           (cons 42 0)
           (cons 91 0)
           (list 10 10.702336 1.3)
           (cons 40 0)
           (cons 41 0)
           (cons 42 0)
           (cons 91 0)
           (list 10 10.8588 1.2474728)
           (cons 40 0)
           (cons 41 0)
           (cons 42 0)
           (cons 91 0)
           (list 10 10.8588 1.0731272)
           (cons 40 0)
           (cons 41 0)
           (cons 42 0)
           (cons 91 0)
           (list 10 10.702336 1.0206)
           (cons 40 0)
           (cons 41 0)
           (cons 42 0)
           (cons 91 0)
           (list 10 9.897664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.0112 -0.7445528)
           (cons 40 0)
           (cons 41 0)
           (cons 42 0)
           (cons 91 0)
           (list 10 11.0112 -0.5702072)
           (cons 40 0)
           (cons 41 0)
           (cons 42 0)
           (cons 91 0)
           (list 10 11.167664 -0.51768)
           (cons 40 0)
           (cons 41 0)
           (cons 42 0)
           (cons 91 0)
           (list 10 11.972336 -0.51768)
           (cons 40 0)
           (cons 41 0)
           (cons 42 0)
           (cons 91 0)
           (list 10 12.1288 -0.5702072)
           (cons 40 0)
           (cons 41 0)
           (cons 42 0)
           (cons 91 0)
           (list 10 12.1288 -0.7445528)
           (cons 40 0)
           (cons 41 0)
           (cons 42 0)
           (cons 91 0)
           (list 10 11.972336 -0.79708)
           (cons 40 0)
           (cons 41 0)
           (cons 42 0)
           (cons 91 0)
           (list 10 11.167664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.0112 -1.2474728)
           (cons 40 0)
           (cons 41 0)
           (cons 42 0)
           (cons 91 0)
           (list 10 11.0112 -1.0731272)
           (cons 40 0)
           (cons 41 0)
           (cons 42 0)
           (cons 91 0)
           (list 10 11.167664 -1.0206)
           (cons 40 0)
           (cons 41 0)
           (cons 42 0)
           (cons 91 0)
           (list 10 11.972336 -1.0206)
           (cons 40 0)
           (cons 41 0)
           (cons 42 0)
           (cons 91 0)
           (list 10 12.1288 -1.0731272)
           (cons 40 0)
           (cons 41 0)
           (cons 42 0)
           (cons 91 0)
           (list 10 12.1288 -1.2474728)
           (cons 40 0)
           (cons 41 0)
           (cons 42 0)
           (cons 91 0)
           (list 10 11.972336 -1.3)
           (cons 40 0)
           (cons 41 0)
           (cons 42 0)
           (cons 91 0)
           (list 10 11.167664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.0112 0.5702072)
           (cons 40 0)
           (cons 41 0)
           (cons 42 0)
           (cons 91 0)
           (list 10 11.0112 0.7445528)
           (cons 40 0)
           (cons 41 0)
           (cons 42 0)
           (cons 91 0)
           (list 10 11.167664 0.79708)
           (cons 40 0)
           (cons 41 0)
           (cons 42 0)
           (cons 91 0)
           (list 10 11.972336 0.79708)
           (cons 40 0)
           (cons 41 0)
           (cons 42 0)
           (cons 91 0)
           (list 10 12.1288 0.7445528)
           (cons 40 0)
           (cons 41 0)
           (cons 42 0)
           (cons 91 0)
           (list 10 12.1288 0.5702072)
           (cons 40 0)
           (cons 41 0)
           (cons 42 0)
           (cons 91 0)
           (list 10 11.972336 0.51768)
           (cons 40 0)
           (cons 41 0)
           (cons 42 0)
           (cons 91 0)
           (list 10 11.167664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.0112 1.0731272)
           (cons 40 0)
           (cons 41 0)
           (cons 42 0)
           (cons 91 0)
           (list 10 11.0112 1.2474728)
           (cons 40 0)
           (cons 41 0)
           (cons 42 0)
           (cons 91 0)
           (list 10 11.167664 1.3)
           (cons 40 0)
           (cons 41 0)
           (cons 42 0)
           (cons 91 0)
           (list 10 11.972336 1.3)
           (cons 40 0)
           (cons 41 0)
           (cons 42 0)
           (cons 91 0)
           (list 10 12.1288 1.2474728)
           (cons 40 0)
           (cons 41 0)
           (cons 42 0)
           (cons 91 0)
           (list 10 12.1288 1.0731272)
           (cons 40 0)
           (cons 41 0)
           (cons 42 0)
           (cons 91 0)
           (list 10 11.972336 1.0206)
           (cons 40 0)
           (cons 41 0)
           (cons 42 0)
           (cons 91 0)
           (list 10 11.167664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 1.3 0 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 10.3 1.3 0)
           (cons 50 0)
          )
         )
         (entmake
          (list
           (cons 0 "POINT")
           (cons 100 "AcDbEntity")
           (cons 67 0)
           (cons 8 "0")
           (cons 100 "AcDbPoint")
           (list 10 10.3 -1.3 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 11.57 -1.3)
           (cons 40 0)
           (cons 41 0)
           (cons 42 0)
           (cons 91 0)
           (list 10 11.57 1.3)
           (cons 40 0)
           (cons 41 0)
           (cons 42 0)
           (cons 91 0)
           (list 10 0 1.3)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 11.1 0 0)
           (cons 50 0)
          )
         )
         (entmake
          (list
           (cons 0 "ATTDEF")
           (cons 100 "AcDbEntity")
           (cons 67 0)
           (cons 8 "0")
           (cons 100 "AcDbText")
           (list 10 0.6 0.56666667 0)
           (cons 40 0.2)
           (cons 1 "1.30")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 0.23333333 0)
           (cons 40 0.2)
           (cons 1 "1.30")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.1 0)
           (cons 40 0.2)
           (cons 1 "10.30")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.43333333 0)
           (cons 40 0.2)
           (cons 1 "11.10")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "TAC-2017-BTD-TRUCK"))
        (progn
         (entmake)
         (entmake
          (list
           (cons 0 "BLOCK")
           (cons 2 "TAC-2017-BTD-TRUCK")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.535 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.535 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 6.9 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 7.16263966 -0.26263966 0)
           (list 11 7.16263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.7062 -0.7445528)
           (cons 40 0)
           (cons 41 0)
           (cons 42 0)
           (cons 91 0)
           (list 10 5.7062 -0.5702072)
           (cons 40 0)
           (cons 41 0)
           (cons 42 0)
           (cons 91 0)
           (list 10 5.862664 -0.51768)
           (cons 40 0)
           (cons 41 0)
           (cons 42 0)
           (cons 91 0)
           (list 10 6.667336 -0.51768)
           (cons 40 0)
           (cons 41 0)
           (cons 42 0)
           (cons 91 0)
           (list 10 6.8238 -0.5702072)
           (cons 40 0)
           (cons 41 0)
           (cons 42 0)
           (cons 91 0)
           (list 10 6.8238 -0.7445528)
           (cons 40 0)
           (cons 41 0)
           (cons 42 0)
           (cons 91 0)
           (list 10 6.667336 -0.79708)
           (cons 40 0)
           (cons 41 0)
           (cons 42 0)
           (cons 91 0)
           (list 10 5.862664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.7062 -1.2474728)
           (cons 40 0)
           (cons 41 0)
           (cons 42 0)
           (cons 91 0)
           (list 10 5.7062 -1.0731272)
           (cons 40 0)
           (cons 41 0)
           (cons 42 0)
           (cons 91 0)
           (list 10 5.862664 -1.0206)
           (cons 40 0)
           (cons 41 0)
           (cons 42 0)
           (cons 91 0)
           (list 10 6.667336 -1.0206)
           (cons 40 0)
           (cons 41 0)
           (cons 42 0)
           (cons 91 0)
           (list 10 6.8238 -1.0731272)
           (cons 40 0)
           (cons 41 0)
           (cons 42 0)
           (cons 91 0)
           (list 10 6.8238 -1.2474728)
           (cons 40 0)
           (cons 41 0)
           (cons 42 0)
           (cons 91 0)
           (list 10 6.667336 -1.3)
           (cons 40 0)
           (cons 41 0)
           (cons 42 0)
           (cons 91 0)
           (list 10 5.862664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.7062 0.5702072)
           (cons 40 0)
           (cons 41 0)
           (cons 42 0)
           (cons 91 0)
           (list 10 5.7062 0.7445528)
           (cons 40 0)
           (cons 41 0)
           (cons 42 0)
           (cons 91 0)
           (list 10 5.862664 0.79708)
           (cons 40 0)
           (cons 41 0)
           (cons 42 0)
           (cons 91 0)
           (list 10 6.667336 0.79708)
           (cons 40 0)
           (cons 41 0)
           (cons 42 0)
           (cons 91 0)
           (list 10 6.8238 0.7445528)
           (cons 40 0)
           (cons 41 0)
           (cons 42 0)
           (cons 91 0)
           (list 10 6.8238 0.5702072)
           (cons 40 0)
           (cons 41 0)
           (cons 42 0)
           (cons 91 0)
           (list 10 6.667336 0.51768)
           (cons 40 0)
           (cons 41 0)
           (cons 42 0)
           (cons 91 0)
           (list 10 5.862664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.7062 1.0731272)
           (cons 40 0)
           (cons 41 0)
           (cons 42 0)
           (cons 91 0)
           (list 10 5.7062 1.2474728)
           (cons 40 0)
           (cons 41 0)
           (cons 42 0)
           (cons 91 0)
           (list 10 5.862664 1.3)
           (cons 40 0)
           (cons 41 0)
           (cons 42 0)
           (cons 91 0)
           (list 10 6.667336 1.3)
           (cons 40 0)
           (cons 41 0)
           (cons 42 0)
           (cons 91 0)
           (list 10 6.8238 1.2474728)
           (cons 40 0)
           (cons 41 0)
           (cons 42 0)
           (cons 91 0)
           (list 10 6.8238 1.0731272)
           (cons 40 0)
           (cons 41 0)
           (cons 42 0)
           (cons 91 0)
           (list 10 6.667336 1.0206)
           (cons 40 0)
           (cons 41 0)
           (cons 42 0)
           (cons 91 0)
           (list 10 5.862664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.9762 -0.7445528)
           (cons 40 0)
           (cons 41 0)
           (cons 42 0)
           (cons 91 0)
           (list 10 6.9762 -0.5702072)
           (cons 40 0)
           (cons 41 0)
           (cons 42 0)
           (cons 91 0)
           (list 10 7.132664 -0.51768)
           (cons 40 0)
           (cons 41 0)
           (cons 42 0)
           (cons 91 0)
           (list 10 7.937336 -0.51768)
           (cons 40 0)
           (cons 41 0)
           (cons 42 0)
           (cons 91 0)
           (list 10 8.0938 -0.5702072)
           (cons 40 0)
           (cons 41 0)
           (cons 42 0)
           (cons 91 0)
           (list 10 8.0938 -0.7445528)
           (cons 40 0)
           (cons 41 0)
           (cons 42 0)
           (cons 91 0)
           (list 10 7.937336 -0.79708)
           (cons 40 0)
           (cons 41 0)
           (cons 42 0)
           (cons 91 0)
           (list 10 7.132664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.9762 -1.2474728)
           (cons 40 0)
           (cons 41 0)
           (cons 42 0)
           (cons 91 0)
           (list 10 6.9762 -1.0731272)
           (cons 40 0)
           (cons 41 0)
           (cons 42 0)
           (cons 91 0)
           (list 10 7.132664 -1.0206)
           (cons 40 0)
           (cons 41 0)
           (cons 42 0)
           (cons 91 0)
           (list 10 7.937336 -1.0206)
           (cons 40 0)
           (cons 41 0)
           (cons 42 0)
           (cons 91 0)
           (list 10 8.0938 -1.0731272)
           (cons 40 0)
           (cons 41 0)
           (cons 42 0)
           (cons 91 0)
           (list 10 8.0938 -1.2474728)
           (cons 40 0)
           (cons 41 0)
           (cons 42 0)
           (cons 91 0)
           (list 10 7.937336 -1.3)
           (cons 40 0)
           (cons 41 0)
           (cons 42 0)
           (cons 91 0)
           (list 10 7.132664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.9762 0.5702072)
           (cons 40 0)
           (cons 41 0)
           (cons 42 0)
           (cons 91 0)
           (list 10 6.9762 0.7445528)
           (cons 40 0)
           (cons 41 0)
           (cons 42 0)
           (cons 91 0)
           (list 10 7.132664 0.79708)
           (cons 40 0)
           (cons 41 0)
           (cons 42 0)
           (cons 91 0)
           (list 10 7.937336 0.79708)
           (cons 40 0)
           (cons 41 0)
           (cons 42 0)
           (cons 91 0)
           (list 10 8.0938 0.7445528)
           (cons 40 0)
           (cons 41 0)
           (cons 42 0)
           (cons 91 0)
           (list 10 8.0938 0.5702072)
           (cons 40 0)
           (cons 41 0)
           (cons 42 0)
           (cons 91 0)
           (list 10 7.937336 0.51768)
           (cons 40 0)
           (cons 41 0)
           (cons 42 0)
           (cons 91 0)
           (list 10 7.132664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.9762 1.0731272)
           (cons 40 0)
           (cons 41 0)
           (cons 42 0)
           (cons 91 0)
           (list 10 6.9762 1.2474728)
           (cons 40 0)
           (cons 41 0)
           (cons 42 0)
           (cons 91 0)
           (list 10 7.132664 1.3)
           (cons 40 0)
           (cons 41 0)
           (cons 42 0)
           (cons 91 0)
           (list 10 7.937336 1.3)
           (cons 40 0)
           (cons 41 0)
           (cons 42 0)
           (cons 91 0)
           (list 10 8.0938 1.2474728)
           (cons 40 0)
           (cons 41 0)
           (cons 42 0)
           (cons 91 0)
           (list 10 8.0938 1.0731272)
           (cons 40 0)
           (cons 41 0)
           (cons 42 0)
           (cons 91 0)
           (list 10 7.937336 1.0206)
           (cons 40 0)
           (cons 41 0)
           (cons 42 0)
           (cons 91 0)
           (list 10 7.132664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0.8 0 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0.8 1.3 0)
           (cons 50 0)
          )
         )
         (entmake
          (list
           (cons 0 "POINT")
           (cons 100 "AcDbEntity")
           (cons 67 0)
           (cons 8 "0")
           (cons 100 "AcDbPoint")
           (list 10 0.8 -1.3 0)
           (cons 50 0)
          )
         )
         (entmake
          (list
           (cons 0 "POINT")
           (cons 100 "AcDbEntity")
           (cons 67 0)
           (cons 8 "0")
           (cons 100 "AcDbPoint")
           (list 10 6.9 -1.3 0)
           (cons 50 0)
          )
         )
         (entmake
          (list
           (cons 0 "POINT")
           (cons 100 "AcDbEntity")
           (cons 67 0)
           (cons 8 "0")
           (cons 100 "AcDbPoint")
           (list 10 6.9 1.3 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 7.535 -1.3)
           (cons 40 0)
           (cons 41 0)
           (cons 42 0)
           (cons 91 0)
           (list 10 7.535 1.3)
           (cons 40 0)
           (cons 41 0)
           (cons 42 0)
           (cons 91 0)
           (list 10 0 1.3)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 6.9 0 0)
           (cons 50 0)
          )
         )
         (entmake
          (list
           (cons 0 "ATTDEF")
           (cons 100 "AcDbEntity")
           (cons 67 0)
           (cons 8 "0")
           (cons 100 "AcDbText")
           (list 10 0.1 0.56666667 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 0.23333333 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.1 0)
           (cons 40 0.2)
           (cons 1 "6.90")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.43333333 0)
           (cons 40 0.2)
           (cons 1 "6.90")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.76666667 0)
           (cons 40 0.2)
           (cons 1 "39.451")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelLeftM1")
           (list 10 0.8 -1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM1")
           (list 10 0.8 1.0206 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "TAC-2017-B-12"))
        (progn
         (entmake)
         (entmake
          (list
           (cons 0 "BLOCK")
           (cons 2 "TAC-2017-B-12")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.2)
           (cons 40 0)
           (cons 41 0)
           (cons 42 0)
           (cons 91 0)
           (list 10 12.2 -1.2)
           (cons 40 0)
           (cons 41 0)
           (cons 42 0)
           (cons 91 0)
           (list 10 12.2 1.2)
           (cons 40 0)
           (cons 41 0)
           (cons 42 0)
           (cons 91 0)
           (list 10 0 1.2)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 12.2 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 12.2 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.892 -1.152248)
           (cons 40 0)
           (cons 41 0)
           (cons 42 0)
           (cons 91 0)
           (list 10 8.892 -0.993752)
           (cons 40 0)
           (cons 41 0)
           (cons 42 0)
           (cons 91 0)
           (list 10 9.03424 -0.946)
           (cons 40 0)
           (cons 41 0)
           (cons 42 0)
           (cons 91 0)
           (list 10 9.76576 -0.946)
           (cons 40 0)
           (cons 41 0)
           (cons 42 0)
           (cons 91 0)
           (list 10 9.908 -0.993752)
           (cons 40 0)
           (cons 41 0)
           (cons 42 0)
           (cons 91 0)
           (list 10 9.908 -1.152248)
           (cons 40 0)
           (cons 41 0)
           (cons 42 0)
           (cons 91 0)
           (list 10 9.76576 -1.2)
           (cons 40 0)
           (cons 41 0)
           (cons 42 0)
           (cons 91 0)
           (list 10 9.03424 -1.2)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.892 0.993752)
           (cons 40 0)
           (cons 41 0)
           (cons 42 0)
           (cons 91 0)
           (list 10 8.892 1.152248)
           (cons 40 0)
           (cons 41 0)
           (cons 42 0)
           (cons 91 0)
           (list 10 9.03424 1.2)
           (cons 40 0)
           (cons 41 0)
           (cons 42 0)
           (cons 91 0)
           (list 10 9.76576 1.2)
           (cons 40 0)
           (cons 41 0)
           (cons 42 0)
           (cons 91 0)
           (list 10 9.908 1.152248)
           (cons 40 0)
           (cons 41 0)
           (cons 42 0)
           (cons 91 0)
           (list 10 9.908 0.993752)
           (cons 40 0)
           (cons 41 0)
           (cons 42 0)
           (cons 91 0)
           (list 10 9.76576 0.946)
           (cons 40 0)
           (cons 41 0)
           (cons 42 0)
           (cons 91 0)
           (list 10 9.03424 0.946)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -1.2 0)
           (cons 50 0)
          )
         )
         (entmake
          (list
           (cons 0 "POINT")
           (cons 100 "AcDbEntity")
           (cons 67 0)
           (cons 8 "0")
           (cons 100 "AcDbPoint")
           (list 10 0 1.2 0)
           (cons 50 0)
          )
         )
         (entmake
          (list
           (cons 0 "POINT")
           (cons 100 "AcDbEntity")
           (cons 67 0)
           (cons 8 "0")
           (cons 100 "AcDbPoint")
           (list 10 12.2 1.2 0)
           (cons 50 0)
          )
         )
         (entmake
          (list
           (cons 0 "POINT")
           (cons 100 "AcDbEntity")
           (cons 67 0)
           (cons 8 "0")
           (cons 100 "AcDbPoint")
           (list 10 12.2 -1.2 0)
           (cons 50 0)
          )
         )
         (entmake
          (list
           (cons 0 "POINT")
           (cons 100 "AcDbEntity")
           (cons 67 0)
           (cons 8 "0")
           (cons 100 "AcDbPoint")
           (list 10 2.2 0 0)
           (cons 50 0)
          )
         )
         (entmake
          (list
           (cons 0 "POINT")
           (cons 100 "AcDbEntity")
           (cons 67 0)
           (cons 8 "0")
           (cons 100 "AcDbPoint")
           (list 10 2.2 1.2 0)
           (cons 50 0)
          )
         )
         (entmake
          (list
           (cons 0 "POINT")
           (cons 100 "AcDbEntity")
           (cons 67 0)
           (cons 8 "0")
           (cons 100 "AcDbPoint")
           (list 10 9.4 1.2 0)
           (cons 50 0)
          )
         )
         (entmake
          (list
           (cons 0 "POINT")
           (cons 100 "AcDbEntity")
           (cons 67 0)
           (cons 8 "0")
           (cons 100 "AcDbPoint")
           (list 10 9.4 -1.2 0)
           (cons 50 0)
          )
         )
         (entmake
          (list
           (cons 0 "POINT")
           (cons 100 "AcDbEntity")
           (cons 67 0)
           (cons 8 "0")
           (cons 100 "AcDbPoint")
           (list 10 2.2 -1.2 0)
           (cons 50 0)
          )
         )
         (entmake
          (list
           (cons 0 "ATTDEF")
           (cons 100 "AcDbEntity")
           (cons 67 0)
           (cons 8 "0")
           (cons 100 "AcDbText")
           (list 10 1.5 0.56666667 0)
           (cons 40 0.2)
           (cons 1 "2.200")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.5 0.23333333 0)
           (cons 40 0.2)
           (cons 1 "2.200")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.5 -0.1 0)
           (cons 40 0.2)
           (cons 1 "9.400")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.5 -0.43333333 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.5 -0.76666667 0)
           (cons 40 0.2)
           (cons 1 "33.927")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelLeftM2")
           (list 10 2.2 -0.946 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM2")
           (list 10 2.2 0.946 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "TAC-2017-ATD-TRAILER2"))
        (progn
         (entmake)
         (entmake
          (list
           (cons 0 "BLOCK")
           (cons 2 "TAC-2017-ATD-TRAILER2")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 9.4 -1.3)
           (cons 40 0)
           (cons 41 0)
           (cons 42 0)
           (cons 91 0)
           (list 10 9.4 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.4 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.4 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 1 0 0)
           (cons 40 0.17333333)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.7062 -0.7445528)
           (cons 40 0)
           (cons 41 0)
           (cons 42 0)
           (cons 91 0)
           (list 10 6.7062 -0.5702072)
           (cons 40 0)
           (cons 41 0)
           (cons 42 0)
           (cons 91 0)
           (list 10 6.862664 -0.51768)
           (cons 40 0)
           (cons 41 0)
           (cons 42 0)
           (cons 91 0)
           (list 10 7.667336 -0.51768)
           (cons 40 0)
           (cons 41 0)
           (cons 42 0)
           (cons 91 0)
           (list 10 7.8238 -0.5702072)
           (cons 40 0)
           (cons 41 0)
           (cons 42 0)
           (cons 91 0)
           (list 10 7.8238 -0.7445528)
           (cons 40 0)
           (cons 41 0)
           (cons 42 0)
           (cons 91 0)
           (list 10 7.667336 -0.79708)
           (cons 40 0)
           (cons 41 0)
           (cons 42 0)
           (cons 91 0)
           (list 10 6.862664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.7062 -1.2474728)
           (cons 40 0)
           (cons 41 0)
           (cons 42 0)
           (cons 91 0)
           (list 10 6.7062 -1.0731272)
           (cons 40 0)
           (cons 41 0)
           (cons 42 0)
           (cons 91 0)
           (list 10 6.862664 -1.0206)
           (cons 40 0)
           (cons 41 0)
           (cons 42 0)
           (cons 91 0)
           (list 10 7.667336 -1.0206)
           (cons 40 0)
           (cons 41 0)
           (cons 42 0)
           (cons 91 0)
           (list 10 7.8238 -1.0731272)
           (cons 40 0)
           (cons 41 0)
           (cons 42 0)
           (cons 91 0)
           (list 10 7.8238 -1.2474728)
           (cons 40 0)
           (cons 41 0)
           (cons 42 0)
           (cons 91 0)
           (list 10 7.667336 -1.3)
           (cons 40 0)
           (cons 41 0)
           (cons 42 0)
           (cons 91 0)
           (list 10 6.862664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.7062 0.5702072)
           (cons 40 0)
           (cons 41 0)
           (cons 42 0)
           (cons 91 0)
           (list 10 6.7062 0.7445528)
           (cons 40 0)
           (cons 41 0)
           (cons 42 0)
           (cons 91 0)
           (list 10 6.862664 0.79708)
           (cons 40 0)
           (cons 41 0)
           (cons 42 0)
           (cons 91 0)
           (list 10 7.667336 0.79708)
           (cons 40 0)
           (cons 41 0)
           (cons 42 0)
           (cons 91 0)
           (list 10 7.8238 0.7445528)
           (cons 40 0)
           (cons 41 0)
           (cons 42 0)
           (cons 91 0)
           (list 10 7.8238 0.5702072)
           (cons 40 0)
           (cons 41 0)
           (cons 42 0)
           (cons 91 0)
           (list 10 7.667336 0.51768)
           (cons 40 0)
           (cons 41 0)
           (cons 42 0)
           (cons 91 0)
           (list 10 6.862664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.7062 1.0731272)
           (cons 40 0)
           (cons 41 0)
           (cons 42 0)
           (cons 91 0)
           (list 10 6.7062 1.2474728)
           (cons 40 0)
           (cons 41 0)
           (cons 42 0)
           (cons 91 0)
           (list 10 6.862664 1.3)
           (cons 40 0)
           (cons 41 0)
           (cons 42 0)
           (cons 91 0)
           (list 10 7.667336 1.3)
           (cons 40 0)
           (cons 41 0)
           (cons 42 0)
           (cons 91 0)
           (list 10 7.8238 1.2474728)
           (cons 40 0)
           (cons 41 0)
           (cons 42 0)
           (cons 91 0)
           (list 10 7.8238 1.0731272)
           (cons 40 0)
           (cons 41 0)
           (cons 42 0)
           (cons 91 0)
           (list 10 7.667336 1.0206)
           (cons 40 0)
           (cons 41 0)
           (cons 42 0)
           (cons 91 0)
           (list 10 6.862664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.9762 -0.7445528)
           (cons 40 0)
           (cons 41 0)
           (cons 42 0)
           (cons 91 0)
           (list 10 7.9762 -0.5702072)
           (cons 40 0)
           (cons 41 0)
           (cons 42 0)
           (cons 91 0)
           (list 10 8.132664 -0.51768)
           (cons 40 0)
           (cons 41 0)
           (cons 42 0)
           (cons 91 0)
           (list 10 8.937336 -0.51768)
           (cons 40 0)
           (cons 41 0)
           (cons 42 0)
           (cons 91 0)
           (list 10 9.0938 -0.5702072)
           (cons 40 0)
           (cons 41 0)
           (cons 42 0)
           (cons 91 0)
           (list 10 9.0938 -0.7445528)
           (cons 40 0)
           (cons 41 0)
           (cons 42 0)
           (cons 91 0)
           (list 10 8.937336 -0.79708)
           (cons 40 0)
           (cons 41 0)
           (cons 42 0)
           (cons 91 0)
           (list 10 8.132664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.9762 -1.2474728)
           (cons 40 0)
           (cons 41 0)
           (cons 42 0)
           (cons 91 0)
           (list 10 7.9762 -1.0731272)
           (cons 40 0)
           (cons 41 0)
           (cons 42 0)
           (cons 91 0)
           (list 10 8.132664 -1.0206)
           (cons 40 0)
           (cons 41 0)
           (cons 42 0)
           (cons 91 0)
           (list 10 8.937336 -1.0206)
           (cons 40 0)
           (cons 41 0)
           (cons 42 0)
           (cons 91 0)
           (list 10 9.0938 -1.0731272)
           (cons 40 0)
           (cons 41 0)
           (cons 42 0)
           (cons 91 0)
           (list 10 9.0938 -1.2474728)
           (cons 40 0)
           (cons 41 0)
           (cons 42 0)
           (cons 91 0)
           (list 10 8.937336 -1.3)
           (cons 40 0)
           (cons 41 0)
           (cons 42 0)
           (cons 91 0)
           (list 10 8.132664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.9762 0.5702072)
           (cons 40 0)
           (cons 41 0)
           (cons 42 0)
           (cons 91 0)
           (list 10 7.9762 0.7445528)
           (cons 40 0)
           (cons 41 0)
           (cons 42 0)
           (cons 91 0)
           (list 10 8.132664 0.79708)
           (cons 40 0)
           (cons 41 0)
           (cons 42 0)
           (cons 91 0)
           (list 10 8.937336 0.79708)
           (cons 40 0)
           (cons 41 0)
           (cons 42 0)
           (cons 91 0)
           (list 10 9.0938 0.7445528)
           (cons 40 0)
           (cons 41 0)
           (cons 42 0)
           (cons 91 0)
           (list 10 9.0938 0.5702072)
           (cons 40 0)
           (cons 41 0)
           (cons 42 0)
           (cons 91 0)
           (list 10 8.937336 0.51768)
           (cons 40 0)
           (cons 41 0)
           (cons 42 0)
           (cons 91 0)
           (list 10 8.132664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.9762 1.0731272)
           (cons 40 0)
           (cons 41 0)
           (cons 42 0)
           (cons 91 0)
           (list 10 7.9762 1.2474728)
           (cons 40 0)
           (cons 41 0)
           (cons 42 0)
           (cons 91 0)
           (list 10 8.132664 1.3)
           (cons 40 0)
           (cons 41 0)
           (cons 42 0)
           (cons 91 0)
           (list 10 8.937336 1.3)
           (cons 40 0)
           (cons 41 0)
           (cons 42 0)
           (cons 91 0)
           (list 10 9.0938 1.2474728)
           (cons 40 0)
           (cons 41 0)
           (cons 42 0)
           (cons 91 0)
           (list 10 9.0938 1.0731272)
           (cons 40 0)
           (cons 41 0)
           (cons 42 0)
           (cons 91 0)
           (list 10 8.937336 1.0206)
           (cons 40 0)
           (cons 41 0)
           (cons 42 0)
           (cons 91 0)
           (list 10 8.132664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 9.4 -1.3 0)
           (cons 50 0)
          )
         )
         (entmake
          (list
           (cons 0 "POINT")
           (cons 100 "AcDbEntity")
           (cons 67 0)
           (cons 8 "0")
           (cons 100 "AcDbPoint")
           (list 10 9.4 1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 1 0 0)
           (cons 50 0)
          )
         )
         (entmake
          (list
           (cons 0 "POINT")
           (cons 100 "AcDbEntity")
           (cons 67 0)
           (cons 8 "0")
           (cons 100 "AcDbPoint")
           (list 10 7.9 0 0)
           (cons 50 0)
          )
         )
         (entmake
          (list
           (cons 0 "POINT")
           (cons 100 "AcDbEntity")
           (cons 67 0)
           (cons 8 "0")
           (cons 100 "AcDbPoint")
           (list 10 7.9 1.3 0)
           (cons 50 0)
          )
         )
         (entmake
          (list
           (cons 0 "POINT")
           (cons 100 "AcDbEntity")
           (cons 67 0)
           (cons 8 "0")
           (cons 100 "AcDbPoint")
           (list 10 7.9 -1.3 0)
           (cons 50 0)
          )
         )
         (entmake
          (list
           (cons 0 "ATTDEF")
           (cons 100 "AcDbEntity")
           (cons 67 0)
           (cons 8 "0")
           (cons 100 "AcDbText")
           (list 10 0.3 0.56666667 0)
           (cons 40 0.2)
           (cons 1 "1.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 0.23333333 0)
           (cons 40 0.2)
           (cons 1 "1.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.1 0)
           (cons 40 0.2)
           (cons 1 "7.900")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.43333333 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "TAC-2017-ATD-PUP"))
        (progn
         (entmake)
         (entmake
          (list
           (cons 0 "BLOCK")
           (cons 2 "TAC-2017-ATD-PUP")
           (cons 70 2)
           (cons 4 "")
           (list 10 0 0 0)
          )
         )
         (entmake
          (list
           (cons 0 "POLYLINE")
           (cons 100 "AcDbEntity")
           (cons 67 0)
           (cons 8 "Defpoints")
           (cons 100 "AcDb2dPolyline")
           (cons 66 1)
           (list 10 0 0 0)
           (cons 70 129)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "Defpoints")
           (cons 100 "AcDbVertex")
           (cons 100 "AcDb2dVertex")
           (list 10 0 0 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 2.1 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 2.1 1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "Defpoints")
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 2.1 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.17333333)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 -0.7445528)
           (cons 40 0)
           (cons 41 0)
           (cons 42 0)
           (cons 91 0)
           (list 10 1.5412 -0.5702072)
           (cons 40 0)
           (cons 41 0)
           (cons 42 0)
           (cons 91 0)
           (list 10 1.697664 -0.51768)
           (cons 40 0)
           (cons 41 0)
           (cons 42 0)
           (cons 91 0)
           (list 10 2.502336 -0.51768)
           (cons 40 0)
           (cons 41 0)
           (cons 42 0)
           (cons 91 0)
           (list 10 2.6588 -0.5702072)
           (cons 40 0)
           (cons 41 0)
           (cons 42 0)
           (cons 91 0)
           (list 10 2.6588 -0.7445528)
           (cons 40 0)
           (cons 41 0)
           (cons 42 0)
           (cons 91 0)
           (list 10 2.502336 -0.79708)
           (cons 40 0)
           (cons 41 0)
           (cons 42 0)
           (cons 91 0)
           (list 10 1.697664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 -1.2474728)
           (cons 40 0)
           (cons 41 0)
           (cons 42 0)
           (cons 91 0)
           (list 10 1.5412 -1.0731272)
           (cons 40 0)
           (cons 41 0)
           (cons 42 0)
           (cons 91 0)
           (list 10 1.697664 -1.0206)
           (cons 40 0)
           (cons 41 0)
           (cons 42 0)
           (cons 91 0)
           (list 10 2.502336 -1.0206)
           (cons 40 0)
           (cons 41 0)
           (cons 42 0)
           (cons 91 0)
           (list 10 2.6588 -1.0731272)
           (cons 40 0)
           (cons 41 0)
           (cons 42 0)
           (cons 91 0)
           (list 10 2.6588 -1.2474728)
           (cons 40 0)
           (cons 41 0)
           (cons 42 0)
           (cons 91 0)
           (list 10 2.502336 -1.3)
           (cons 40 0)
           (cons 41 0)
           (cons 42 0)
           (cons 91 0)
           (list 10 1.697664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 0.5702072)
           (cons 40 0)
           (cons 41 0)
           (cons 42 0)
           (cons 91 0)
           (list 10 1.5412 0.7445528)
           (cons 40 0)
           (cons 41 0)
           (cons 42 0)
           (cons 91 0)
           (list 10 1.697664 0.79708)
           (cons 40 0)
           (cons 41 0)
           (cons 42 0)
           (cons 91 0)
           (list 10 2.502336 0.79708)
           (cons 40 0)
           (cons 41 0)
           (cons 42 0)
           (cons 91 0)
           (list 10 2.6588 0.7445528)
           (cons 40 0)
           (cons 41 0)
           (cons 42 0)
           (cons 91 0)
           (list 10 2.6588 0.5702072)
           (cons 40 0)
           (cons 41 0)
           (cons 42 0)
           (cons 91 0)
           (list 10 2.502336 0.51768)
           (cons 40 0)
           (cons 41 0)
           (cons 42 0)
           (cons 91 0)
           (list 10 1.697664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 1.0731272)
           (cons 40 0)
           (cons 41 0)
           (cons 42 0)
           (cons 91 0)
           (list 10 1.5412 1.2474728)
           (cons 40 0)
           (cons 41 0)
           (cons 42 0)
           (cons 91 0)
           (list 10 1.697664 1.3)
           (cons 40 0)
           (cons 41 0)
           (cons 42 0)
           (cons 91 0)
           (list 10 2.502336 1.3)
           (cons 40 0)
           (cons 41 0)
           (cons 42 0)
           (cons 91 0)
           (list 10 2.6588 1.2474728)
           (cons 40 0)
           (cons 41 0)
           (cons 42 0)
           (cons 91 0)
           (list 10 2.6588 1.0731272)
           (cons 40 0)
           (cons 41 0)
           (cons 42 0)
           (cons 91 0)
           (list 10 2.502336 1.0206)
           (cons 40 0)
           (cons 41 0)
           (cons 42 0)
           (cons 91 0)
           (list 10 1.697664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 2.1 0 0)
           (cons 50 0)
          )
         )
         (entmake
          (list
           (cons 0 "POINT")
           (cons 100 "AcDbEntity")
           (cons 67 0)
           (cons 8 "0")
           (cons 100 "AcDbPoint")
           (list 10 2.1 1.3 0)
           (cons 50 0)
          )
         )
         (entmake
          (list
           (cons 0 "POINT")
           (cons 100 "AcDbEntity")
           (cons 67 0)
           (cons 8 "0")
           (cons 100 "AcDbPoint")
           (list 10 2.1 -1.3 0)
           (cons 50 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "2.100")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "2.100")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "TAC-2017-ATD-TRAILER1"))
        (progn
         (entmake)
         (entmake
          (list
           (cons 0 "BLOCK")
           (cons 2 "TAC-2017-ATD-TRAILER1")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 9.1 -1.3)
           (cons 40 0)
           (cons 41 0)
           (cons 42 0)
           (cons 91 0)
           (list 10 9.1 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.1 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.1 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 1 0 0)
           (cons 40 0.104)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.7062 -0.7445528)
           (cons 40 0)
           (cons 41 0)
           (cons 42 0)
           (cons 91 0)
           (list 10 6.7062 -0.5702072)
           (cons 40 0)
           (cons 41 0)
           (cons 42 0)
           (cons 91 0)
           (list 10 6.862664 -0.51768)
           (cons 40 0)
           (cons 41 0)
           (cons 42 0)
           (cons 91 0)
           (list 10 7.667336 -0.51768)
           (cons 40 0)
           (cons 41 0)
           (cons 42 0)
           (cons 91 0)
           (list 10 7.8238 -0.5702072)
           (cons 40 0)
           (cons 41 0)
           (cons 42 0)
           (cons 91 0)
           (list 10 7.8238 -0.7445528)
           (cons 40 0)
           (cons 41 0)
           (cons 42 0)
           (cons 91 0)
           (list 10 7.667336 -0.79708)
           (cons 40 0)
           (cons 41 0)
           (cons 42 0)
           (cons 91 0)
           (list 10 6.862664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.7062 -1.2474728)
           (cons 40 0)
           (cons 41 0)
           (cons 42 0)
           (cons 91 0)
           (list 10 6.7062 -1.0731272)
           (cons 40 0)
           (cons 41 0)
           (cons 42 0)
           (cons 91 0)
           (list 10 6.862664 -1.0206)
           (cons 40 0)
           (cons 41 0)
           (cons 42 0)
           (cons 91 0)
           (list 10 7.667336 -1.0206)
           (cons 40 0)
           (cons 41 0)
           (cons 42 0)
           (cons 91 0)
           (list 10 7.8238 -1.0731272)
           (cons 40 0)
           (cons 41 0)
           (cons 42 0)
           (cons 91 0)
           (list 10 7.8238 -1.2474728)
           (cons 40 0)
           (cons 41 0)
           (cons 42 0)
           (cons 91 0)
           (list 10 7.667336 -1.3)
           (cons 40 0)
           (cons 41 0)
           (cons 42 0)
           (cons 91 0)
           (list 10 6.862664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.7062 0.5702072)
           (cons 40 0)
           (cons 41 0)
           (cons 42 0)
           (cons 91 0)
           (list 10 6.7062 0.7445528)
           (cons 40 0)
           (cons 41 0)
           (cons 42 0)
           (cons 91 0)
           (list 10 6.862664 0.79708)
           (cons 40 0)
           (cons 41 0)
           (cons 42 0)
           (cons 91 0)
           (list 10 7.667336 0.79708)
           (cons 40 0)
           (cons 41 0)
           (cons 42 0)
           (cons 91 0)
           (list 10 7.8238 0.7445528)
           (cons 40 0)
           (cons 41 0)
           (cons 42 0)
           (cons 91 0)
           (list 10 7.8238 0.5702072)
           (cons 40 0)
           (cons 41 0)
           (cons 42 0)
           (cons 91 0)
           (list 10 7.667336 0.51768)
           (cons 40 0)
           (cons 41 0)
           (cons 42 0)
           (cons 91 0)
           (list 10 6.862664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.7062 1.0731272)
           (cons 40 0)
           (cons 41 0)
           (cons 42 0)
           (cons 91 0)
           (list 10 6.7062 1.2474728)
           (cons 40 0)
           (cons 41 0)
           (cons 42 0)
           (cons 91 0)
           (list 10 6.862664 1.3)
           (cons 40 0)
           (cons 41 0)
           (cons 42 0)
           (cons 91 0)
           (list 10 7.667336 1.3)
           (cons 40 0)
           (cons 41 0)
           (cons 42 0)
           (cons 91 0)
           (list 10 7.8238 1.2474728)
           (cons 40 0)
           (cons 41 0)
           (cons 42 0)
           (cons 91 0)
           (list 10 7.8238 1.0731272)
           (cons 40 0)
           (cons 41 0)
           (cons 42 0)
           (cons 91 0)
           (list 10 7.667336 1.0206)
           (cons 40 0)
           (cons 41 0)
           (cons 42 0)
           (cons 91 0)
           (list 10 6.862664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.9762 -0.7445528)
           (cons 40 0)
           (cons 41 0)
           (cons 42 0)
           (cons 91 0)
           (list 10 7.9762 -0.5702072)
           (cons 40 0)
           (cons 41 0)
           (cons 42 0)
           (cons 91 0)
           (list 10 8.132664 -0.51768)
           (cons 40 0)
           (cons 41 0)
           (cons 42 0)
           (cons 91 0)
           (list 10 8.937336 -0.51768)
           (cons 40 0)
           (cons 41 0)
           (cons 42 0)
           (cons 91 0)
           (list 10 9.0938 -0.5702072)
           (cons 40 0)
           (cons 41 0)
           (cons 42 0)
           (cons 91 0)
           (list 10 9.0938 -0.7445528)
           (cons 40 0)
           (cons 41 0)
           (cons 42 0)
           (cons 91 0)
           (list 10 8.937336 -0.79708)
           (cons 40 0)
           (cons 41 0)
           (cons 42 0)
           (cons 91 0)
           (list 10 8.132664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.9762 -1.2474728)
           (cons 40 0)
           (cons 41 0)
           (cons 42 0)
           (cons 91 0)
           (list 10 7.9762 -1.0731272)
           (cons 40 0)
           (cons 41 0)
           (cons 42 0)
           (cons 91 0)
           (list 10 8.132664 -1.0206)
           (cons 40 0)
           (cons 41 0)
           (cons 42 0)
           (cons 91 0)
           (list 10 8.937336 -1.0206)
           (cons 40 0)
           (cons 41 0)
           (cons 42 0)
           (cons 91 0)
           (list 10 9.0938 -1.0731272)
           (cons 40 0)
           (cons 41 0)
           (cons 42 0)
           (cons 91 0)
           (list 10 9.0938 -1.2474728)
           (cons 40 0)
           (cons 41 0)
           (cons 42 0)
           (cons 91 0)
           (list 10 8.937336 -1.3)
           (cons 40 0)
           (cons 41 0)
           (cons 42 0)
           (cons 91 0)
           (list 10 8.132664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.9762 0.5702072)
           (cons 40 0)
           (cons 41 0)
           (cons 42 0)
           (cons 91 0)
           (list 10 7.9762 0.7445528)
           (cons 40 0)
           (cons 41 0)
           (cons 42 0)
           (cons 91 0)
           (list 10 8.132664 0.79708)
           (cons 40 0)
           (cons 41 0)
           (cons 42 0)
           (cons 91 0)
           (list 10 8.937336 0.79708)
           (cons 40 0)
           (cons 41 0)
           (cons 42 0)
           (cons 91 0)
           (list 10 9.0938 0.7445528)
           (cons 40 0)
           (cons 41 0)
           (cons 42 0)
           (cons 91 0)
           (list 10 9.0938 0.5702072)
           (cons 40 0)
           (cons 41 0)
           (cons 42 0)
           (cons 91 0)
           (list 10 8.937336 0.51768)
           (cons 40 0)
           (cons 41 0)
           (cons 42 0)
           (cons 91 0)
           (list 10 8.132664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.9762 1.0731272)
           (cons 40 0)
           (cons 41 0)
           (cons 42 0)
           (cons 91 0)
           (list 10 7.9762 1.2474728)
           (cons 40 0)
           (cons 41 0)
           (cons 42 0)
           (cons 91 0)
           (list 10 8.132664 1.3)
           (cons 40 0)
           (cons 41 0)
           (cons 42 0)
           (cons 91 0)
           (list 10 8.937336 1.3)
           (cons 40 0)
           (cons 41 0)
           (cons 42 0)
           (cons 91 0)
           (list 10 9.0938 1.2474728)
           (cons 40 0)
           (cons 41 0)
           (cons 42 0)
           (cons 91 0)
           (list 10 9.0938 1.0731272)
           (cons 40 0)
           (cons 41 0)
           (cons 42 0)
           (cons 91 0)
           (list 10 8.937336 1.0206)
           (cons 40 0)
           (cons 41 0)
           (cons 42 0)
           (cons 91 0)
           (list 10 8.132664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 1 0 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 9.1 1.3 0)
           (cons 50 0)
          )
         )
         (entmake
          (list
           (cons 0 "POINT")
           (cons 100 "AcDbEntity")
           (cons 67 0)
           (cons 8 "0")
           (cons 100 "AcDbPoint")
           (list 10 9.1 -1.3 0)
           (cons 50 0)
          )
         )
         (entmake
          (list
           (cons 0 "POINT")
           (cons 100 "AcDbEntity")
           (cons 67 0)
           (cons 8 "0")
           (cons 100 "AcDbPoint")
           (list 10 7.9 -1.3 0)
           (cons 50 0)
          )
         )
         (entmake
          (list
           (cons 0 "POINT")
           (cons 100 "AcDbEntity")
           (cons 67 0)
           (cons 8 "0")
           (cons 100 "AcDbPoint")
           (list 10 7.9 1.3 0)
           (cons 50 0)
          )
         )
         (entmake
          (list
           (cons 0 "ATTDEF")
           (cons 100 "AcDbEntity")
           (cons 67 0)
           (cons 8 "0")
           (cons 100 "AcDbText")
           (list 10 0.3 0.56666667 0)
           (cons 40 0.2)
           (cons 1 "1.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 0.23333333 0)
           (cons 40 0.2)
           (cons 1 "1.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.1 0)
           (cons 40 0.2)
           (cons 1 "7.900")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.43333333 0)
           (cons 40 0.2)
           (cons 1 "9.100")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "POINT")
           (cons 100 "AcDbEntity")
           (cons 67 0)
           (cons 8 "0")
           (cons 100 "AcDbPoint")
           (list 10 9.1 0 0)
           (cons 50 0)
          )
         )
         (entmake (list (cons 0 "ENDBLK")))
        )
       )
       ((= (strcase BLKNAME) (strcase "TAC-2017-ATD-TRUCK"))
        (progn
         (entmake)
         (entmake
          (list
           (cons 0 "BLOCK")
           (cons 2 "TAC-2017-ATD-TRUCK")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 6.535 -1.3)
           (cons 40 0)
           (cons 41 0)
           (cons 42 0)
           (cons 91 0)
           (list 10 6.535 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.535 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.535 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 5.9 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 6.16263966 -0.26263966 0)
           (list 11 6.16263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.7062 -0.7445528)
           (cons 40 0)
           (cons 41 0)
           (cons 42 0)
           (cons 91 0)
           (list 10 4.7062 -0.5702072)
           (cons 40 0)
           (cons 41 0)
           (cons 42 0)
           (cons 91 0)
           (list 10 4.862664 -0.51768)
           (cons 40 0)
           (cons 41 0)
           (cons 42 0)
           (cons 91 0)
           (list 10 5.667336 -0.51768)
           (cons 40 0)
           (cons 41 0)
           (cons 42 0)
           (cons 91 0)
           (list 10 5.8238 -0.5702072)
           (cons 40 0)
           (cons 41 0)
           (cons 42 0)
           (cons 91 0)
           (list 10 5.8238 -0.7445528)
           (cons 40 0)
           (cons 41 0)
           (cons 42 0)
           (cons 91 0)
           (list 10 5.667336 -0.79708)
           (cons 40 0)
           (cons 41 0)
           (cons 42 0)
           (cons 91 0)
           (list 10 4.862664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.7062 -1.2474728)
           (cons 40 0)
           (cons 41 0)
           (cons 42 0)
           (cons 91 0)
           (list 10 4.7062 -1.0731272)
           (cons 40 0)
           (cons 41 0)
           (cons 42 0)
           (cons 91 0)
           (list 10 4.862664 -1.0206)
           (cons 40 0)
           (cons 41 0)
           (cons 42 0)
           (cons 91 0)
           (list 10 5.667336 -1.0206)
           (cons 40 0)
           (cons 41 0)
           (cons 42 0)
           (cons 91 0)
           (list 10 5.8238 -1.0731272)
           (cons 40 0)
           (cons 41 0)
           (cons 42 0)
           (cons 91 0)
           (list 10 5.8238 -1.2474728)
           (cons 40 0)
           (cons 41 0)
           (cons 42 0)
           (cons 91 0)
           (list 10 5.667336 -1.3)
           (cons 40 0)
           (cons 41 0)
           (cons 42 0)
           (cons 91 0)
           (list 10 4.862664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.7062 0.5702072)
           (cons 40 0)
           (cons 41 0)
           (cons 42 0)
           (cons 91 0)
           (list 10 4.7062 0.7445528)
           (cons 40 0)
           (cons 41 0)
           (cons 42 0)
           (cons 91 0)
           (list 10 4.862664 0.79708)
           (cons 40 0)
           (cons 41 0)
           (cons 42 0)
           (cons 91 0)
           (list 10 5.667336 0.79708)
           (cons 40 0)
           (cons 41 0)
           (cons 42 0)
           (cons 91 0)
           (list 10 5.8238 0.7445528)
           (cons 40 0)
           (cons 41 0)
           (cons 42 0)
           (cons 91 0)
           (list 10 5.8238 0.5702072)
           (cons 40 0)
           (cons 41 0)
           (cons 42 0)
           (cons 91 0)
           (list 10 5.667336 0.51768)
           (cons 40 0)
           (cons 41 0)
           (cons 42 0)
           (cons 91 0)
           (list 10 4.862664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.7062 1.0731272)
           (cons 40 0)
           (cons 41 0)
           (cons 42 0)
           (cons 91 0)
           (list 10 4.7062 1.2474728)
           (cons 40 0)
           (cons 41 0)
           (cons 42 0)
           (cons 91 0)
           (list 10 4.862664 1.3)
           (cons 40 0)
           (cons 41 0)
           (cons 42 0)
           (cons 91 0)
           (list 10 5.667336 1.3)
           (cons 40 0)
           (cons 41 0)
           (cons 42 0)
           (cons 91 0)
           (list 10 5.8238 1.2474728)
           (cons 40 0)
           (cons 41 0)
           (cons 42 0)
           (cons 91 0)
           (list 10 5.8238 1.0731272)
           (cons 40 0)
           (cons 41 0)
           (cons 42 0)
           (cons 91 0)
           (list 10 5.667336 1.0206)
           (cons 40 0)
           (cons 41 0)
           (cons 42 0)
           (cons 91 0)
           (list 10 4.862664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9762 -0.7445528)
           (cons 40 0)
           (cons 41 0)
           (cons 42 0)
           (cons 91 0)
           (list 10 5.9762 -0.5702072)
           (cons 40 0)
           (cons 41 0)
           (cons 42 0)
           (cons 91 0)
           (list 10 6.132664 -0.51768)
           (cons 40 0)
           (cons 41 0)
           (cons 42 0)
           (cons 91 0)
           (list 10 6.937336 -0.51768)
           (cons 40 0)
           (cons 41 0)
           (cons 42 0)
           (cons 91 0)
           (list 10 7.0938 -0.5702072)
           (cons 40 0)
           (cons 41 0)
           (cons 42 0)
           (cons 91 0)
           (list 10 7.0938 -0.7445528)
           (cons 40 0)
           (cons 41 0)
           (cons 42 0)
           (cons 91 0)
           (list 10 6.937336 -0.79708)
           (cons 40 0)
           (cons 41 0)
           (cons 42 0)
           (cons 91 0)
           (list 10 6.132664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9762 -1.2474728)
           (cons 40 0)
           (cons 41 0)
           (cons 42 0)
           (cons 91 0)
           (list 10 5.9762 -1.0731272)
           (cons 40 0)
           (cons 41 0)
           (cons 42 0)
           (cons 91 0)
           (list 10 6.132664 -1.0206)
           (cons 40 0)
           (cons 41 0)
           (cons 42 0)
           (cons 91 0)
           (list 10 6.937336 -1.0206)
           (cons 40 0)
           (cons 41 0)
           (cons 42 0)
           (cons 91 0)
           (list 10 7.0938 -1.0731272)
           (cons 40 0)
           (cons 41 0)
           (cons 42 0)
           (cons 91 0)
           (list 10 7.0938 -1.2474728)
           (cons 40 0)
           (cons 41 0)
           (cons 42 0)
           (cons 91 0)
           (list 10 6.937336 -1.3)
           (cons 40 0)
           (cons 41 0)
           (cons 42 0)
           (cons 91 0)
           (list 10 6.132664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9762 0.5702072)
           (cons 40 0)
           (cons 41 0)
           (cons 42 0)
           (cons 91 0)
           (list 10 5.9762 0.7445528)
           (cons 40 0)
           (cons 41 0)
           (cons 42 0)
           (cons 91 0)
           (list 10 6.132664 0.79708)
           (cons 40 0)
           (cons 41 0)
           (cons 42 0)
           (cons 91 0)
           (list 10 6.937336 0.79708)
           (cons 40 0)
           (cons 41 0)
           (cons 42 0)
           (cons 91 0)
           (list 10 7.0938 0.7445528)
           (cons 40 0)
           (cons 41 0)
           (cons 42 0)
           (cons 91 0)
           (list 10 7.0938 0.5702072)
           (cons 40 0)
           (cons 41 0)
           (cons 42 0)
           (cons 91 0)
           (list 10 6.937336 0.51768)
           (cons 40 0)
           (cons 41 0)
           (cons 42 0)
           (cons 91 0)
           (list 10 6.132664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9762 1.0731272)
           (cons 40 0)
           (cons 41 0)
           (cons 42 0)
           (cons 91 0)
           (list 10 5.9762 1.2474728)
           (cons 40 0)
           (cons 41 0)
           (cons 42 0)
           (cons 91 0)
           (list 10 6.132664 1.3)
           (cons 40 0)
           (cons 41 0)
           (cons 42 0)
           (cons 91 0)
           (list 10 6.937336 1.3)
           (cons 40 0)
           (cons 41 0)
           (cons 42 0)
           (cons 91 0)
           (list 10 7.0938 1.2474728)
           (cons 40 0)
           (cons 41 0)
           (cons 42 0)
           (cons 91 0)
           (list 10 7.0938 1.0731272)
           (cons 40 0)
           (cons 41 0)
           (cons 42 0)
           (cons 91 0)
           (list 10 6.937336 1.0206)
           (cons 40 0)
           (cons 41 0)
           (cons 42 0)
           (cons 91 0)
           (list 10 6.132664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0.8 0 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0.8 1.3 0)
           (cons 50 0)
          )
         )
         (entmake
          (list
           (cons 0 "POINT")
           (cons 100 "AcDbEntity")
           (cons 67 0)
           (cons 8 "0")
           (cons 100 "AcDbPoint")
           (list 10 0.8 -1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 5.9 1.3 0)
           (cons 50 0)
          )
         )
         (entmake
          (list
           (cons 0 "POINT")
           (cons 100 "AcDbEntity")
           (cons 67 0)
           (cons 8 "0")
           (cons 100 "AcDbPoint")
           (list 10 5.9 -1.3 0)
           (cons 50 0)
          )
         )
         (entmake
          (list
           (cons 0 "POINT")
           (cons 100 "AcDbEntity")
           (cons 67 0)
           (cons 8 "0")
           (cons 100 "AcDbPoint")
           (list 10 5.9 0 0)
           (cons 50 0)
          )
         )
         (entmake
          (list
           (cons 0 "ATTDEF")
           (cons 100 "AcDbEntity")
           (cons 67 0)
           (cons 8 "0")
           (cons 100 "AcDbText")
           (list 10 0.1 0.56666667 0)
           (cons 40 0.2)
           (cons 1 "0.800")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 0.23333333 0)
           (cons 40 0.2)
           (cons 1 "0.800")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.1 0)
           (cons 40 0.2)
           (cons 1 "5.900")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.43333333 0)
           (cons 40 0.2)
           (cons 1 "5.900")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.76666667 0)
           (cons 40 0.2)
           (cons 1 "32.090")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelRightM1")
           (list 10 0.8 1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM1")
           (list 10 0.8 -1.0206 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "TAC-2017-A-BUS-REAR"))
        (progn
         (entmake)
         (entmake
          (list
           (cons 0 "BLOCK")
           (cons 2 "TAC-2017-A-BUS-REAR")
           (cons 70 2)
           (cons 4 "")
           (list 10 0 0 0)
          )
         )
         (entmake
          (list
           (cons 0 "POLYLINE")
           (cons 100 "AcDbEntity")
           (cons 67 0)
           (cons 8 "Defpoints")
           (cons 100 "AcDb2dPolyline")
           (cons 66 1)
           (list 10 0 0 0)
           (cons 70 129)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "Defpoints")
           (cons 100 "AcDbVertex")
           (cons 100 "AcDb2dVertex")
           (list 10 0 0 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 0.6 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 7.8 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 7.8 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 0.6 1.2 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "Defpoints")
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0.6 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.8 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.8 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0.6 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0.6 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0.6 -1.2 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 0.6 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.16)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.292 -1.152248)
           (cons 40 0)
           (cons 41 0)
           (cons 42 0)
           (cons 91 0)
           (list 10 4.292 -0.993752)
           (cons 40 0)
           (cons 41 0)
           (cons 42 0)
           (cons 91 0)
           (list 10 4.43424 -0.946)
           (cons 40 0)
           (cons 41 0)
           (cons 42 0)
           (cons 91 0)
           (list 10 5.16576 -0.946)
           (cons 40 0)
           (cons 41 0)
           (cons 42 0)
           (cons 91 0)
           (list 10 5.308 -0.993752)
           (cons 40 0)
           (cons 41 0)
           (cons 42 0)
           (cons 91 0)
           (list 10 5.308 -1.152248)
           (cons 40 0)
           (cons 41 0)
           (cons 42 0)
           (cons 91 0)
           (list 10 5.16576 -1.2)
           (cons 40 0)
           (cons 41 0)
           (cons 42 0)
           (cons 91 0)
           (list 10 4.43424 -1.2)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.292 0.993752)
           (cons 40 0)
           (cons 41 0)
           (cons 42 0)
           (cons 91 0)
           (list 10 4.292 1.152248)
           (cons 40 0)
           (cons 41 0)
           (cons 42 0)
           (cons 91 0)
           (list 10 4.43424 1.2)
           (cons 40 0)
           (cons 41 0)
           (cons 42 0)
           (cons 91 0)
           (list 10 5.16576 1.2)
           (cons 40 0)
           (cons 41 0)
           (cons 42 0)
           (cons 91 0)
           (list 10 5.308 1.152248)
           (cons 40 0)
           (cons 41 0)
           (cons 42 0)
           (cons 91 0)
           (list 10 5.308 0.993752)
           (cons 40 0)
           (cons 41 0)
           (cons 42 0)
           (cons 91 0)
           (list 10 5.16576 0.946)
           (cons 40 0)
           (cons 41 0)
           (cons 42 0)
           (cons 91 0)
           (list 10 4.43424 0.946)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "4.800")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "POINT")
           (cons 100 "AcDbEntity")
           (cons 67 0)
           (cons 8 "0")
           (cons 100 "AcDbPoint")
           (list 10 4.8 -1.2 0)
           (cons 50 0)
          )
         )
         (entmake
          (list
           (cons 0 "POINT")
           (cons 100 "AcDbEntity")
           (cons 67 0)
           (cons 8 "0")
           (cons 100 "AcDbPoint")
           (list 10 4.8 1.2 0)
           (cons 50 0)
          )
         )
         (entmake
          (list
           (cons 0 "POINT")
           (cons 100 "AcDbEntity")
           (cons 67 0)
           (cons 8 "0")
           (cons 100 "AcDbPoint")
           (list 10 7.8 1.2 0)
           (cons 50 0)
          )
         )
         (entmake
          (list
           (cons 0 "POINT")
           (cons 100 "AcDbEntity")
           (cons 67 0)
           (cons 8 "0")
           (cons 100 "AcDbPoint")
           (list 10 7.8 -1.2 0)
           (cons 50 0)
          )
         )
         (entmake (list (cons 0 "ENDBLK")))
        )
       )
       ((= (strcase BLKNAME) (strcase "TAC-2017-A-BUS-FRONT"))
        (progn
         (entmake)
         (entmake
          (list
           (cons 0 "BLOCK")
           (cons 2 "TAC-2017-A-BUS-FRONT")
           (cons 70 2)
           (cons 4 "")
           (list 10 0 0 0)
          )
         )
         (entmake
          (list
           (cons 0 "POLYLINE")
           (cons 100 "AcDbEntity")
           (cons 67 0)
           (cons 8 "Defpoints")
           (cons 100 "AcDb2dPolyline")
           (cons 66 1)
           (list 10 0 0 0)
           (cons 70 129)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "Defpoints")
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 9.9 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 10.5 0 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 9.9 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 0 1.2 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "Defpoints")
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.9 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.9 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 9.9 0 0)
           (list 11 10.5 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 10.5 0 0)
           (cons 40 0.1016)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.192 -1.152248)
           (cons 40 0)
           (cons 41 0)
           (cons 42 0)
           (cons 91 0)
           (list 10 8.192 -0.993752)
           (cons 40 0)
           (cons 41 0)
           (cons 42 0)
           (cons 91 0)
           (list 10 8.33424 -0.946)
           (cons 40 0)
           (cons 41 0)
           (cons 42 0)
           (cons 91 0)
           (list 10 9.06576 -0.946)
           (cons 40 0)
           (cons 41 0)
           (cons 42 0)
           (cons 91 0)
           (list 10 9.208 -0.993752)
           (cons 40 0)
           (cons 41 0)
           (cons 42 0)
           (cons 91 0)
           (list 10 9.208 -1.152248)
           (cons 40 0)
           (cons 41 0)
           (cons 42 0)
           (cons 91 0)
           (list 10 9.06576 -1.2)
           (cons 40 0)
           (cons 41 0)
           (cons 42 0)
           (cons 91 0)
           (list 10 8.33424 -1.2)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.192 0.993752)
           (cons 40 0)
           (cons 41 0)
           (cons 42 0)
           (cons 91 0)
           (list 10 8.192 1.152248)
           (cons 40 0)
           (cons 41 0)
           (cons 42 0)
           (cons 91 0)
           (list 10 8.33424 1.2)
           (cons 40 0)
           (cons 41 0)
           (cons 42 0)
           (cons 91 0)
           (list 10 9.06576 1.2)
           (cons 40 0)
           (cons 41 0)
           (cons 42 0)
           (cons 91 0)
           (list 10 9.208 1.152248)
           (cons 40 0)
           (cons 41 0)
           (cons 42 0)
           (cons 91 0)
           (list 10 9.208 0.993752)
           (cons 40 0)
           (cons 41 0)
           (cons 42 0)
           (cons 91 0)
           (list 10 9.06576 0.946)
           (cons 40 0)
           (cons 41 0)
           (cons 42 0)
           (cons 91 0)
           (list 10 8.33424 0.946)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 3.2 0 0)
           (cons 50 0)
          )
         )
         (entmake
          (list
           (cons 0 "ATTDEF")
           (cons 100 "AcDbEntity")
           (cons 67 0)
           (cons 8 "0")
           (cons 100 "AcDbText")
           (list 10 2.5 0.56666667 0)
           (cons 40 0.2)
           (cons 1 "3.200")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 2.5 0.23333333 0)
           (cons 40 0.2)
           (cons 1 "3.200")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 2.5 -0.1 0)
           (cons 40 0.2)
           (cons 1 "8.700")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 2.5 -0.43333333 0)
           (cons 40 0.2)
           (cons 1 "10.500")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 2.5 -0.76666667 0)
           (cons 40 0.2)
           (cons 1 "24.825")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "POINT")
           (cons 100 "AcDbEntity")
           (cons 67 0)
           (cons 8 "0")
           (cons 100 "AcDbPoint")
           (list 10 0 -1.2 0)
           (cons 50 0)
          )
         )
         (entmake
          (list
           (cons 0 "POINT")
           (cons 100 "AcDbEntity")
           (cons 67 0)
           (cons 8 "0")
           (cons 100 "AcDbPoint")
           (list 10 0 1.2 0)
           (cons 50 0)
          )
         )
         (entmake
          (list
           (cons 0 "POINT")
           (cons 100 "AcDbEntity")
           (cons 67 0)
           (cons 8 "0")
           (cons 100 "AcDbPoint")
           (list 10 9.9 1.2 0)
           (cons 50 0)
          )
         )
         (entmake
          (list
           (cons 0 "POINT")
           (cons 100 "AcDbEntity")
           (cons 67 0)
           (cons 8 "0")
           (cons 100 "AcDbPoint")
           (list 10 9.9 -1.2 0)
           (cons 50 0)
          )
         )
         (entmake
          (list
           (cons 0 "POINT")
           (cons 100 "AcDbEntity")
           (cons 67 0)
           (cons 8 "0")
           (cons 100 "AcDbPoint")
           (list 10 3.2 1.2 0)
           (cons 50 0)
          )
         )
         (entmake
          (list
           (cons 0 "POINT")
           (cons 100 "AcDbEntity")
           (cons 67 0)
           (cons 8 "0")
           (cons 100 "AcDbPoint")
           (list 10 3.2 -1.2 0)
           (cons 50 0)
          )
         )
         (entmake
          (list
           (cons 0 "POINT")
           (cons 100 "AcDbEntity")
           (cons 67 0)
           (cons 8 "0")
           (cons 100 "AcDbPoint")
           (list 10 8.7 -1.2 0)
           (cons 50 0)
          )
         )
         (entmake
          (list
           (cons 0 "POINT")
           (cons 100 "AcDbEntity")
           (cons 67 0)
           (cons 8 "0")
           (cons 100 "AcDbPoint")
           (list 10 8.7 1.2 0)
           (cons 50 0)
          )
         )
         (entmake
          (list
           (cons 0 "POINT")
           (cons 100 "AcDbEntity")
           (cons 67 0)
           (cons 8 "0")
           (cons 100 "AcDbPoint")
           (list 10 10.5 0 0)
           (cons 50 0)
          )
         )
         (entmake
          (list
           (cons 0 "INSERT")
           (cons 100 "AcDbEntity")
           (cons 67 0)
           (cons 8 "0")
           (cons 100 "AcDbBlockReference")
           (cons 2 "WheelRightM2")
           (list 10 3.2 0.946 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM2")
           (list 10 3.2 -0.946 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "BC_MOTI-TS7-Trailer"))
        (progn
         (entmake)
         (entmake
          (list
           (cons 0 "BLOCK")
           (cons 2 "BC_MOTI-TS7-Trailer")
           (cons 70 2)
           (cons 4 "")
           (list 10 0 0 0)
          )
         )
         (entmake
          (list
           (cons 0 "LWPOLYLINE")
           (cons 100 "AcDbEntity")
           (cons 67 0)
           (cons 8 "Defpoints")
           (cons 6 "Continuous")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 17.25 -1.3)
           (cons 40 0)
           (cons 41 0)
           (cons 42 0)
           (cons 91 0)
           (list 10 17.25 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 17.25 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 17.25 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.4912 -0.7445528)
           (cons 40 0)
           (cons 41 0)
           (cons 42 0)
           (cons 91 0)
           (list 10 13.4912 -0.5702072)
           (cons 40 0)
           (cons 41 0)
           (cons 42 0)
           (cons 91 0)
           (list 10 13.647664 -0.51768)
           (cons 40 0)
           (cons 41 0)
           (cons 42 0)
           (cons 91 0)
           (list 10 14.452336 -0.51768)
           (cons 40 0)
           (cons 41 0)
           (cons 42 0)
           (cons 91 0)
           (list 10 14.6088 -0.5702072)
           (cons 40 0)
           (cons 41 0)
           (cons 42 0)
           (cons 91 0)
           (list 10 14.6088 -0.7445528)
           (cons 40 0)
           (cons 41 0)
           (cons 42 0)
           (cons 91 0)
           (list 10 14.452336 -0.79708)
           (cons 40 0)
           (cons 41 0)
           (cons 42 0)
           (cons 91 0)
           (list 10 13.647664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.4912 -1.2474728)
           (cons 40 0)
           (cons 41 0)
           (cons 42 0)
           (cons 91 0)
           (list 10 13.4912 -1.0731272)
           (cons 40 0)
           (cons 41 0)
           (cons 42 0)
           (cons 91 0)
           (list 10 13.647664 -1.0206)
           (cons 40 0)
           (cons 41 0)
           (cons 42 0)
           (cons 91 0)
           (list 10 14.452336 -1.0206)
           (cons 40 0)
           (cons 41 0)
           (cons 42 0)
           (cons 91 0)
           (list 10 14.6088 -1.0731272)
           (cons 40 0)
           (cons 41 0)
           (cons 42 0)
           (cons 91 0)
           (list 10 14.6088 -1.2474728)
           (cons 40 0)
           (cons 41 0)
           (cons 42 0)
           (cons 91 0)
           (list 10 14.452336 -1.3)
           (cons 40 0)
           (cons 41 0)
           (cons 42 0)
           (cons 91 0)
           (list 10 13.647664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.4912 0.5702072)
           (cons 40 0)
           (cons 41 0)
           (cons 42 0)
           (cons 91 0)
           (list 10 13.4912 0.7445528)
           (cons 40 0)
           (cons 41 0)
           (cons 42 0)
           (cons 91 0)
           (list 10 13.647664 0.79708)
           (cons 40 0)
           (cons 41 0)
           (cons 42 0)
           (cons 91 0)
           (list 10 14.452336 0.79708)
           (cons 40 0)
           (cons 41 0)
           (cons 42 0)
           (cons 91 0)
           (list 10 14.6088 0.7445528)
           (cons 40 0)
           (cons 41 0)
           (cons 42 0)
           (cons 91 0)
           (list 10 14.6088 0.5702072)
           (cons 40 0)
           (cons 41 0)
           (cons 42 0)
           (cons 91 0)
           (list 10 14.452336 0.51768)
           (cons 40 0)
           (cons 41 0)
           (cons 42 0)
           (cons 91 0)
           (list 10 13.647664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.4912 1.0731272)
           (cons 40 0)
           (cons 41 0)
           (cons 42 0)
           (cons 91 0)
           (list 10 13.4912 1.2474728)
           (cons 40 0)
           (cons 41 0)
           (cons 42 0)
           (cons 91 0)
           (list 10 13.647664 1.3)
           (cons 40 0)
           (cons 41 0)
           (cons 42 0)
           (cons 91 0)
           (list 10 14.452336 1.3)
           (cons 40 0)
           (cons 41 0)
           (cons 42 0)
           (cons 91 0)
           (list 10 14.6088 1.2474728)
           (cons 40 0)
           (cons 41 0)
           (cons 42 0)
           (cons 91 0)
           (list 10 14.6088 1.0731272)
           (cons 40 0)
           (cons 41 0)
           (cons 42 0)
           (cons 91 0)
           (list 10 14.452336 1.0206)
           (cons 40 0)
           (cons 41 0)
           (cons 42 0)
           (cons 91 0)
           (list 10 13.647664 1.0206)
           (cons 40 0)
           (cons 41 0)
           (cons 42 0)
           (cons 91 0)
          )
         )
         (entmake
          (list
           (cons 0 "POINT")
           (cons 100 "AcDbEntity")
           (cons 67 0)
           (cons 8 "0")
           (cons 6 "Continuous")
           (cons 100 "AcDbPoint")
           (list 10 14.05 1.3 0)
           (cons 50 0)
          )
         )
         (entmake
          (list
           (cons 0 "POINT")
           (cons 100 "AcDbEntity")
           (cons 67 0)
           (cons 8 "0")
           (cons 6 "Continuous")
           (cons 100 "AcDbPoint")
           (list 10 14.05 -1.3 0)
           (cons 50 0)
          )
         )
         (entmake
          (list
           (cons 0 "POINT")
           (cons 100 "AcDbEntity")
           (cons 67 0)
           (cons 8 "0")
           (cons 6 "Continuous")
           (cons 100 "AcDbPoint")
           (list 10 17.25 -1.3 0)
           (cons 50 0)
          )
         )
         (entmake
          (list
           (cons 0 "POINT")
           (cons 100 "AcDbEntity")
           (cons 67 0)
           (cons 8 "0")
           (cons 6 "Continuous")
           (cons 100 "AcDbPoint")
           (list 10 17.25 1.3 0)
           (cons 50 0)
          )
         )
         (entmake
          (list
           (cons 0 "POINT")
           (cons 100 "AcDbEntity")
           (cons 67 0)
           (cons 8 "0")
           (cons 6 "Continuous")
           (cons 100 "AcDbPoint")
           (list 10 0 -1.3 0)
           (cons 50 0)
          )
         )
         (entmake
          (list
           (cons 0 "POINT")
           (cons 100 "AcDbEntity")
           (cons 67 0)
           (cons 8 "0")
           (cons 6 "Continuous")
           (cons 100 "AcDbPoint")
           (list 10 0 1.3 0)
           (cons 50 0)
          )
         )
         (entmake
          (list
           (cons 0 "POINT")
           (cons 100 "AcDbEntity")
           (cons 67 0)
           (cons 8 "0")
           (cons 6 "Continuous")
           (cons 100 "AcDbPoint")
           (list 10 1.55 0 0)
           (cons 50 0)
          )
         )
         (entmake
          (list
           (cons 0 "ATTDEF")
           (cons 100 "AcDbEntity")
           (cons 67 0)
           (cons 8 "0")
           (cons 6 "Continuous")
           (cons 100 "AcDbText")
           (list 10 0.85 0.56666667 0)
           (cons 40 0.2)
           (cons 1 "1.550")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 6 "Continuous")
           (cons 100 "AcDbText")
           (list 10 0.85 0.23333333 0)
           (cons 40 0.2)
           (cons 1 "1.550")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 6 "Continuous")
           (cons 100 "AcDbText")
           (list 10 0.85 -0.1 0)
           (cons 40 0.2)
           (cons 1 "14.050")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 6 "Continuous")
           (cons 100 "AcDbText")
           (list 10 0.85 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 6 "Continuous")
           (cons 100 "AcDbText")
           (list 10 0.85 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "BC_MOTI-TS7-Truck"))
        (progn
         (entmake)
         (entmake
          (list
           (cons 0 "BLOCK")
           (cons 2 "BC_MOTI-TS7-Truck")
           (cons 70 2)
           (cons 4 "")
           (list 10 0 0 0)
          )
         )
         (entmake
          (list
           (cons 0 "POINT")
           (cons 100 "AcDbEntity")
           (cons 67 0)
           (cons 8 "0")
           (cons 6 "Continuous")
           (cons 100 "AcDbPoint")
           (list 10 0 1.3 0)
           (cons 50 0)
          )
         )
         (entmake
          (list
           (cons 0 "POINT")
           (cons 100 "AcDbEntity")
           (cons 67 0)
           (cons 8 "0")
           (cons 6 "Continuous")
           (cons 100 "AcDbPoint")
           (list 10 0 -1.3 0)
           (cons 50 0)
          )
         )
         (entmake
          (list
           (cons 0 "POINT")
           (cons 100 "AcDbEntity")
           (cons 67 0)
           (cons 8 "0")
           (cons 6 "Continuous")
           (cons 100 "AcDbPoint")
           (list 10 7.9 -1.3 0)
           (cons 50 0)
          )
         )
         (entmake
          (list
           (cons 0 "POINT")
           (cons 100 "AcDbEntity")
           (cons 67 0)
           (cons 8 "0")
           (cons 6 "Continuous")
           (cons 100 "AcDbPoint")
           (list 10 7.9 1.3 0)
           (cons 50 0)
          )
         )
         (entmake
          (list
           (cons 0 "POINT")
           (cons 100 "AcDbEntity")
           (cons 67 0)
           (cons 8 "0")
           (cons 6 "Continuous")
           (cons 100 "AcDbPoint")
           (list 10 1.1 -1.3 0)
           (cons 50 0)
          )
         )
         (entmake
          (list
           (cons 0 "POINT")
           (cons 100 "AcDbEntity")
           (cons 67 0)
           (cons 8 "0")
           (cons 6 "Continuous")
           (cons 100 "AcDbPoint")
           (list 10 1.1 1.3 0)
           (cons 50 0)
          )
         )
         (entmake
          (list
           (cons 0 "POINT")
           (cons 100 "AcDbEntity")
           (cons 67 0)
           (cons 8 "0")
           (cons 6 "Continuous")
           (cons 100 "AcDbPoint")
           (list 10 1.1 0 0)
           (cons 50 0)
          )
         )
         (entmake
          (list
           (cons 0 "INSERT")
           (cons 100 "AcDbEntity")
           (cons 67 0)
           (cons 8 "0")
           (cons 6 "Continuous")
           (cons 100 "AcDbBlockReference")
           (cons 2 "WheelLeftM1")
           (list 10 1.1 -1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 6 "Continuous")
           (cons 100 "AcDbBlockReference")
           (cons 2 "WheelRightM1")
           (list 10 1.1 1.0206 0)
           (cons 41 1)
           (cons 42 1)
           (cons 43 1)
           (cons 50 0)
           (cons 70 0)
           (cons 71 0)
           (cons 44 0)
           (cons 45 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.341 1.073452)
           (cons 40 0)
           (cons 41 0)
           (cons 42 0)
           (cons 91 0)
           (list 10 7.341 1.247548)
           (cons 40 0)
           (cons 41 0)
           (cons 42 0)
           (cons 91 0)
           (list 10 7.49752 1.3)
           (cons 40 0)
           (cons 41 0)
           (cons 42 0)
           (cons 91 0)
           (list 10 8.30248 1.3)
           (cons 40 0)
           (cons 41 0)
           (cons 42 0)
           (cons 91 0)
           (list 10 8.459 1.247548)
           (cons 40 0)
           (cons 41 0)
           (cons 42 0)
           (cons 91 0)
           (list 10 8.459 1.073452)
           (cons 40 0)
           (cons 41 0)
           (cons 42 0)
           (cons 91 0)
           (list 10 8.30248 1.021)
           (cons 40 0)
           (cons 41 0)
           (cons 42 0)
           (cons 91 0)
           (list 10 7.49752 1.021)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.341 0.570452)
           (cons 40 0)
           (cons 41 0)
           (cons 42 0)
           (cons 91 0)
           (list 10 7.341 0.744548)
           (cons 40 0)
           (cons 41 0)
           (cons 42 0)
           (cons 91 0)
           (list 10 7.49752 0.797)
           (cons 40 0)
           (cons 41 0)
           (cons 42 0)
           (cons 91 0)
           (list 10 8.30248 0.797)
           (cons 40 0)
           (cons 41 0)
           (cons 42 0)
           (cons 91 0)
           (list 10 8.459 0.744548)
           (cons 40 0)
           (cons 41 0)
           (cons 42 0)
           (cons 91 0)
           (list 10 8.459 0.570452)
           (cons 40 0)
           (cons 41 0)
           (cons 42 0)
           (cons 91 0)
           (list 10 8.30248 0.518)
           (cons 40 0)
           (cons 41 0)
           (cons 42 0)
           (cons 91 0)
           (list 10 7.49752 0.518)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.341 -0.744548)
           (cons 40 0)
           (cons 41 0)
           (cons 42 0)
           (cons 91 0)
           (list 10 7.341 -0.570452)
           (cons 40 0)
           (cons 41 0)
           (cons 42 0)
           (cons 91 0)
           (list 10 7.49752 -0.518)
           (cons 40 0)
           (cons 41 0)
           (cons 42 0)
           (cons 91 0)
           (list 10 8.30248 -0.518)
           (cons 40 0)
           (cons 41 0)
           (cons 42 0)
           (cons 91 0)
           (list 10 8.459 -0.570452)
           (cons 40 0)
           (cons 41 0)
           (cons 42 0)
           (cons 91 0)
           (list 10 8.459 -0.744548)
           (cons 40 0)
           (cons 41 0)
           (cons 42 0)
           (cons 91 0)
           (list 10 8.30248 -0.797)
           (cons 40 0)
           (cons 41 0)
           (cons 42 0)
           (cons 91 0)
           (list 10 7.49752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.341 -1.247548)
           (cons 40 0)
           (cons 41 0)
           (cons 42 0)
           (cons 91 0)
           (list 10 7.341 -1.073452)
           (cons 40 0)
           (cons 41 0)
           (cons 42 0)
           (cons 91 0)
           (list 10 7.49752 -1.021)
           (cons 40 0)
           (cons 41 0)
           (cons 42 0)
           (cons 91 0)
           (list 10 8.30248 -1.021)
           (cons 40 0)
           (cons 41 0)
           (cons 42 0)
           (cons 91 0)
           (list 10 8.459 -1.073452)
           (cons 40 0)
           (cons 41 0)
           (cons 42 0)
           (cons 91 0)
           (list 10 8.459 -1.247548)
           (cons 40 0)
           (cons 41 0)
           (cons 42 0)
           (cons 91 0)
           (list 10 8.30248 -1.3)
           (cons 40 0)
           (cons 41 0)
           (cons 42 0)
           (cons 91 0)
           (list 10 7.49752 -1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.38016 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.38016 -0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 10.4 -0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 10.4 0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.38016 0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.38016 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "Defpoints")
           (cons 6 "Continuous")
           (cons 100 "AcDbPolyline")
           (cons 90 8)
           (cons 70 1)
           (cons 43 0)
           (cons 38 0)
           (cons 39 0)
           (list 10 0 -1.3)
           (cons 40 0)
           (cons 41 0)
           (cons 42 0)
           (cons 91 0)
           (list 10 8.459 -1.3)
           (cons 40 0)
           (cons 41 0)
           (cons 42 0)
           (cons 91 0)
           (list 10 8.459 -0.5188)
           (cons 40 0)
           (cons 41 0)
           (cons 42 0)
           (cons 91 0)
           (list 10 10.4 -0.5188)
           (cons 40 0)
           (cons 41 0)
           (cons 42 0)
           (cons 91 0)
           (list 10 10.4 0.5188)
           (cons 40 0)
           (cons 41 0)
           (cons 42 0)
           (cons 91 0)
           (list 10 8.459 0.5188)
           (cons 40 0)
           (cons 41 0)
           (cons 42 0)
           (cons 91 0)
           (list 10 8.459 1.3)
           (cons 40 0)
           (cons 41 0)
           (cons 42 0)
           (cons 91 0)
           (list 10 0 1.3)
           (cons 40 0)
           (cons 41 0)
           (cons 42 0)
           (cons 91 0)
          )
         )
         (entmake
          (list
           (cons 0 "POINT")
           (cons 100 "AcDbEntity")
           (cons 67 0)
           (cons 8 "0")
           (cons 6 "Continuous")
           (cons 100 "AcDbPoint")
           (list 10 7.3 0 0)
           (cons 50 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 7.3 0 0)
           (cons 40 0.17333333)
          )
         )
         (entmake
          (list
           (cons 0 "ATTDEF")
           (cons 100 "AcDbEntity")
           (cons 67 0)
           (cons 8 "0")
           (cons 6 "Continuous")
           (cons 100 "AcDbText")
           (list 10 0.4 0.56666667 0)
           (cons 40 0.2)
           (cons 1 "1.100")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 6 "Continuous")
           (cons 100 "AcDbText")
           (list 10 0.4 0.23333333 0)
           (cons 40 0.2)
           (cons 1 "1.100")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 6 "Continuous")
           (cons 100 "AcDbText")
           (list 10 0.4 -0.1 0)
           (cons 40 0.2)
           (cons 1 "7.900")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 6 "Continuous")
           (cons 100 "AcDbText")
           (list 10 0.4 -0.43333333 0)
           (cons 40 0.2)
           (cons 1 "7.300")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 6 "Continuous")
           (cons 100 "AcDbText")
           (list 10 0.4 -0.76666667 0)
           (cons 40 0.2)
           (cons 1 "32.983")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "BC_MOTI-WB-15-Truck"))
        (progn
         (entmake)
         (entmake
          (list
           (cons 0 "BLOCK")
           (cons 2 "BC_MOTI-WB-15-Truck")
           (cons 70 2)
           (cons 4 "")
           (list 10 0 0 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 6.4 -1.3 0)
           (cons 50 0)
          )
         )
         (entmake
          (list
           (cons 0 "POINT")
           (cons 100 "AcDbEntity")
           (cons 67 0)
           (cons 8 "0")
           (cons 100 "AcDbPoint")
           (list 10 6.4 1.3 0)
           (cons 50 0)
          )
         )
         (entmake
          (list
           (cons 0 "POINT")
           (cons 100 "AcDbEntity")
           (cons 67 0)
           (cons 8 "0")
           (cons 100 "AcDbPoint")
           (list 10 0.9 -1.3 0)
           (cons 50 0)
          )
         )
         (entmake
          (list
           (cons 0 "POINT")
           (cons 100 "AcDbEntity")
           (cons 67 0)
           (cons 8 "0")
           (cons 100 "AcDbPoint")
           (list 10 0.9 1.3 0)
           (cons 50 0)
          )
         )
         (entmake
          (list
           (cons 0 "POINT")
           (cons 100 "AcDbEntity")
           (cons 67 0)
           (cons 8 "0")
           (cons 100 "AcDbPoint")
           (list 10 0.9 0 0)
           (cons 50 0)
          )
         )
         (entmake
          (list
           (cons 0 "INSERT")
           (cons 100 "AcDbEntity")
           (cons 67 0)
           (cons 8 "0")
           (cons 100 "AcDbBlockReference")
           (cons 2 "WheelLeftM1")
           (list 10 0.9 -1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM1")
           (list 10 0.9 1.0206 0)
           (cons 41 1)
           (cons 42 1)
           (cons 43 1)
           (cons 50 0)
           (cons 70 0)
           (cons 71 0)
           (cons 44 0)
           (cons 45 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.841 1.073452)
           (cons 40 0)
           (cons 41 0)
           (cons 42 0)
           (cons 91 0)
           (list 10 5.841 1.247548)
           (cons 40 0)
           (cons 41 0)
           (cons 42 0)
           (cons 91 0)
           (list 10 5.99752 1.3)
           (cons 40 0)
           (cons 41 0)
           (cons 42 0)
           (cons 91 0)
           (list 10 6.80248 1.3)
           (cons 40 0)
           (cons 41 0)
           (cons 42 0)
           (cons 91 0)
           (list 10 6.959 1.247548)
           (cons 40 0)
           (cons 41 0)
           (cons 42 0)
           (cons 91 0)
           (list 10 6.959 1.073452)
           (cons 40 0)
           (cons 41 0)
           (cons 42 0)
           (cons 91 0)
           (list 10 6.80248 1.021)
           (cons 40 0)
           (cons 41 0)
           (cons 42 0)
           (cons 91 0)
           (list 10 5.99752 1.021)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.841 0.570452)
           (cons 40 0)
           (cons 41 0)
           (cons 42 0)
           (cons 91 0)
           (list 10 5.841 0.744548)
           (cons 40 0)
           (cons 41 0)
           (cons 42 0)
           (cons 91 0)
           (list 10 5.99752 0.797)
           (cons 40 0)
           (cons 41 0)
           (cons 42 0)
           (cons 91 0)
           (list 10 6.80248 0.797)
           (cons 40 0)
           (cons 41 0)
           (cons 42 0)
           (cons 91 0)
           (list 10 6.959 0.744548)
           (cons 40 0)
           (cons 41 0)
           (cons 42 0)
           (cons 91 0)
           (list 10 6.959 0.570452)
           (cons 40 0)
           (cons 41 0)
           (cons 42 0)
           (cons 91 0)
           (list 10 6.80248 0.518)
           (cons 40 0)
           (cons 41 0)
           (cons 42 0)
           (cons 91 0)
           (list 10 5.99752 0.518)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.841 -0.744548)
           (cons 40 0)
           (cons 41 0)
           (cons 42 0)
           (cons 91 0)
           (list 10 5.841 -0.570452)
           (cons 40 0)
           (cons 41 0)
           (cons 42 0)
           (cons 91 0)
           (list 10 5.99752 -0.518)
           (cons 40 0)
           (cons 41 0)
           (cons 42 0)
           (cons 91 0)
           (list 10 6.80248 -0.518)
           (cons 40 0)
           (cons 41 0)
           (cons 42 0)
           (cons 91 0)
           (list 10 6.959 -0.570452)
           (cons 40 0)
           (cons 41 0)
           (cons 42 0)
           (cons 91 0)
           (list 10 6.959 -0.744548)
           (cons 40 0)
           (cons 41 0)
           (cons 42 0)
           (cons 91 0)
           (list 10 6.80248 -0.797)
           (cons 40 0)
           (cons 41 0)
           (cons 42 0)
           (cons 91 0)
           (list 10 5.99752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.841 -1.247548)
           (cons 40 0)
           (cons 41 0)
           (cons 42 0)
           (cons 91 0)
           (list 10 5.841 -1.073452)
           (cons 40 0)
           (cons 41 0)
           (cons 42 0)
           (cons 91 0)
           (list 10 5.99752 -1.021)
           (cons 40 0)
           (cons 41 0)
           (cons 42 0)
           (cons 91 0)
           (list 10 6.80248 -1.021)
           (cons 40 0)
           (cons 41 0)
           (cons 42 0)
           (cons 91 0)
           (list 10 6.959 -1.073452)
           (cons 40 0)
           (cons 41 0)
           (cons 42 0)
           (cons 91 0)
           (list 10 6.959 -1.247548)
           (cons 40 0)
           (cons 41 0)
           (cons 42 0)
           (cons 91 0)
           (list 10 6.80248 -1.3)
           (cons 40 0)
           (cons 41 0)
           (cons 42 0)
           (cons 91 0)
           (list 10 5.99752 -1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.18016 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.18016 -0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.6 -0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.6 0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.18016 0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.18016 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "Defpoints")
           (cons 100 "AcDbPolyline")
           (cons 90 8)
           (cons 70 1)
           (cons 43 0)
           (cons 38 0)
           (cons 39 0)
           (list 10 0 -1.3)
           (cons 40 0)
           (cons 41 0)
           (cons 42 0)
           (cons 91 0)
           (list 10 6.959 -1.3)
           (cons 40 0)
           (cons 41 0)
           (cons 42 0)
           (cons 91 0)
           (list 10 6.959 -0.5188)
           (cons 40 0)
           (cons 41 0)
           (cons 42 0)
           (cons 91 0)
           (list 10 7.6 -0.5188)
           (cons 40 0)
           (cons 41 0)
           (cons 42 0)
           (cons 91 0)
           (list 10 7.6 0.5188)
           (cons 40 0)
           (cons 41 0)
           (cons 42 0)
           (cons 91 0)
           (list 10 6.959 0.5188)
           (cons 40 0)
           (cons 41 0)
           (cons 42 0)
           (cons 91 0)
           (list 10 6.959 1.3)
           (cons 40 0)
           (cons 41 0)
           (cons 42 0)
           (cons 91 0)
           (list 10 0 1.3)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 6.4 0 0)
           (cons 50 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 6.4 0 0)
           (cons 40 0.17333333)
          )
         )
         (entmake
          (list
           (cons 0 "ATTDEF")
           (cons 100 "AcDbEntity")
           (cons 67 0)
           (cons 8 "0")
           (cons 100 "AcDbText")
           (list 10 0.2 0.56666667 0)
           (cons 40 0.2)
           (cons 1 "0.900")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.2 0.23333333 0)
           (cons 40 0.2)
           (cons 1 "0.900")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.2 -0.1 0)
           (cons 40 0.2)
           (cons 1 "6.400")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.2 -0.43333333 0)
           (cons 40 0.2)
           (cons 1 "6.400")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.2 -0.76666667 0)
           (cons 40 0.2)
           (cons 1 "26.059")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "BC_MOTI-WB-15-Trailer"))
        (progn
         (entmake)
         (entmake
          (list
           (cons 0 "BLOCK")
           (cons 2 "BC_MOTI-WB-15-Trailer")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 14.7 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 14.7 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.9912 -0.7445528)
           (cons 40 0)
           (cons 41 0)
           (cons 42 0)
           (cons 91 0)
           (list 10 11.9912 -0.5702072)
           (cons 40 0)
           (cons 41 0)
           (cons 42 0)
           (cons 91 0)
           (list 10 12.147664 -0.51768)
           (cons 40 0)
           (cons 41 0)
           (cons 42 0)
           (cons 91 0)
           (list 10 12.952336 -0.51768)
           (cons 40 0)
           (cons 41 0)
           (cons 42 0)
           (cons 91 0)
           (list 10 13.1088 -0.5702072)
           (cons 40 0)
           (cons 41 0)
           (cons 42 0)
           (cons 91 0)
           (list 10 13.1088 -0.7445528)
           (cons 40 0)
           (cons 41 0)
           (cons 42 0)
           (cons 91 0)
           (list 10 12.952336 -0.79708)
           (cons 40 0)
           (cons 41 0)
           (cons 42 0)
           (cons 91 0)
           (list 10 12.147664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.9912 -1.2474728)
           (cons 40 0)
           (cons 41 0)
           (cons 42 0)
           (cons 91 0)
           (list 10 11.9912 -1.0731272)
           (cons 40 0)
           (cons 41 0)
           (cons 42 0)
           (cons 91 0)
           (list 10 12.147664 -1.0206)
           (cons 40 0)
           (cons 41 0)
           (cons 42 0)
           (cons 91 0)
           (list 10 12.952336 -1.0206)
           (cons 40 0)
           (cons 41 0)
           (cons 42 0)
           (cons 91 0)
           (list 10 13.1088 -1.0731272)
           (cons 40 0)
           (cons 41 0)
           (cons 42 0)
           (cons 91 0)
           (list 10 13.1088 -1.2474728)
           (cons 40 0)
           (cons 41 0)
           (cons 42 0)
           (cons 91 0)
           (list 10 12.952336 -1.3)
           (cons 40 0)
           (cons 41 0)
           (cons 42 0)
           (cons 91 0)
           (list 10 12.147664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.9912 0.5702072)
           (cons 40 0)
           (cons 41 0)
           (cons 42 0)
           (cons 91 0)
           (list 10 11.9912 0.7445528)
           (cons 40 0)
           (cons 41 0)
           (cons 42 0)
           (cons 91 0)
           (list 10 12.147664 0.79708)
           (cons 40 0)
           (cons 41 0)
           (cons 42 0)
           (cons 91 0)
           (list 10 12.952336 0.79708)
           (cons 40 0)
           (cons 41 0)
           (cons 42 0)
           (cons 91 0)
           (list 10 13.1088 0.7445528)
           (cons 40 0)
           (cons 41 0)
           (cons 42 0)
           (cons 91 0)
           (list 10 13.1088 0.5702072)
           (cons 40 0)
           (cons 41 0)
           (cons 42 0)
           (cons 91 0)
           (list 10 12.952336 0.51768)
           (cons 40 0)
           (cons 41 0)
           (cons 42 0)
           (cons 91 0)
           (list 10 12.147664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.9912 1.0731272)
           (cons 40 0)
           (cons 41 0)
           (cons 42 0)
           (cons 91 0)
           (list 10 11.9912 1.2474728)
           (cons 40 0)
           (cons 41 0)
           (cons 42 0)
           (cons 91 0)
           (list 10 12.147664 1.3)
           (cons 40 0)
           (cons 41 0)
           (cons 42 0)
           (cons 91 0)
           (list 10 12.952336 1.3)
           (cons 40 0)
           (cons 41 0)
           (cons 42 0)
           (cons 91 0)
           (list 10 13.1088 1.2474728)
           (cons 40 0)
           (cons 41 0)
           (cons 42 0)
           (cons 91 0)
           (list 10 13.1088 1.0731272)
           (cons 40 0)
           (cons 41 0)
           (cons 42 0)
           (cons 91 0)
           (list 10 12.952336 1.0206)
           (cons 40 0)
           (cons 41 0)
           (cons 42 0)
           (cons 91 0)
           (list 10 12.147664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 1.55 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 14.7 -1.3)
           (cons 40 0)
           (cons 41 0)
           (cons 42 0)
           (cons 91 0)
           (list 10 14.7 1.3)
           (cons 40 0)
           (cons 41 0)
           (cons 42 0)
           (cons 91 0)
           (list 10 0 1.3)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 14.7 -1.3 0)
           (cons 50 0)
          )
         )
         (entmake
          (list
           (cons 0 "POINT")
           (cons 100 "AcDbEntity")
           (cons 67 0)
           (cons 8 "0")
           (cons 100 "AcDbPoint")
           (list 10 14.7 1.3 0)
           (cons 50 0)
          )
         )
         (entmake
          (list
           (cons 0 "POINT")
           (cons 100 "AcDbEntity")
           (cons 67 0)
           (cons 8 "0")
           (cons 100 "AcDbPoint")
           (list 10 12.55 1.3 0)
           (cons 50 0)
          )
         )
         (entmake
          (list
           (cons 0 "POINT")
           (cons 100 "AcDbEntity")
           (cons 67 0)
           (cons 8 "0")
           (cons 100 "AcDbPoint")
           (list 10 12.55 -1.3 0)
           (cons 50 0)
          )
         )
         (entmake
          (list
           (cons 0 "ATTDEF")
           (cons 100 "AcDbEntity")
           (cons 67 0)
           (cons 8 "0")
           (cons 100 "AcDbText")
           (list 10 0.85 0.56666667 0)
           (cons 40 0.2)
           (cons 1 "1.550")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.85 0.23333333 0)
           (cons 40 0.2)
           (cons 1 "1.550")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.85 -0.1 0)
           (cons 40 0.2)
           (cons 1 "12.550")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.85 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.85 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "BC_MOTI-LG5-Trailer1"))
        (progn
         (entmake)
         (entmake
          (list
           (cons 0 "BLOCK")
           (cons 2 "BC_MOTI-LG5-Trailer1")
           (cons 70 2)
           (cons 4 "")
           (list 10 0 0 0)
          )
         )
         (entmake
          (list
           (cons 0 "POINT")
           (cons 100 "AcDbEntity")
           (cons 67 0)
           (cons 8 "0")
           (cons 62 1)
           (cons 100 "AcDbPoint")
           (list 10 4.09 0 0)
           (cons 50 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 4.09 0 0)
           (cons 40 0.1524)
          )
         )
         (entmake
          (list
           (cons 0 "POINT")
           (cons 100 "AcDbEntity")
           (cons 67 0)
           (cons 8 "0")
           (cons 100 "AcDbPoint")
           (list 10 7.29 -1.3 0)
           (cons 50 0)
          )
         )
         (entmake
          (list
           (cons 0 "POINT")
           (cons 100 "AcDbEntity")
           (cons 67 0)
           (cons 8 "0")
           (cons 100 "AcDbPoint")
           (list 10 7.29 1.3 0)
           (cons 50 0)
          )
         )
         (entmake
          (list
           (cons 0 "POINT")
           (cons 100 "AcDbEntity")
           (cons 67 0)
           (cons 8 "0")
           (cons 100 "AcDbPoint")
           (list 10 0.7 0 0)
           (cons 50 0)
          )
         )
         (entmake
          (list
           (cons 0 "POINT")
           (cons 100 "AcDbEntity")
           (cons 67 0)
           (cons 8 "0")
           (cons 100 "AcDbPoint")
           (list 10 8.89 0 0)
           (cons 50 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 8.89 0 0)
           (cons 40 0.17333333)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.731 1.073452)
           (cons 40 0)
           (cons 41 0)
           (cons 42 0)
           (cons 91 0)
           (list 10 6.731 1.247548)
           (cons 40 0)
           (cons 41 0)
           (cons 42 0)
           (cons 91 0)
           (list 10 6.88752 1.3)
           (cons 40 0)
           (cons 41 0)
           (cons 42 0)
           (cons 91 0)
           (list 10 7.69248 1.3)
           (cons 40 0)
           (cons 41 0)
           (cons 42 0)
           (cons 91 0)
           (list 10 7.849 1.247548)
           (cons 40 0)
           (cons 41 0)
           (cons 42 0)
           (cons 91 0)
           (list 10 7.849 1.073452)
           (cons 40 0)
           (cons 41 0)
           (cons 42 0)
           (cons 91 0)
           (list 10 7.69248 1.021)
           (cons 40 0)
           (cons 41 0)
           (cons 42 0)
           (cons 91 0)
           (list 10 6.88752 1.021)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.731 0.570452)
           (cons 40 0)
           (cons 41 0)
           (cons 42 0)
           (cons 91 0)
           (list 10 6.731 0.744548)
           (cons 40 0)
           (cons 41 0)
           (cons 42 0)
           (cons 91 0)
           (list 10 6.88752 0.797)
           (cons 40 0)
           (cons 41 0)
           (cons 42 0)
           (cons 91 0)
           (list 10 7.69248 0.797)
           (cons 40 0)
           (cons 41 0)
           (cons 42 0)
           (cons 91 0)
           (list 10 7.849 0.744548)
           (cons 40 0)
           (cons 41 0)
           (cons 42 0)
           (cons 91 0)
           (list 10 7.849 0.570452)
           (cons 40 0)
           (cons 41 0)
           (cons 42 0)
           (cons 91 0)
           (list 10 7.69248 0.518)
           (cons 40 0)
           (cons 41 0)
           (cons 42 0)
           (cons 91 0)
           (list 10 6.88752 0.518)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.731 -0.744548)
           (cons 40 0)
           (cons 41 0)
           (cons 42 0)
           (cons 91 0)
           (list 10 6.731 -0.570452)
           (cons 40 0)
           (cons 41 0)
           (cons 42 0)
           (cons 91 0)
           (list 10 6.88752 -0.518)
           (cons 40 0)
           (cons 41 0)
           (cons 42 0)
           (cons 91 0)
           (list 10 7.69248 -0.518)
           (cons 40 0)
           (cons 41 0)
           (cons 42 0)
           (cons 91 0)
           (list 10 7.849 -0.570452)
           (cons 40 0)
           (cons 41 0)
           (cons 42 0)
           (cons 91 0)
           (list 10 7.849 -0.744548)
           (cons 40 0)
           (cons 41 0)
           (cons 42 0)
           (cons 91 0)
           (list 10 7.69248 -0.797)
           (cons 40 0)
           (cons 41 0)
           (cons 42 0)
           (cons 91 0)
           (list 10 6.88752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.731 -1.247548)
           (cons 40 0)
           (cons 41 0)
           (cons 42 0)
           (cons 91 0)
           (list 10 6.731 -1.073452)
           (cons 40 0)
           (cons 41 0)
           (cons 42 0)
           (cons 91 0)
           (list 10 6.88752 -1.021)
           (cons 40 0)
           (cons 41 0)
           (cons 42 0)
           (cons 91 0)
           (list 10 7.69248 -1.021)
           (cons 40 0)
           (cons 41 0)
           (cons 42 0)
           (cons 91 0)
           (list 10 7.849 -1.073452)
           (cons 40 0)
           (cons 41 0)
           (cons 42 0)
           (cons 91 0)
           (list 10 7.849 -1.247548)
           (cons 40 0)
           (cons 41 0)
           (cons 42 0)
           (cons 91 0)
           (list 10 7.69248 -1.3)
           (cons 40 0)
           (cons 41 0)
           (cons 42 0)
           (cons 91 0)
           (list 10 6.88752 -1.3)
           (cons 40 0)
           (cons 41 0)
           (cons 42 0)
           (cons 91 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0.7 0 0)
           (cons 40 0.104)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.89 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.89 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "POLYLINE")
           (cons 100 "AcDbEntity")
           (cons 67 0)
           (cons 8 "Defpoints")
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "Defpoints")
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.731 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.731 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 7.849 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 7.849 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 8.89 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 8.89 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 7.849 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 7.849 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.731 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.731 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 0 0.5 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "Defpoints")
          )
         )
         (entmake
          (list
           (cons 0 "TEXT")
           (cons 100 "AcDbEntity")
           (cons 67 0)
           (cons 8 "0")
           (cons 100 "AcDbText")
           (list 10 1.53333333 -0.25 0)
           (cons 40 0.5)
           (cons 1 "2")
           (cons 50 0)
           (cons 41 1)
           (cons 51 0)
           (cons 7 "Standard")
           (cons 71 0)
           (cons 72 4)
           (list 11 1.7 0 0)
           (cons 100 "AcDbText")
           (cons 73 0)
          )
         )
         (entmake
          (list
           (cons 0 "ATTDEF")
           (cons 100 "AcDbEntity")
           (cons 67 0)
           (cons 8 "0")
           (cons 100 "AcDbText")
           (list 10 -0.3 0.56666667 0)
           (cons 40 0.2)
           (cons 1 "0.700")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 0.23333333 0)
           (cons 40 0.2)
           (cons 1 "0.700")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.1 0)
           (cons 40 0.2)
           (cons 1 "7.290")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.43333333 0)
           (cons 40 0.2)
           (cons 1 "8.890")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -1.10000001 0)
           (cons 40 0.2)
           (cons 1 "4.090")
           (cons 50 0)
           (cons 41 1)
           (cons 51 0)
           (cons 7 "Standard")
           (cons 71 0)
           (cons 72 0)
           (list 11 0 0 0)
           (cons 100 "AcDbAttributeDefinition")
           (cons 3 "Load Angle Point (LA)")
           (cons 2 "LA")
           (cons 70 9)
           (cons 73 0)
           (cons 74 0)
          )
         )
         (entmake (list (cons 0 "ENDBLK")))
        )
       )
       ((= (strcase BLKNAME) (strcase "BC_MOTI-LG5-Load"))
        (progn
         (entmake)
         (entmake
          (list
           (cons 0 "BLOCK")
           (cons 2 "BC_MOTI-LG5-Load")
           (cons 70 2)
           (cons 4 "")
           (list 10 0 0 0)
          )
         )
         (entmake
          (list
           (cons 0 "POINT")
           (cons 100 "AcDbEntity")
           (cons 67 0)
           (cons 8 "0")
           (cons 100 "AcDbPoint")
           (list 10 16.8 1.3 0)
           (cons 50 0)
          )
         )
         (entmake
          (list
           (cons 0 "POINT")
           (cons 100 "AcDbEntity")
           (cons 67 0)
           (cons 8 "0")
           (cons 100 "AcDbPoint")
           (list 10 16.8 -1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 62 3)
           (cons 100 "AcDbPoint")
           (list 10 15 0 0)
           (cons 50 0)
          )
         )
         (entmake
          (list
           (cons 0 "POINT")
           (cons 100 "AcDbEntity")
           (cons 67 0)
           (cons 8 "0")
           (cons 62 3)
           (cons 100 "AcDbPoint")
           (list 10 4.2 0 0)
           (cons 50 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 4.2 0 0)
           (cons 40 0.1524)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 16.8 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 16.8 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 15 0 0)
           (cons 40 0.1524)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 16.8 -1.3)
           (cons 40 0)
           (cons 41 0)
           (cons 42 0)
           (cons 91 0)
           (list 10 16.8 1.3)
           (cons 40 0)
           (cons 41 0)
           (cons 42 0)
           (cons 91 0)
           (list 10 0 1.3)
           (cons 40 0)
           (cons 41 0)
           (cons 42 0)
           (cons 91 0)
          )
         )
         (entmake
          (list
           (cons 0 "TEXT")
           (cons 100 "AcDbEntity")
           (cons 67 0)
           (cons 8 "0")
           (cons 100 "AcDbText")
           (list 10 5.02142857 -0.25 0)
           (cons 40 0.5)
           (cons 1 "4")
           (cons 50 0)
           (cons 41 1)
           (cons 51 0)
           (cons 7 "Standard")
           (cons 71 0)
           (cons 72 4)
           (list 11 5.2 0 0)
           (cons 100 "AcDbText")
           (cons 73 0)
          )
         )
         (entmake
          (list
           (cons 0 "ATTDEF")
           (cons 100 "AcDbEntity")
           (cons 67 0)
           (cons 8 "0")
           (cons 100 "AcDbText")
           (list 10 3.5 -0.1 0)
           (cons 40 0.2)
           (cons 1 "15.000")
           (cons 50 0)
           (cons 41 1)
           (cons 51 0)
           (cons 7 "Standard")
           (cons 71 0)
           (cons 72 0)
           (list 11 0 0 0)
           (cons 100 "AcDbAttributeDefinition")
           (cons 3 "Load Base Point (LB)")
           (cons 2 "LB")
           (cons 70 9)
           (cons 73 0)
           (cons 74 0)
          )
         )
         (entmake
          (list
           (cons 0 "ATTDEF")
           (cons 100 "AcDbEntity")
           (cons 67 0)
           (cons 8 "0")
           (cons 100 "AcDbText")
           (list 10 3.5 -0.43333333 0)
           (cons 40 0.2)
           (cons 1 "4.200")
           (cons 50 0)
           (cons 41 1)
           (cons 51 0)
           (cons 7 "Standard")
           (cons 71 0)
           (cons 72 0)
           (list 11 0 0 0)
           (cons 100 "AcDbAttributeDefinition")
           (cons 3 "Load Angle Point (LA)")
           (cons 2 "LA")
           (cons 70 9)
           (cons 73 0)
           (cons 74 0)
          )
         )
         (entmake (list (cons 0 "ENDBLK")))
        )
       )
       ((= (strcase BLKNAME) (strcase "BC_MOTI-LG5-Trailer2"))
        (progn
         (entmake)
         (entmake
          (list
           (cons 0 "BLOCK")
           (cons 2 "BC_MOTI-LG5-Trailer2")
           (cons 70 2)
           (cons 4 "")
           (list 10 0 0 0)
          )
         )
         (entmake
          (list
           (cons 0 "POINT")
           (cons 100 "AcDbEntity")
           (cons 67 0)
           (cons 8 "0")
           (cons 100 "AcDbPoint")
           (list 10 5.95 -1.3 0)
           (cons 50 0)
          )
         )
         (entmake
          (list
           (cons 0 "POINT")
           (cons 100 "AcDbEntity")
           (cons 67 0)
           (cons 8 "0")
           (cons 100 "AcDbPoint")
           (list 10 5.95 1.3 0)
           (cons 50 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 6 0 0)
           (cons 40 0.1524)
          )
         )
         (entmake
          (list
           (cons 0 "POINT")
           (cons 100 "AcDbEntity")
           (cons 67 0)
           (cons 8 "0")
           (cons 62 1)
           (cons 6 "Continuous")
           (cons 48 1.524)
           (cons 100 "AcDbPoint")
           (list 10 6 0 0)
           (cons 50 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.391 0.570452)
           (cons 40 0)
           (cons 41 0)
           (cons 42 0)
           (cons 91 0)
           (list 10 5.391 0.744548)
           (cons 40 0)
           (cons 41 0)
           (cons 42 0)
           (cons 91 0)
           (list 10 5.54752 0.797)
           (cons 40 0)
           (cons 41 0)
           (cons 42 0)
           (cons 91 0)
           (list 10 6.35248 0.797)
           (cons 40 0)
           (cons 41 0)
           (cons 42 0)
           (cons 91 0)
           (list 10 6.509 0.744548)
           (cons 40 0)
           (cons 41 0)
           (cons 42 0)
           (cons 91 0)
           (list 10 6.509 0.570452)
           (cons 40 0)
           (cons 41 0)
           (cons 42 0)
           (cons 91 0)
           (list 10 6.35248 0.518)
           (cons 40 0)
           (cons 41 0)
           (cons 42 0)
           (cons 91 0)
           (list 10 5.54752 0.518)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.391 -0.744548)
           (cons 40 0)
           (cons 41 0)
           (cons 42 0)
           (cons 91 0)
           (list 10 5.391 -0.570452)
           (cons 40 0)
           (cons 41 0)
           (cons 42 0)
           (cons 91 0)
           (list 10 5.54752 -0.518)
           (cons 40 0)
           (cons 41 0)
           (cons 42 0)
           (cons 91 0)
           (list 10 6.35248 -0.518)
           (cons 40 0)
           (cons 41 0)
           (cons 42 0)
           (cons 91 0)
           (list 10 6.509 -0.570452)
           (cons 40 0)
           (cons 41 0)
           (cons 42 0)
           (cons 91 0)
           (list 10 6.509 -0.744548)
           (cons 40 0)
           (cons 41 0)
           (cons 42 0)
           (cons 91 0)
           (list 10 6.35248 -0.797)
           (cons 40 0)
           (cons 41 0)
           (cons 42 0)
           (cons 91 0)
           (list 10 5.54752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.391 -1.247548)
           (cons 40 0)
           (cons 41 0)
           (cons 42 0)
           (cons 91 0)
           (list 10 5.391 -1.073452)
           (cons 40 0)
           (cons 41 0)
           (cons 42 0)
           (cons 91 0)
           (list 10 5.54752 -1.021)
           (cons 40 0)
           (cons 41 0)
           (cons 42 0)
           (cons 91 0)
           (list 10 6.35248 -1.021)
           (cons 40 0)
           (cons 41 0)
           (cons 42 0)
           (cons 91 0)
           (list 10 6.509 -1.073452)
           (cons 40 0)
           (cons 41 0)
           (cons 42 0)
           (cons 91 0)
           (list 10 6.509 -1.247548)
           (cons 40 0)
           (cons 41 0)
           (cons 42 0)
           (cons 91 0)
           (list 10 6.35248 -1.3)
           (cons 40 0)
           (cons 41 0)
           (cons 42 0)
           (cons 91 0)
           (list 10 5.54752 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.391 1.073452)
           (cons 40 0)
           (cons 41 0)
           (cons 42 0)
           (cons 91 0)
           (list 10 5.391 1.247548)
           (cons 40 0)
           (cons 41 0)
           (cons 42 0)
           (cons 91 0)
           (list 10 5.54752 1.3)
           (cons 40 0)
           (cons 41 0)
           (cons 42 0)
           (cons 91 0)
           (list 10 6.35248 1.3)
           (cons 40 0)
           (cons 41 0)
           (cons 42 0)
           (cons 91 0)
           (list 10 6.509 1.247548)
           (cons 40 0)
           (cons 41 0)
           (cons 42 0)
           (cons 91 0)
           (list 10 6.509 1.073452)
           (cons 40 0)
           (cons 41 0)
           (cons 42 0)
           (cons 91 0)
           (list 10 6.35248 1.021)
           (cons 40 0)
           (cons 41 0)
           (cons 42 0)
           (cons 91 0)
           (list 10 5.54752 1.021)
           (cons 40 0)
           (cons 41 0)
           (cons 42 0)
           (cons 91 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.1016)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.8 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.8 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "POLYLINE")
           (cons 100 "AcDbEntity")
           (cons 67 0)
           (cons 8 "Defpoints")
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "Defpoints")
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 5.391 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 5.391 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.509 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.509 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 7.8 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 7.8 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.509 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.509 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 5.391 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 5.391 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 0 0.5 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "Defpoints")
          )
         )
         (entmake
          (list
           (cons 0 "TEXT")
           (cons 100 "AcDbEntity")
           (cons 67 0)
           (cons 8 "0")
           (cons 100 "AcDbText")
           (list 10 0.83333333 -0.25 0)
           (cons 40 0.5)
           (cons 1 "3")
           (cons 50 0)
           (cons 41 1)
           (cons 51 0)
           (cons 7 "Standard")
           (cons 71 0)
           (cons 72 4)
           (list 11 1 0 0)
           (cons 100 "AcDbText")
           (cons 73 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "5.950")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -1.1 0)
           (cons 40 0.2)
           (cons 1 "6.000")
           (cons 50 0)
           (cons 41 1)
           (cons 51 0)
           (cons 7 "Standard")
           (cons 71 0)
           (cons 72 0)
           (list 11 0 0 0)
           (cons 100 "AcDbAttributeDefinition")
           (cons 3 "Load Base Point (LB)")
           (cons 2 "LB")
           (cons 70 9)
           (cons 73 0)
           (cons 74 0)
          )
         )
         (entmake (list (cons 0 "ENDBLK")))
        )
       )
       ((= (strcase BLKNAME) (strcase "BC_MOTI-LG5-Truck"))
        (progn
         (entmake)
         (entmake
          (list
           (cons 0 "BLOCK")
           (cons 2 "BC_MOTI-LG5-Truck")
           (cons 70 2)
           (cons 4 "")
           (list 10 0 0 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 7 -1.3 0)
           (cons 50 0)
          )
         )
         (entmake
          (list
           (cons 0 "POINT")
           (cons 100 "AcDbEntity")
           (cons 67 0)
           (cons 8 "0")
           (cons 100 "AcDbPoint")
           (list 10 7 1.3 0)
           (cons 50 0)
          )
         )
         (entmake
          (list
           (cons 0 "POINT")
           (cons 100 "AcDbEntity")
           (cons 67 0)
           (cons 8 "0")
           (cons 100 "AcDbPoint")
           (list 10 1.1 -1.3 0)
           (cons 50 0)
          )
         )
         (entmake
          (list
           (cons 0 "POINT")
           (cons 100 "AcDbEntity")
           (cons 67 0)
           (cons 8 "0")
           (cons 100 "AcDbPoint")
           (list 10 1.1 1.3 0)
           (cons 50 0)
          )
         )
         (entmake
          (list
           (cons 0 "POINT")
           (cons 100 "AcDbEntity")
           (cons 67 0)
           (cons 8 "0")
           (cons 100 "AcDbPoint")
           (list 10 1.1 0 0)
           (cons 50 0)
          )
         )
         (entmake
          (list
           (cons 0 "INSERT")
           (cons 100 "AcDbEntity")
           (cons 67 0)
           (cons 8 "0")
           (cons 100 "AcDbBlockReference")
           (cons 2 "WheelLeftM1")
           (list 10 1.1 -1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM1")
           (list 10 1.1 1.0206 0)
           (cons 41 1)
           (cons 42 1)
           (cons 43 1)
           (cons 50 0)
           (cons 70 0)
           (cons 71 0)
           (cons 44 0)
           (cons 45 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.441 1.073452)
           (cons 40 0)
           (cons 41 0)
           (cons 42 0)
           (cons 91 0)
           (list 10 6.441 1.247548)
           (cons 40 0)
           (cons 41 0)
           (cons 42 0)
           (cons 91 0)
           (list 10 6.59752 1.3)
           (cons 40 0)
           (cons 41 0)
           (cons 42 0)
           (cons 91 0)
           (list 10 7.40248 1.3)
           (cons 40 0)
           (cons 41 0)
           (cons 42 0)
           (cons 91 0)
           (list 10 7.559 1.247548)
           (cons 40 0)
           (cons 41 0)
           (cons 42 0)
           (cons 91 0)
           (list 10 7.559 1.073452)
           (cons 40 0)
           (cons 41 0)
           (cons 42 0)
           (cons 91 0)
           (list 10 7.40248 1.021)
           (cons 40 0)
           (cons 41 0)
           (cons 42 0)
           (cons 91 0)
           (list 10 6.59752 1.021)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.441 0.570452)
           (cons 40 0)
           (cons 41 0)
           (cons 42 0)
           (cons 91 0)
           (list 10 6.441 0.744548)
           (cons 40 0)
           (cons 41 0)
           (cons 42 0)
           (cons 91 0)
           (list 10 6.59752 0.797)
           (cons 40 0)
           (cons 41 0)
           (cons 42 0)
           (cons 91 0)
           (list 10 7.40248 0.797)
           (cons 40 0)
           (cons 41 0)
           (cons 42 0)
           (cons 91 0)
           (list 10 7.559 0.744548)
           (cons 40 0)
           (cons 41 0)
           (cons 42 0)
           (cons 91 0)
           (list 10 7.559 0.570452)
           (cons 40 0)
           (cons 41 0)
           (cons 42 0)
           (cons 91 0)
           (list 10 7.40248 0.518)
           (cons 40 0)
           (cons 41 0)
           (cons 42 0)
           (cons 91 0)
           (list 10 6.59752 0.518)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.441 -0.744548)
           (cons 40 0)
           (cons 41 0)
           (cons 42 0)
           (cons 91 0)
           (list 10 6.441 -0.570452)
           (cons 40 0)
           (cons 41 0)
           (cons 42 0)
           (cons 91 0)
           (list 10 6.59752 -0.518)
           (cons 40 0)
           (cons 41 0)
           (cons 42 0)
           (cons 91 0)
           (list 10 7.40248 -0.518)
           (cons 40 0)
           (cons 41 0)
           (cons 42 0)
           (cons 91 0)
           (list 10 7.559 -0.570452)
           (cons 40 0)
           (cons 41 0)
           (cons 42 0)
           (cons 91 0)
           (list 10 7.559 -0.744548)
           (cons 40 0)
           (cons 41 0)
           (cons 42 0)
           (cons 91 0)
           (list 10 7.40248 -0.797)
           (cons 40 0)
           (cons 41 0)
           (cons 42 0)
           (cons 91 0)
           (list 10 6.59752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.441 -1.247548)
           (cons 40 0)
           (cons 41 0)
           (cons 42 0)
           (cons 91 0)
           (list 10 6.441 -1.073452)
           (cons 40 0)
           (cons 41 0)
           (cons 42 0)
           (cons 91 0)
           (list 10 6.59752 -1.021)
           (cons 40 0)
           (cons 41 0)
           (cons 42 0)
           (cons 91 0)
           (list 10 7.40248 -1.021)
           (cons 40 0)
           (cons 41 0)
           (cons 42 0)
           (cons 91 0)
           (list 10 7.559 -1.073452)
           (cons 40 0)
           (cons 41 0)
           (cons 42 0)
           (cons 91 0)
           (list 10 7.559 -1.247548)
           (cons 40 0)
           (cons 41 0)
           (cons 42 0)
           (cons 91 0)
           (list 10 7.40248 -1.3)
           (cons 40 0)
           (cons 41 0)
           (cons 42 0)
           (cons 91 0)
           (list 10 6.59752 -1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.38016 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.38016 -0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.8 -0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.8 0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.38016 0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.38016 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "Defpoints")
           (cons 100 "AcDbPolyline")
           (cons 90 8)
           (cons 70 1)
           (cons 43 0)
           (cons 38 0)
           (cons 39 0)
           (list 10 0 -1.3)
           (cons 40 0)
           (cons 41 0)
           (cons 42 0)
           (cons 91 0)
           (list 10 7.559 -1.3)
           (cons 40 0)
           (cons 41 0)
           (cons 42 0)
           (cons 91 0)
           (list 10 7.559 -0.5188)
           (cons 40 0)
           (cons 41 0)
           (cons 42 0)
           (cons 91 0)
           (list 10 8.8 -0.5188)
           (cons 40 0)
           (cons 41 0)
           (cons 42 0)
           (cons 91 0)
           (list 10 8.8 0.5188)
           (cons 40 0)
           (cons 41 0)
           (cons 42 0)
           (cons 91 0)
           (list 10 7.559 0.5188)
           (cons 40 0)
           (cons 41 0)
           (cons 42 0)
           (cons 91 0)
           (list 10 7.559 1.3)
           (cons 40 0)
           (cons 41 0)
           (cons 42 0)
           (cons 91 0)
           (list 10 0 1.3)
           (cons 40 0)
           (cons 41 0)
           (cons 42 0)
           (cons 91 0)
          )
         )
         (entmake
          (list
           (cons 0 "TEXT")
           (cons 100 "AcDbEntity")
           (cons 67 0)
           (cons 8 "0")
           (cons 100 "AcDbText")
           (list 10 2.04047619 -0.25 0)
           (cons 40 0.5)
           (cons 1 "1")
           (cons 50 0)
           (cons 41 1)
           (cons 51 0)
           (cons 7 "Standard")
           (cons 71 0)
           (cons 72 4)
           (list 11 2.1 0 0)
           (cons 100 "AcDbText")
           (cons 73 0)
          )
         )
         (entmake
          (list
           (cons 0 "POINT")
           (cons 100 "AcDbEntity")
           (cons 67 0)
           (cons 8 "0")
           (cons 100 "AcDbPoint")
           (list 10 6.68 0 0)
           (cons 50 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 6.68 0 0)
           (cons 40 0.17333333)
          )
         )
         (entmake
          (list
           (cons 0 "ATTDEF")
           (cons 100 "AcDbEntity")
           (cons 67 0)
           (cons 8 "0")
           (cons 100 "AcDbText")
           (list 10 0.4 0.56666667 0)
           (cons 40 0.2)
           (cons 1 "1.100")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.4 0.23333333 0)
           (cons 40 0.2)
           (cons 1 "1.100")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.4 -0.1 0)
           (cons 40 0.2)
           (cons 1 "7.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.4 -0.43333333 0)
           (cons 40 0.2)
           (cons 1 "6.680")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.4 -0.76666667 0)
           (cons 40 0.2)
           (cons 1 "32.983")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "BC_MOTI-LG3-Load"))
        (progn
         (entmake)
         (entmake
          (list
           (cons 0 "BLOCK")
           (cons 2 "BC_MOTI-LG3-Load")
           (cons 70 2)
           (cons 4 "")
           (list 10 0 0 0)
          )
         )
         (entmake
          (list
           (cons 0 "POINT")
           (cons 100 "AcDbEntity")
           (cons 67 0)
           (cons 8 "0")
           (cons 100 "AcDbPoint")
           (list 10 16.7 1.3 0)
           (cons 50 0)
          )
         )
         (entmake
          (list
           (cons 0 "POINT")
           (cons 100 "AcDbEntity")
           (cons 67 0)
           (cons 8 "0")
           (cons 100 "AcDbPoint")
           (list 10 16.7 -1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 62 3)
           (cons 100 "AcDbPoint")
           (list 10 12.85 0 0)
           (cons 50 0)
          )
         )
         (entmake
          (list
           (cons 0 "POINT")
           (cons 100 "AcDbEntity")
           (cons 67 0)
           (cons 8 "0")
           (cons 62 3)
           (cons 100 "AcDbPoint")
           (list 10 2.5 0 0)
           (cons 50 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 2.5 0 0)
           (cons 40 0.1524)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 16.7 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 16.7 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 12.85 0 0)
           (cons 40 0.1524)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 16.7 -1.3)
           (cons 40 0)
           (cons 41 0)
           (cons 42 0)
           (cons 91 0)
           (list 10 16.7 1.3)
           (cons 40 0)
           (cons 41 0)
           (cons 42 0)
           (cons 91 0)
           (list 10 0 1.3)
           (cons 40 0)
           (cons 41 0)
           (cons 42 0)
           (cons 91 0)
          )
         )
         (entmake
          (list
           (cons 0 "TEXT")
           (cons 100 "AcDbEntity")
           (cons 67 0)
           (cons 8 "0")
           (cons 100 "AcDbText")
           (list 10 3.32142857 -0.25 0)
           (cons 40 0.5)
           (cons 1 "4")
           (cons 50 0)
           (cons 41 1)
           (cons 51 0)
           (cons 7 "Standard")
           (cons 71 0)
           (cons 72 4)
           (list 11 3.5 0 0)
           (cons 100 "AcDbText")
           (cons 73 0)
          )
         )
         (entmake
          (list
           (cons 0 "ATTDEF")
           (cons 100 "AcDbEntity")
           (cons 67 0)
           (cons 8 "0")
           (cons 100 "AcDbText")
           (list 10 1.8 -0.1 0)
           (cons 40 0.2)
           (cons 1 "12.850")
           (cons 50 0)
           (cons 41 1)
           (cons 51 0)
           (cons 7 "Standard")
           (cons 71 0)
           (cons 72 0)
           (list 11 0 0 0)
           (cons 100 "AcDbAttributeDefinition")
           (cons 3 "Load Base Point (LB)")
           (cons 2 "LB")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.8 -0.43333333 0)
           (cons 40 0.2)
           (cons 1 "2.500")
           (cons 50 0)
           (cons 41 1)
           (cons 51 0)
           (cons 7 "Standard")
           (cons 71 0)
           (cons 72 0)
           (list 11 0 0 0)
           (cons 100 "AcDbAttributeDefinition")
           (cons 3 "Load Angle Point (LA)")
           (cons 2 "LA")
           (cons 70 9)
           (cons 73 0)
           (cons 74 0)
          )
         )
         (entmake (list (cons 0 "ENDBLK")))
        )
       )
       ((= (strcase BLKNAME) (strcase "BC_MOTI-LG3-Trailer2"))
        (progn
         (entmake)
         (entmake
          (list
           (cons 0 "BLOCK")
           (cons 2 "BC_MOTI-LG3-Trailer2")
           (cons 70 2)
           (cons 4 "")
           (list 10 0 0 0)
          )
         )
         (entmake
          (list
           (cons 0 "POINT")
           (cons 100 "AcDbEntity")
           (cons 67 0)
           (cons 8 "0")
           (cons 100 "AcDbPoint")
           (list 10 5.15 -1.3 0)
           (cons 50 0)
          )
         )
         (entmake
          (list
           (cons 0 "POINT")
           (cons 100 "AcDbEntity")
           (cons 67 0)
           (cons 8 "0")
           (cons 100 "AcDbPoint")
           (list 10 5.15 1.3 0)
           (cons 50 0)
          )
         )
         (entmake
          (list
           (cons 0 "POINT")
           (cons 100 "AcDbEntity")
           (cons 67 0)
           (cons 8 "0")
           (cons 100 "AcDbPoint")
           (list 10 0.5 0 0)
           (cons 50 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 3.72 0 0)
           (cons 40 0.1524)
          )
         )
         (entmake
          (list
           (cons 0 "POINT")
           (cons 100 "AcDbEntity")
           (cons 67 0)
           (cons 8 "0")
           (cons 62 1)
           (cons 6 "Continuous")
           (cons 48 1.524)
           (cons 100 "AcDbPoint")
           (list 10 3.72 0 0)
           (cons 50 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.591 0.570452)
           (cons 40 0)
           (cons 41 0)
           (cons 42 0)
           (cons 91 0)
           (list 10 4.591 0.744548)
           (cons 40 0)
           (cons 41 0)
           (cons 42 0)
           (cons 91 0)
           (list 10 4.74752 0.797)
           (cons 40 0)
           (cons 41 0)
           (cons 42 0)
           (cons 91 0)
           (list 10 5.55248 0.797)
           (cons 40 0)
           (cons 41 0)
           (cons 42 0)
           (cons 91 0)
           (list 10 5.709 0.744548)
           (cons 40 0)
           (cons 41 0)
           (cons 42 0)
           (cons 91 0)
           (list 10 5.709 0.570452)
           (cons 40 0)
           (cons 41 0)
           (cons 42 0)
           (cons 91 0)
           (list 10 5.55248 0.518)
           (cons 40 0)
           (cons 41 0)
           (cons 42 0)
           (cons 91 0)
           (list 10 4.74752 0.518)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.591 -0.744548)
           (cons 40 0)
           (cons 41 0)
           (cons 42 0)
           (cons 91 0)
           (list 10 4.591 -0.570452)
           (cons 40 0)
           (cons 41 0)
           (cons 42 0)
           (cons 91 0)
           (list 10 4.74752 -0.518)
           (cons 40 0)
           (cons 41 0)
           (cons 42 0)
           (cons 91 0)
           (list 10 5.55248 -0.518)
           (cons 40 0)
           (cons 41 0)
           (cons 42 0)
           (cons 91 0)
           (list 10 5.709 -0.570452)
           (cons 40 0)
           (cons 41 0)
           (cons 42 0)
           (cons 91 0)
           (list 10 5.709 -0.744548)
           (cons 40 0)
           (cons 41 0)
           (cons 42 0)
           (cons 91 0)
           (list 10 5.55248 -0.797)
           (cons 40 0)
           (cons 41 0)
           (cons 42 0)
           (cons 91 0)
           (list 10 4.74752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.591 -1.247548)
           (cons 40 0)
           (cons 41 0)
           (cons 42 0)
           (cons 91 0)
           (list 10 4.591 -1.073452)
           (cons 40 0)
           (cons 41 0)
           (cons 42 0)
           (cons 91 0)
           (list 10 4.74752 -1.021)
           (cons 40 0)
           (cons 41 0)
           (cons 42 0)
           (cons 91 0)
           (list 10 5.55248 -1.021)
           (cons 40 0)
           (cons 41 0)
           (cons 42 0)
           (cons 91 0)
           (list 10 5.709 -1.073452)
           (cons 40 0)
           (cons 41 0)
           (cons 42 0)
           (cons 91 0)
           (list 10 5.709 -1.247548)
           (cons 40 0)
           (cons 41 0)
           (cons 42 0)
           (cons 91 0)
           (list 10 5.55248 -1.3)
           (cons 40 0)
           (cons 41 0)
           (cons 42 0)
           (cons 91 0)
           (list 10 4.74752 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.591 1.073452)
           (cons 40 0)
           (cons 41 0)
           (cons 42 0)
           (cons 91 0)
           (list 10 4.591 1.247548)
           (cons 40 0)
           (cons 41 0)
           (cons 42 0)
           (cons 91 0)
           (list 10 4.74752 1.3)
           (cons 40 0)
           (cons 41 0)
           (cons 42 0)
           (cons 91 0)
           (list 10 5.55248 1.3)
           (cons 40 0)
           (cons 41 0)
           (cons 42 0)
           (cons 91 0)
           (list 10 5.709 1.247548)
           (cons 40 0)
           (cons 41 0)
           (cons 42 0)
           (cons 91 0)
           (list 10 5.709 1.073452)
           (cons 40 0)
           (cons 41 0)
           (cons 42 0)
           (cons 91 0)
           (list 10 5.55248 1.021)
           (cons 40 0)
           (cons 41 0)
           (cons 42 0)
           (cons 91 0)
           (list 10 4.74752 1.021)
           (cons 40 0)
           (cons 41 0)
           (cons 42 0)
           (cons 91 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0.5 0 0)
           (cons 40 0.1016)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.57 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.57 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "POLYLINE")
           (cons 100 "AcDbEntity")
           (cons 67 0)
           (cons 8 "Defpoints")
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "Defpoints")
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 4.591 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 4.591 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 5.709 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 5.709 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 7.57 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 7.57 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 5.709 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 5.709 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 4.591 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 4.591 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 0 0.5 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "Defpoints")
          )
         )
         (entmake
          (list
           (cons 0 "TEXT")
           (cons 100 "AcDbEntity")
           (cons 67 0)
           (cons 8 "0")
           (cons 100 "AcDbText")
           (list 10 1.33333333 -0.25 0)
           (cons 40 0.5)
           (cons 1 "3")
           (cons 50 0)
           (cons 41 1)
           (cons 51 0)
           (cons 7 "Standard")
           (cons 71 0)
           (cons 72 4)
           (list 11 1.5 0 0)
           (cons 100 "AcDbText")
           (cons 73 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "0.500")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "0.500")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "5.150")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -1.1 0)
           (cons 40 0.2)
           (cons 1 "3.720")
           (cons 50 0)
           (cons 41 1)
           (cons 51 0)
           (cons 7 "Standard")
           (cons 71 0)
           (cons 72 0)
           (list 11 0 0 0)
           (cons 100 "AcDbAttributeDefinition")
           (cons 3 "Load Base Point (LB)")
           (cons 2 "LB")
           (cons 70 9)
           (cons 73 0)
           (cons 74 0)
          )
         )
         (entmake (list (cons 0 "ENDBLK")))
        )
       )
       ((= (strcase BLKNAME) (strcase "BC_MOTI-LG3-Trailer1"))
        (progn
         (entmake)
         (entmake
          (list
           (cons 0 "BLOCK")
           (cons 2 "BC_MOTI-LG3-Trailer1")
           (cons 70 2)
           (cons 4 "")
           (list 10 0 0 0)
          )
         )
         (entmake
          (list
           (cons 0 "POINT")
           (cons 100 "AcDbEntity")
           (cons 67 0)
           (cons 8 "0")
           (cons 100 "AcDbPoint")
           (list 10 4.49 -1.3 0)
           (cons 50 0)
          )
         )
         (entmake
          (list
           (cons 0 "POINT")
           (cons 100 "AcDbEntity")
           (cons 67 0)
           (cons 8 "0")
           (cons 100 "AcDbPoint")
           (list 10 4.49 1.3 0)
           (cons 50 0)
          )
         )
         (entmake
          (list
           (cons 0 "POINT")
           (cons 100 "AcDbEntity")
           (cons 67 0)
           (cons 8 "0")
           (cons 100 "AcDbPoint")
           (list 10 0.5 0 0)
           (cons 50 0)
          )
         )
         (entmake
          (list
           (cons 0 "POINT")
           (cons 100 "AcDbEntity")
           (cons 67 0)
           (cons 8 "0")
           (cons 100 "AcDbPoint")
           (list 10 4.49 0 0)
           (cons 50 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 4.49 0 0)
           (cons 40 0.17333333)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.931 1.073452)
           (cons 40 0)
           (cons 41 0)
           (cons 42 0)
           (cons 91 0)
           (list 10 3.931 1.247548)
           (cons 40 0)
           (cons 41 0)
           (cons 42 0)
           (cons 91 0)
           (list 10 4.08752 1.3)
           (cons 40 0)
           (cons 41 0)
           (cons 42 0)
           (cons 91 0)
           (list 10 4.89248 1.3)
           (cons 40 0)
           (cons 41 0)
           (cons 42 0)
           (cons 91 0)
           (list 10 5.049 1.247548)
           (cons 40 0)
           (cons 41 0)
           (cons 42 0)
           (cons 91 0)
           (list 10 5.049 1.073452)
           (cons 40 0)
           (cons 41 0)
           (cons 42 0)
           (cons 91 0)
           (list 10 4.89248 1.021)
           (cons 40 0)
           (cons 41 0)
           (cons 42 0)
           (cons 91 0)
           (list 10 4.08752 1.021)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.931 0.570452)
           (cons 40 0)
           (cons 41 0)
           (cons 42 0)
           (cons 91 0)
           (list 10 3.931 0.744548)
           (cons 40 0)
           (cons 41 0)
           (cons 42 0)
           (cons 91 0)
           (list 10 4.08752 0.797)
           (cons 40 0)
           (cons 41 0)
           (cons 42 0)
           (cons 91 0)
           (list 10 4.89248 0.797)
           (cons 40 0)
           (cons 41 0)
           (cons 42 0)
           (cons 91 0)
           (list 10 5.049 0.744548)
           (cons 40 0)
           (cons 41 0)
           (cons 42 0)
           (cons 91 0)
           (list 10 5.049 0.570452)
           (cons 40 0)
           (cons 41 0)
           (cons 42 0)
           (cons 91 0)
           (list 10 4.89248 0.518)
           (cons 40 0)
           (cons 41 0)
           (cons 42 0)
           (cons 91 0)
           (list 10 4.08752 0.518)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.931 -0.744548)
           (cons 40 0)
           (cons 41 0)
           (cons 42 0)
           (cons 91 0)
           (list 10 3.931 -0.570452)
           (cons 40 0)
           (cons 41 0)
           (cons 42 0)
           (cons 91 0)
           (list 10 4.08752 -0.518)
           (cons 40 0)
           (cons 41 0)
           (cons 42 0)
           (cons 91 0)
           (list 10 4.89248 -0.518)
           (cons 40 0)
           (cons 41 0)
           (cons 42 0)
           (cons 91 0)
           (list 10 5.049 -0.570452)
           (cons 40 0)
           (cons 41 0)
           (cons 42 0)
           (cons 91 0)
           (list 10 5.049 -0.744548)
           (cons 40 0)
           (cons 41 0)
           (cons 42 0)
           (cons 91 0)
           (list 10 4.89248 -0.797)
           (cons 40 0)
           (cons 41 0)
           (cons 42 0)
           (cons 91 0)
           (list 10 4.08752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.931 -1.247548)
           (cons 40 0)
           (cons 41 0)
           (cons 42 0)
           (cons 91 0)
           (list 10 3.931 -1.073452)
           (cons 40 0)
           (cons 41 0)
           (cons 42 0)
           (cons 91 0)
           (list 10 4.08752 -1.021)
           (cons 40 0)
           (cons 41 0)
           (cons 42 0)
           (cons 91 0)
           (list 10 4.89248 -1.021)
           (cons 40 0)
           (cons 41 0)
           (cons 42 0)
           (cons 91 0)
           (list 10 5.049 -1.073452)
           (cons 40 0)
           (cons 41 0)
           (cons 42 0)
           (cons 91 0)
           (list 10 5.049 -1.247548)
           (cons 40 0)
           (cons 41 0)
           (cons 42 0)
           (cons 91 0)
           (list 10 4.89248 -1.3)
           (cons 40 0)
           (cons 41 0)
           (cons 42 0)
           (cons 91 0)
           (list 10 4.08752 -1.3)
           (cons 40 0)
           (cons 41 0)
           (cons 42 0)
           (cons 91 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0.5 0 0)
           (cons 40 0.104)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.99 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.99 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "POLYLINE")
           (cons 100 "AcDbEntity")
           (cons 67 0)
           (cons 8 "Defpoints")
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "Defpoints")
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 3.931 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 3.931 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 5.049 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 5.049 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 4.99 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 4.99 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 5.049 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 5.049 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 3.931 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 3.931 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 0 0.5 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "Defpoints")
          )
         )
         (entmake
          (list
           (cons 0 "TEXT")
           (cons 100 "AcDbEntity")
           (cons 67 0)
           (cons 8 "0")
           (cons 100 "AcDbText")
           (list 10 1.33333333 -0.25 0)
           (cons 40 0.5)
           (cons 1 "2")
           (cons 50 0)
           (cons 41 1)
           (cons 51 0)
           (cons 7 "Standard")
           (cons 71 0)
           (cons 72 4)
           (list 11 1.5 0 0)
           (cons 100 "AcDbText")
           (cons 73 0)
          )
         )
         (entmake
          (list
           (cons 0 "ATTDEF")
           (cons 100 "AcDbEntity")
           (cons 67 0)
           (cons 8 "0")
           (cons 100 "AcDbText")
           (list 10 -0.3 0.56666667 0)
           (cons 40 0.2)
           (cons 1 "0.500")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 0.23333333 0)
           (cons 40 0.2)
           (cons 1 "0.500")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.1 0)
           (cons 40 0.2)
           (cons 1 "4.490")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.43333333 0)
           (cons 40 0.2)
           (cons 1 "4.490")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "BC_MOTI-LG3-Truck"))
        (progn
         (entmake)
         (entmake
          (list
           (cons 0 "BLOCK")
           (cons 2 "BC_MOTI-LG3-Truck")
           (cons 70 2)
           (cons 4 "")
           (list 10 0 0 0)
          )
         )
         (entmake
          (list
           (cons 0 "POINT")
           (cons 100 "AcDbEntity")
           (cons 67 0)
           (cons 8 "0")
           (cons 62 1)
           (cons 100 "AcDbPoint")
           (list 10 7.52 0 0)
           (cons 50 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 7.52 0 0)
           (cons 40 0.1524)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 7.9 -1.3 0)
           (cons 50 0)
          )
         )
         (entmake
          (list
           (cons 0 "POINT")
           (cons 100 "AcDbEntity")
           (cons 67 0)
           (cons 8 "0")
           (cons 100 "AcDbPoint")
           (list 10 7.9 1.3 0)
           (cons 50 0)
          )
         )
         (entmake
          (list
           (cons 0 "POINT")
           (cons 100 "AcDbEntity")
           (cons 67 0)
           (cons 8 "0")
           (cons 100 "AcDbPoint")
           (list 10 1.1 -1.3 0)
           (cons 50 0)
          )
         )
         (entmake
          (list
           (cons 0 "POINT")
           (cons 100 "AcDbEntity")
           (cons 67 0)
           (cons 8 "0")
           (cons 100 "AcDbPoint")
           (list 10 1.1 1.3 0)
           (cons 50 0)
          )
         )
         (entmake
          (list
           (cons 0 "POINT")
           (cons 100 "AcDbEntity")
           (cons 67 0)
           (cons 8 "0")
           (cons 100 "AcDbPoint")
           (list 10 1.1 0 0)
           (cons 50 0)
          )
         )
         (entmake
          (list
           (cons 0 "INSERT")
           (cons 100 "AcDbEntity")
           (cons 67 0)
           (cons 8 "0")
           (cons 100 "AcDbBlockReference")
           (cons 2 "WheelLeftM1")
           (list 10 1.1 -1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM1")
           (list 10 1.1 1.0206 0)
           (cons 41 1)
           (cons 42 1)
           (cons 43 1)
           (cons 50 0)
           (cons 70 0)
           (cons 71 0)
           (cons 44 0)
           (cons 45 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.341 1.073452)
           (cons 40 0)
           (cons 41 0)
           (cons 42 0)
           (cons 91 0)
           (list 10 7.341 1.247548)
           (cons 40 0)
           (cons 41 0)
           (cons 42 0)
           (cons 91 0)
           (list 10 7.49752 1.3)
           (cons 40 0)
           (cons 41 0)
           (cons 42 0)
           (cons 91 0)
           (list 10 8.30248 1.3)
           (cons 40 0)
           (cons 41 0)
           (cons 42 0)
           (cons 91 0)
           (list 10 8.459 1.247548)
           (cons 40 0)
           (cons 41 0)
           (cons 42 0)
           (cons 91 0)
           (list 10 8.459 1.073452)
           (cons 40 0)
           (cons 41 0)
           (cons 42 0)
           (cons 91 0)
           (list 10 8.30248 1.021)
           (cons 40 0)
           (cons 41 0)
           (cons 42 0)
           (cons 91 0)
           (list 10 7.49752 1.021)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.341 0.570452)
           (cons 40 0)
           (cons 41 0)
           (cons 42 0)
           (cons 91 0)
           (list 10 7.341 0.744548)
           (cons 40 0)
           (cons 41 0)
           (cons 42 0)
           (cons 91 0)
           (list 10 7.49752 0.797)
           (cons 40 0)
           (cons 41 0)
           (cons 42 0)
           (cons 91 0)
           (list 10 8.30248 0.797)
           (cons 40 0)
           (cons 41 0)
           (cons 42 0)
           (cons 91 0)
           (list 10 8.459 0.744548)
           (cons 40 0)
           (cons 41 0)
           (cons 42 0)
           (cons 91 0)
           (list 10 8.459 0.570452)
           (cons 40 0)
           (cons 41 0)
           (cons 42 0)
           (cons 91 0)
           (list 10 8.30248 0.518)
           (cons 40 0)
           (cons 41 0)
           (cons 42 0)
           (cons 91 0)
           (list 10 7.49752 0.518)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.341 -0.744548)
           (cons 40 0)
           (cons 41 0)
           (cons 42 0)
           (cons 91 0)
           (list 10 7.341 -0.570452)
           (cons 40 0)
           (cons 41 0)
           (cons 42 0)
           (cons 91 0)
           (list 10 7.49752 -0.518)
           (cons 40 0)
           (cons 41 0)
           (cons 42 0)
           (cons 91 0)
           (list 10 8.30248 -0.518)
           (cons 40 0)
           (cons 41 0)
           (cons 42 0)
           (cons 91 0)
           (list 10 8.459 -0.570452)
           (cons 40 0)
           (cons 41 0)
           (cons 42 0)
           (cons 91 0)
           (list 10 8.459 -0.744548)
           (cons 40 0)
           (cons 41 0)
           (cons 42 0)
           (cons 91 0)
           (list 10 8.30248 -0.797)
           (cons 40 0)
           (cons 41 0)
           (cons 42 0)
           (cons 91 0)
           (list 10 7.49752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.341 -1.247548)
           (cons 40 0)
           (cons 41 0)
           (cons 42 0)
           (cons 91 0)
           (list 10 7.341 -1.073452)
           (cons 40 0)
           (cons 41 0)
           (cons 42 0)
           (cons 91 0)
           (list 10 7.49752 -1.021)
           (cons 40 0)
           (cons 41 0)
           (cons 42 0)
           (cons 91 0)
           (list 10 8.30248 -1.021)
           (cons 40 0)
           (cons 41 0)
           (cons 42 0)
           (cons 91 0)
           (list 10 8.459 -1.073452)
           (cons 40 0)
           (cons 41 0)
           (cons 42 0)
           (cons 91 0)
           (list 10 8.459 -1.247548)
           (cons 40 0)
           (cons 41 0)
           (cons 42 0)
           (cons 91 0)
           (list 10 8.30248 -1.3)
           (cons 40 0)
           (cons 41 0)
           (cons 42 0)
           (cons 91 0)
           (list 10 7.49752 -1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.38016 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.38016 -0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 11.16 -0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 11.16 0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.38016 0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.38016 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "Defpoints")
           (cons 100 "AcDbPolyline")
           (cons 90 8)
           (cons 70 1)
           (cons 43 0)
           (cons 38 0)
           (cons 39 0)
           (list 10 0 -1.3)
           (cons 40 0)
           (cons 41 0)
           (cons 42 0)
           (cons 91 0)
           (list 10 8.459 -1.3)
           (cons 40 0)
           (cons 41 0)
           (cons 42 0)
           (cons 91 0)
           (list 10 8.459 -0.5188)
           (cons 40 0)
           (cons 41 0)
           (cons 42 0)
           (cons 91 0)
           (list 10 11.16 -0.5188)
           (cons 40 0)
           (cons 41 0)
           (cons 42 0)
           (cons 91 0)
           (list 10 11.16 0.5188)
           (cons 40 0)
           (cons 41 0)
           (cons 42 0)
           (cons 91 0)
           (list 10 8.459 0.5188)
           (cons 40 0)
           (cons 41 0)
           (cons 42 0)
           (cons 91 0)
           (list 10 8.459 1.3)
           (cons 40 0)
           (cons 41 0)
           (cons 42 0)
           (cons 91 0)
           (list 10 0 1.3)
           (cons 40 0)
           (cons 41 0)
           (cons 42 0)
           (cons 91 0)
          )
         )
         (entmake
          (list
           (cons 0 "TEXT")
           (cons 100 "AcDbEntity")
           (cons 67 0)
           (cons 8 "0")
           (cons 100 "AcDbText")
           (list 10 2.04047619 -0.25 0)
           (cons 40 0.5)
           (cons 1 "1")
           (cons 50 0)
           (cons 41 1)
           (cons 51 0)
           (cons 7 "Standard")
           (cons 71 0)
           (cons 72 4)
           (list 11 2.1 0 0)
           (cons 100 "AcDbText")
           (cons 73 0)
          )
         )
         (entmake
          (list
           (cons 0 "POINT")
           (cons 100 "AcDbEntity")
           (cons 67 0)
           (cons 8 "0")
           (cons 100 "AcDbPoint")
           (list 10 10.66 0 0)
           (cons 50 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 10.66 0 0)
           (cons 40 0.17333333)
          )
         )
         (entmake
          (list
           (cons 0 "ATTDEF")
           (cons 100 "AcDbEntity")
           (cons 67 0)
           (cons 8 "0")
           (cons 100 "AcDbText")
           (list 10 0.4 0.56666667 0)
           (cons 40 0.2)
           (cons 1 "1.100")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.4 0.23333333 0)
           (cons 40 0.2)
           (cons 1 "1.100")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.4 -0.1 0)
           (cons 40 0.2)
           (cons 1 "7.900")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.4 -0.43333333 0)
           (cons 40 0.2)
           (cons 1 "10.660")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.4 -0.76666667 0)
           (cons 40 0.2)
           (cons 1 "32.983")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.4 -1.1 0)
           (cons 40 0.2)
           (cons 1 "7.52")
           (cons 50 0)
           (cons 41 1)
           (cons 51 0)
           (cons 7 "Standard")
           (cons 71 0)
           (cons 72 0)
           (list 11 0 0 0)
           (cons 100 "AcDbAttributeDefinition")
           (cons 3 "Load Angle Point (LA)")
           (cons 2 "LA")
           (cons 70 9)
           (cons 73 0)
           (cons 74 0)
          )
         )
         (entmake (list (cons 0 "ENDBLK")))
        )
       )
       ((= (strcase BLKNAME) (strcase "AASHTO-2011-WB-67-TRAILER"))
        (progn
         (entmake)
         (entmake
          (list
           (cons 0 "BLOCK")
           (cons 2 "AASHTO-2011-WB-67-TRAILER")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 53 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 53 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 3 0 0)
           (cons 40 0.34)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 44.84868766 -2.42766667)
           (cons 40 0)
           (cons 41 0)
           (cons 42 0)
           (cons 91 0)
           (list 10 44.84868766 -1.85566667)
           (cons 40 0)
           (cons 41 0)
           (cons 42 0)
           (cons 91 0)
           (list 10 45.31068766 -1.68333333)
           (cons 40 0)
           (cons 41 0)
           (cons 42 0)
           (cons 91 0)
           (list 10 47.68668766 -1.68333333)
           (cons 40 0)
           (cons 41 0)
           (cons 42 0)
           (cons 91 0)
           (list 10 48.14868766 -1.85566667)
           (cons 40 0)
           (cons 41 0)
           (cons 42 0)
           (cons 91 0)
           (list 10 48.14868766 -2.42766667)
           (cons 40 0)
           (cons 41 0)
           (cons 42 0)
           (cons 91 0)
           (list 10 47.68668766 -2.6)
           (cons 40 0)
           (cons 41 0)
           (cons 42 0)
           (cons 91 0)
           (list 10 45.31068766 -2.6)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 44.84868766 -4.07766667)
           (cons 40 0)
           (cons 41 0)
           (cons 42 0)
           (cons 91 0)
           (list 10 44.84868766 -3.50566667)
           (cons 40 0)
           (cons 41 0)
           (cons 42 0)
           (cons 91 0)
           (list 10 45.31068766 -3.33333333)
           (cons 40 0)
           (cons 41 0)
           (cons 42 0)
           (cons 91 0)
           (list 10 47.68668766 -3.33333333)
           (cons 40 0)
           (cons 41 0)
           (cons 42 0)
           (cons 91 0)
           (list 10 48.14868766 -3.50566667)
           (cons 40 0)
           (cons 41 0)
           (cons 42 0)
           (cons 91 0)
           (list 10 48.14868766 -4.07766667)
           (cons 40 0)
           (cons 41 0)
           (cons 42 0)
           (cons 91 0)
           (list 10 47.68668766 -4.25)
           (cons 40 0)
           (cons 41 0)
           (cons 42 0)
           (cons 91 0)
           (list 10 45.31068766 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 44.84868766 1.85566667)
           (cons 40 0)
           (cons 41 0)
           (cons 42 0)
           (cons 91 0)
           (list 10 44.84868766 2.42766667)
           (cons 40 0)
           (cons 41 0)
           (cons 42 0)
           (cons 91 0)
           (list 10 45.31068766 2.6)
           (cons 40 0)
           (cons 41 0)
           (cons 42 0)
           (cons 91 0)
           (list 10 47.68668766 2.6)
           (cons 40 0)
           (cons 41 0)
           (cons 42 0)
           (cons 91 0)
           (list 10 48.14868766 2.42766667)
           (cons 40 0)
           (cons 41 0)
           (cons 42 0)
           (cons 91 0)
           (list 10 48.14868766 1.85566667)
           (cons 40 0)
           (cons 41 0)
           (cons 42 0)
           (cons 91 0)
           (list 10 47.68668766 1.68333333)
           (cons 40 0)
           (cons 41 0)
           (cons 42 0)
           (cons 91 0)
           (list 10 45.31068766 1.68333333)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 44.84868766 3.50566667)
           (cons 40 0)
           (cons 41 0)
           (cons 42 0)
           (cons 91 0)
           (list 10 44.84868766 4.07766667)
           (cons 40 0)
           (cons 41 0)
           (cons 42 0)
           (cons 91 0)
           (list 10 45.31068766 4.25)
           (cons 40 0)
           (cons 41 0)
           (cons 42 0)
           (cons 91 0)
           (list 10 47.68668766 4.25)
           (cons 40 0)
           (cons 41 0)
           (cons 42 0)
           (cons 91 0)
           (list 10 48.14868766 4.07766667)
           (cons 40 0)
           (cons 41 0)
           (cons 42 0)
           (cons 91 0)
           (list 10 48.14868766 3.50566667)
           (cons 40 0)
           (cons 41 0)
           (cons 42 0)
           (cons 91 0)
           (list 10 47.68668766 3.33333333)
           (cons 40 0)
           (cons 41 0)
           (cons 42 0)
           (cons 91 0)
           (list 10 45.31068766 3.33333333)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 48.85131234 -2.42766667)
           (cons 40 0)
           (cons 41 0)
           (cons 42 0)
           (cons 91 0)
           (list 10 48.85131234 -1.85566667)
           (cons 40 0)
           (cons 41 0)
           (cons 42 0)
           (cons 91 0)
           (list 10 49.31331234 -1.68333333)
           (cons 40 0)
           (cons 41 0)
           (cons 42 0)
           (cons 91 0)
           (list 10 51.68931234 -1.68333333)
           (cons 40 0)
           (cons 41 0)
           (cons 42 0)
           (cons 91 0)
           (list 10 52.15131234 -1.85566667)
           (cons 40 0)
           (cons 41 0)
           (cons 42 0)
           (cons 91 0)
           (list 10 52.15131234 -2.42766667)
           (cons 40 0)
           (cons 41 0)
           (cons 42 0)
           (cons 91 0)
           (list 10 51.68931234 -2.6)
           (cons 40 0)
           (cons 41 0)
           (cons 42 0)
           (cons 91 0)
           (list 10 49.31331234 -2.6)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 48.85131234 -4.07766667)
           (cons 40 0)
           (cons 41 0)
           (cons 42 0)
           (cons 91 0)
           (list 10 48.85131234 -3.50566667)
           (cons 40 0)
           (cons 41 0)
           (cons 42 0)
           (cons 91 0)
           (list 10 49.31331234 -3.33333333)
           (cons 40 0)
           (cons 41 0)
           (cons 42 0)
           (cons 91 0)
           (list 10 51.68931234 -3.33333333)
           (cons 40 0)
           (cons 41 0)
           (cons 42 0)
           (cons 91 0)
           (list 10 52.15131234 -3.50566667)
           (cons 40 0)
           (cons 41 0)
           (cons 42 0)
           (cons 91 0)
           (list 10 52.15131234 -4.07766667)
           (cons 40 0)
           (cons 41 0)
           (cons 42 0)
           (cons 91 0)
           (list 10 51.68931234 -4.25)
           (cons 40 0)
           (cons 41 0)
           (cons 42 0)
           (cons 91 0)
           (list 10 49.31331234 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 48.85131234 1.85566667)
           (cons 40 0)
           (cons 41 0)
           (cons 42 0)
           (cons 91 0)
           (list 10 48.85131234 2.42766667)
           (cons 40 0)
           (cons 41 0)
           (cons 42 0)
           (cons 91 0)
           (list 10 49.31331234 2.6)
           (cons 40 0)
           (cons 41 0)
           (cons 42 0)
           (cons 91 0)
           (list 10 51.68931234 2.6)
           (cons 40 0)
           (cons 41 0)
           (cons 42 0)
           (cons 91 0)
           (list 10 52.15131234 2.42766667)
           (cons 40 0)
           (cons 41 0)
           (cons 42 0)
           (cons 91 0)
           (list 10 52.15131234 1.85566667)
           (cons 40 0)
           (cons 41 0)
           (cons 42 0)
           (cons 91 0)
           (list 10 51.68931234 1.68333333)
           (cons 40 0)
           (cons 41 0)
           (cons 42 0)
           (cons 91 0)
           (list 10 49.31331234 1.68333333)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 48.85131234 3.50566667)
           (cons 40 0)
           (cons 41 0)
           (cons 42 0)
           (cons 91 0)
           (list 10 48.85131234 4.07766667)
           (cons 40 0)
           (cons 41 0)
           (cons 42 0)
           (cons 91 0)
           (list 10 49.31331234 4.25)
           (cons 40 0)
           (cons 41 0)
           (cons 42 0)
           (cons 91 0)
           (list 10 51.68931234 4.25)
           (cons 40 0)
           (cons 41 0)
           (cons 42 0)
           (cons 91 0)
           (list 10 52.15131234 4.07766667)
           (cons 40 0)
           (cons 41 0)
           (cons 42 0)
           (cons 91 0)
           (list 10 52.15131234 3.50566667)
           (cons 40 0)
           (cons 41 0)
           (cons 42 0)
           (cons 91 0)
           (list 10 51.68931234 3.33333333)
           (cons 40 0)
           (cons 41 0)
           (cons 42 0)
           (cons 91 0)
           (list 10 49.31331234 3.33333333)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4.25 0)
           (cons 50 0)
          )
         )
         (entmake
          (list
           (cons 0 "POINT")
           (cons 100 "AcDbEntity")
           (cons 67 0)
           (cons 8 "0")
           (cons 100 "AcDbPoint")
           (list 10 0 4.25 0)
           (cons 50 0)
          )
         )
         (entmake
          (list
           (cons 0 "POINT")
           (cons 100 "AcDbEntity")
           (cons 67 0)
           (cons 8 "0")
           (cons 100 "AcDbPoint")
           (list 10 53 -4.25 0)
           (cons 50 0)
          )
         )
         (entmake
          (list
           (cons 0 "POINT")
           (cons 100 "AcDbEntity")
           (cons 67 0)
           (cons 8 "0")
           (cons 100 "AcDbPoint")
           (list 10 53 4.25 0)
           (cons 50 0)
          )
         )
         (entmake
          (list
           (cons 0 "POINT")
           (cons 100 "AcDbEntity")
           (cons 67 0)
           (cons 8 "0")
           (cons 100 "AcDbPoint")
           (list 10 48.5 -4.25 0)
           (cons 50 0)
          )
         )
         (entmake
          (list
           (cons 0 "POINT")
           (cons 100 "AcDbEntity")
           (cons 67 0)
           (cons 8 "0")
           (cons 100 "AcDbPoint")
           (list 10 48.5 4.25 0)
           (cons 50 0)
          )
         )
         (entmake
          (list
           (cons 0 "POINT")
           (cons 100 "AcDbEntity")
           (cons 67 0)
           (cons 8 "0")
           (cons 100 "AcDbPoint")
           (list 10 3 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4.25)
           (cons 40 0)
           (cons 41 0)
           (cons 42 0)
           (cons 91 0)
           (list 10 53 -4.25)
           (cons 40 0)
           (cons 41 0)
           (cons 42 0)
           (cons 91 0)
           (list 10 53 4.25)
           (cons 40 0)
           (cons 41 0)
           (cons 42 0)
           (cons 91 0)
           (list 10 0 4.25)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.70341207 1.85914261 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 0.76552931 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -0.32808399 0)
           (cons 40 0.65616798)
           (cons 1 "48.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-67-TRUCK"))
        (progn
         (entmake)
         (entmake
          (list
           (cons 0 "BLOCK")
           (cons 2 "AASHTO-2011-WB-67-TRUCK")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15 -1.43333333 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 25.6 -1.43333333 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 25.6 1.43333333 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15 1.43333333 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 23.5 0 0)
           (cons 40 1.14285714)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 24.30812204 -0.80812204 0)
           (list 11 24.30812204 0.80812204 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 19.56666667 -2.17766667)
           (cons 40 0)
           (cons 41 0)
           (cons 42 0)
           (cons 91 0)
           (list 10 19.56666667 -1.60566667)
           (cons 40 0)
           (cons 41 0)
           (cons 42 0)
           (cons 91 0)
           (list 10 20.08 -1.43333333)
           (cons 40 0)
           (cons 41 0)
           (cons 42 0)
           (cons 91 0)
           (list 10 22.72 -1.43333333)
           (cons 40 0)
           (cons 41 0)
           (cons 42 0)
           (cons 91 0)
           (list 10 23.23333333 -1.60566667)
           (cons 40 0)
           (cons 41 0)
           (cons 42 0)
           (cons 91 0)
           (list 10 23.23333333 -2.17766667)
           (cons 40 0)
           (cons 41 0)
           (cons 42 0)
           (cons 91 0)
           (list 10 22.72 -2.35)
           (cons 40 0)
           (cons 41 0)
           (cons 42 0)
           (cons 91 0)
           (list 10 20.08 -2.35)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 19.56666667 -3.82766667)
           (cons 40 0)
           (cons 41 0)
           (cons 42 0)
           (cons 91 0)
           (list 10 19.56666667 -3.25566667)
           (cons 40 0)
           (cons 41 0)
           (cons 42 0)
           (cons 91 0)
           (list 10 20.08 -3.08333333)
           (cons 40 0)
           (cons 41 0)
           (cons 42 0)
           (cons 91 0)
           (list 10 22.72 -3.08333333)
           (cons 40 0)
           (cons 41 0)
           (cons 42 0)
           (cons 91 0)
           (list 10 23.23333333 -3.25566667)
           (cons 40 0)
           (cons 41 0)
           (cons 42 0)
           (cons 91 0)
           (list 10 23.23333333 -3.82766667)
           (cons 40 0)
           (cons 41 0)
           (cons 42 0)
           (cons 91 0)
           (list 10 22.72 -4)
           (cons 40 0)
           (cons 41 0)
           (cons 42 0)
           (cons 91 0)
           (list 10 20.08 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 19.56666667 1.60566667)
           (cons 40 0)
           (cons 41 0)
           (cons 42 0)
           (cons 91 0)
           (list 10 19.56666667 2.17766667)
           (cons 40 0)
           (cons 41 0)
           (cons 42 0)
           (cons 91 0)
           (list 10 20.08 2.35)
           (cons 40 0)
           (cons 41 0)
           (cons 42 0)
           (cons 91 0)
           (list 10 22.72 2.35)
           (cons 40 0)
           (cons 41 0)
           (cons 42 0)
           (cons 91 0)
           (list 10 23.23333333 2.17766667)
           (cons 40 0)
           (cons 41 0)
           (cons 42 0)
           (cons 91 0)
           (list 10 23.23333333 1.60566667)
           (cons 40 0)
           (cons 41 0)
           (cons 42 0)
           (cons 91 0)
           (list 10 22.72 1.43333333)
           (cons 40 0)
           (cons 41 0)
           (cons 42 0)
           (cons 91 0)
           (list 10 20.08 1.43333333)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 19.56666667 3.25566667)
           (cons 40 0)
           (cons 41 0)
           (cons 42 0)
           (cons 91 0)
           (list 10 19.56666667 3.82766667)
           (cons 40 0)
           (cons 41 0)
           (cons 42 0)
           (cons 91 0)
           (list 10 20.08 4)
           (cons 40 0)
           (cons 41 0)
           (cons 42 0)
           (cons 91 0)
           (list 10 22.72 4)
           (cons 40 0)
           (cons 41 0)
           (cons 42 0)
           (cons 91 0)
           (list 10 23.23333333 3.82766667)
           (cons 40 0)
           (cons 41 0)
           (cons 42 0)
           (cons 91 0)
           (list 10 23.23333333 3.25566667)
           (cons 40 0)
           (cons 41 0)
           (cons 42 0)
           (cons 91 0)
           (list 10 22.72 3.08333333)
           (cons 40 0)
           (cons 41 0)
           (cons 42 0)
           (cons 91 0)
           (list 10 20.08 3.08333333)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.76666667 -2.17766667)
           (cons 40 0)
           (cons 41 0)
           (cons 42 0)
           (cons 91 0)
           (list 10 23.76666667 -1.60566667)
           (cons 40 0)
           (cons 41 0)
           (cons 42 0)
           (cons 91 0)
           (list 10 24.28 -1.43333333)
           (cons 40 0)
           (cons 41 0)
           (cons 42 0)
           (cons 91 0)
           (list 10 26.92 -1.43333333)
           (cons 40 0)
           (cons 41 0)
           (cons 42 0)
           (cons 91 0)
           (list 10 27.43333333 -1.60566667)
           (cons 40 0)
           (cons 41 0)
           (cons 42 0)
           (cons 91 0)
           (list 10 27.43333333 -2.17766667)
           (cons 40 0)
           (cons 41 0)
           (cons 42 0)
           (cons 91 0)
           (list 10 26.92 -2.35)
           (cons 40 0)
           (cons 41 0)
           (cons 42 0)
           (cons 91 0)
           (list 10 24.28 -2.35)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.76666667 -3.82766667)
           (cons 40 0)
           (cons 41 0)
           (cons 42 0)
           (cons 91 0)
           (list 10 23.76666667 -3.25566667)
           (cons 40 0)
           (cons 41 0)
           (cons 42 0)
           (cons 91 0)
           (list 10 24.28 -3.08333333)
           (cons 40 0)
           (cons 41 0)
           (cons 42 0)
           (cons 91 0)
           (list 10 26.92 -3.08333333)
           (cons 40 0)
           (cons 41 0)
           (cons 42 0)
           (cons 91 0)
           (list 10 27.43333333 -3.25566667)
           (cons 40 0)
           (cons 41 0)
           (cons 42 0)
           (cons 91 0)
           (list 10 27.43333333 -3.82766667)
           (cons 40 0)
           (cons 41 0)
           (cons 42 0)
           (cons 91 0)
           (list 10 26.92 -4)
           (cons 40 0)
           (cons 41 0)
           (cons 42 0)
           (cons 91 0)
           (list 10 24.28 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.76666667 1.60566667)
           (cons 40 0)
           (cons 41 0)
           (cons 42 0)
           (cons 91 0)
           (list 10 23.76666667 2.17766667)
           (cons 40 0)
           (cons 41 0)
           (cons 42 0)
           (cons 91 0)
           (list 10 24.28 2.35)
           (cons 40 0)
           (cons 41 0)
           (cons 42 0)
           (cons 91 0)
           (list 10 26.92 2.35)
           (cons 40 0)
           (cons 41 0)
           (cons 42 0)
           (cons 91 0)
           (list 10 27.43333333 2.17766667)
           (cons 40 0)
           (cons 41 0)
           (cons 42 0)
           (cons 91 0)
           (list 10 27.43333333 1.60566667)
           (cons 40 0)
           (cons 41 0)
           (cons 42 0)
           (cons 91 0)
           (list 10 26.92 1.43333333)
           (cons 40 0)
           (cons 41 0)
           (cons 42 0)
           (cons 91 0)
           (list 10 24.28 1.43333333)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.76666667 3.25566667)
           (cons 40 0)
           (cons 41 0)
           (cons 42 0)
           (cons 91 0)
           (list 10 23.76666667 3.82766667)
           (cons 40 0)
           (cons 41 0)
           (cons 42 0)
           (cons 91 0)
           (list 10 24.28 4)
           (cons 40 0)
           (cons 41 0)
           (cons 42 0)
           (cons 91 0)
           (list 10 26.92 4)
           (cons 40 0)
           (cons 41 0)
           (cons 42 0)
           (cons 91 0)
           (list 10 27.43333333 3.82766667)
           (cons 40 0)
           (cons 41 0)
           (cons 42 0)
           (cons 91 0)
           (list 10 27.43333333 3.25566667)
           (cons 40 0)
           (cons 41 0)
           (cons 42 0)
           (cons 91 0)
           (list 10 26.92 3.08333333)
           (cons 40 0)
           (cons 41 0)
           (cons 42 0)
           (cons 91 0)
           (list 10 24.28 3.08333333)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4 0)
           (cons 50 0)
          )
         )
         (entmake
          (list
           (cons 0 "POINT")
           (cons 100 "AcDbEntity")
           (cons 67 0)
           (cons 8 "0")
           (cons 100 "AcDbPoint")
           (list 10 0 4 0)
           (cons 50 0)
          )
         )
         (entmake
          (list
           (cons 0 "POINT")
           (cons 100 "AcDbEntity")
           (cons 67 0)
           (cons 8 "0")
           (cons 100 "AcDbPoint")
           (list 10 4 4 0)
           (cons 50 0)
          )
         )
         (entmake
          (list
           (cons 0 "POINT")
           (cons 100 "AcDbEntity")
           (cons 67 0)
           (cons 8 "0")
           (cons 100 "AcDbPoint")
           (list 10 4 0 0)
           (cons 50 0)
          )
         )
         (entmake
          (list
           (cons 0 "POINT")
           (cons 100 "AcDbEntity")
           (cons 67 0)
           (cons 8 "0")
           (cons 100 "AcDbPoint")
           (list 10 23.5 4 0)
           (cons 50 0)
          )
         )
         (entmake
          (list
           (cons 0 "POINT")
           (cons 100 "AcDbEntity")
           (cons 67 0)
           (cons 8 "0")
           (cons 100 "AcDbPoint")
           (list 10 23.5 -4 0)
           (cons 50 0)
          )
         )
         (entmake
          (list
           (cons 0 "POINT")
           (cons 100 "AcDbEntity")
           (cons 67 0)
           (cons 8 "0")
           (cons 100 "AcDbPoint")
           (list 10 23.5 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4)
           (cons 40 0)
           (cons 41 0)
           (cons 42 0)
           (cons 91 0)
           (list 10 25.6 -4)
           (cons 40 0)
           (cons 41 0)
           (cons 42 0)
           (cons 91 0)
           (list 10 25.6 4)
           (cons 40 0)
           (cons 41 0)
           (cons 42 0)
           (cons 91 0)
           (list 10 0 4)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelLeft1")
           (list 10 4 -3.08333333 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRight1")
           (list 10 4 3.08333333 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 1.70341207 1.85914261 0)
           (cons 40 0.65616798)
           (cons 1 "4.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 0.76552931 0)
           (cons 40 0.65616798)
           (cons 1 "4.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -0.32808399 0)
           (cons 40 0.65616798)
           (cons 1 "23.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -1.42169729 0)
           (cons 40 0.65616798)
           (cons 1 "23.500")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -2.51531059 0)
           (cons 40 0.65616798)
           (cons 1 "25.8")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-109D-TRAILER"))
        (progn
         (entmake)
         (entmake
          (list
           (cons 0 "BLOCK")
           (cons 2 "AASHTO-2011-WB-109D-TRAILER")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4.25)
           (cons 40 0)
           (cons 41 0)
           (cons 42 0)
           (cons 91 0)
           (list 10 48 -4.25)
           (cons 40 0)
           (cons 41 0)
           (cons 42 0)
           (cons 91 0)
           (list 10 48 4.25)
           (cons 40 0)
           (cons 41 0)
           (cons 42 0)
           (cons 91 0)
           (list 10 0 4.25)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 48 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 48 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 48 0 0)
           (list 11 48 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 48 0 0)
           (cons 40 0.33333333)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 3 0 0)
           (cons 40 0.34)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 39.832021 -2.59333333)
           (cons 40 0)
           (cons 41 0)
           (cons 42 0)
           (cons 91 0)
           (list 10 39.832021 -2.07333333)
           (cons 40 0)
           (cons 41 0)
           (cons 42 0)
           (cons 91 0)
           (list 10 40.29868766 -1.91666667)
           (cons 40 0)
           (cons 41 0)
           (cons 42 0)
           (cons 91 0)
           (list 10 42.69868766 -1.91666667)
           (cons 40 0)
           (cons 41 0)
           (cons 42 0)
           (cons 91 0)
           (list 10 43.16535433 -2.07333333)
           (cons 40 0)
           (cons 41 0)
           (cons 42 0)
           (cons 91 0)
           (list 10 43.16535433 -2.59333333)
           (cons 40 0)
           (cons 41 0)
           (cons 42 0)
           (cons 91 0)
           (list 10 42.69868766 -2.75)
           (cons 40 0)
           (cons 41 0)
           (cons 42 0)
           (cons 91 0)
           (list 10 40.29868766 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 39.832021 -4.09333333)
           (cons 40 0)
           (cons 41 0)
           (cons 42 0)
           (cons 91 0)
           (list 10 39.832021 -3.57333333)
           (cons 40 0)
           (cons 41 0)
           (cons 42 0)
           (cons 91 0)
           (list 10 40.29868766 -3.41666667)
           (cons 40 0)
           (cons 41 0)
           (cons 42 0)
           (cons 91 0)
           (list 10 42.69868766 -3.41666667)
           (cons 40 0)
           (cons 41 0)
           (cons 42 0)
           (cons 91 0)
           (list 10 43.16535433 -3.57333333)
           (cons 40 0)
           (cons 41 0)
           (cons 42 0)
           (cons 91 0)
           (list 10 43.16535433 -4.09333333)
           (cons 40 0)
           (cons 41 0)
           (cons 42 0)
           (cons 91 0)
           (list 10 42.69868766 -4.25)
           (cons 40 0)
           (cons 41 0)
           (cons 42 0)
           (cons 91 0)
           (list 10 40.29868766 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 39.832021 2.07333333)
           (cons 40 0)
           (cons 41 0)
           (cons 42 0)
           (cons 91 0)
           (list 10 39.832021 2.59333333)
           (cons 40 0)
           (cons 41 0)
           (cons 42 0)
           (cons 91 0)
           (list 10 40.29868766 2.75)
           (cons 40 0)
           (cons 41 0)
           (cons 42 0)
           (cons 91 0)
           (list 10 42.69868766 2.75)
           (cons 40 0)
           (cons 41 0)
           (cons 42 0)
           (cons 91 0)
           (list 10 43.16535433 2.59333333)
           (cons 40 0)
           (cons 41 0)
           (cons 42 0)
           (cons 91 0)
           (list 10 43.16535433 2.07333333)
           (cons 40 0)
           (cons 41 0)
           (cons 42 0)
           (cons 91 0)
           (list 10 42.69868766 1.91666667)
           (cons 40 0)
           (cons 41 0)
           (cons 42 0)
           (cons 91 0)
           (list 10 40.29868766 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 39.832021 3.57333333)
           (cons 40 0)
           (cons 41 0)
           (cons 42 0)
           (cons 91 0)
           (list 10 39.832021 4.09333333)
           (cons 40 0)
           (cons 41 0)
           (cons 42 0)
           (cons 91 0)
           (list 10 40.29868766 4.25)
           (cons 40 0)
           (cons 41 0)
           (cons 42 0)
           (cons 91 0)
           (list 10 42.69868766 4.25)
           (cons 40 0)
           (cons 41 0)
           (cons 42 0)
           (cons 91 0)
           (list 10 43.16535433 4.09333333)
           (cons 40 0)
           (cons 41 0)
           (cons 42 0)
           (cons 91 0)
           (list 10 43.16535433 3.57333333)
           (cons 40 0)
           (cons 41 0)
           (cons 42 0)
           (cons 91 0)
           (list 10 42.69868766 3.41666667)
           (cons 40 0)
           (cons 41 0)
           (cons 42 0)
           (cons 91 0)
           (list 10 40.29868766 3.41666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 43.83464567 -2.59333333)
           (cons 40 0)
           (cons 41 0)
           (cons 42 0)
           (cons 91 0)
           (list 10 43.83464567 -2.07333333)
           (cons 40 0)
           (cons 41 0)
           (cons 42 0)
           (cons 91 0)
           (list 10 44.30131234 -1.91666667)
           (cons 40 0)
           (cons 41 0)
           (cons 42 0)
           (cons 91 0)
           (list 10 46.70131234 -1.91666667)
           (cons 40 0)
           (cons 41 0)
           (cons 42 0)
           (cons 91 0)
           (list 10 47.167979 -2.07333333)
           (cons 40 0)
           (cons 41 0)
           (cons 42 0)
           (cons 91 0)
           (list 10 47.167979 -2.59333333)
           (cons 40 0)
           (cons 41 0)
           (cons 42 0)
           (cons 91 0)
           (list 10 46.70131234 -2.75)
           (cons 40 0)
           (cons 41 0)
           (cons 42 0)
           (cons 91 0)
           (list 10 44.30131234 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 43.83464567 -4.09333333)
           (cons 40 0)
           (cons 41 0)
           (cons 42 0)
           (cons 91 0)
           (list 10 43.83464567 -3.57333333)
           (cons 40 0)
           (cons 41 0)
           (cons 42 0)
           (cons 91 0)
           (list 10 44.30131234 -3.41666667)
           (cons 40 0)
           (cons 41 0)
           (cons 42 0)
           (cons 91 0)
           (list 10 46.70131234 -3.41666667)
           (cons 40 0)
           (cons 41 0)
           (cons 42 0)
           (cons 91 0)
           (list 10 47.167979 -3.57333333)
           (cons 40 0)
           (cons 41 0)
           (cons 42 0)
           (cons 91 0)
           (list 10 47.167979 -4.09333333)
           (cons 40 0)
           (cons 41 0)
           (cons 42 0)
           (cons 91 0)
           (list 10 46.70131234 -4.25)
           (cons 40 0)
           (cons 41 0)
           (cons 42 0)
           (cons 91 0)
           (list 10 44.30131234 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 43.83464567 2.07333333)
           (cons 40 0)
           (cons 41 0)
           (cons 42 0)
           (cons 91 0)
           (list 10 43.83464567 2.59333333)
           (cons 40 0)
           (cons 41 0)
           (cons 42 0)
           (cons 91 0)
           (list 10 44.30131234 2.75)
           (cons 40 0)
           (cons 41 0)
           (cons 42 0)
           (cons 91 0)
           (list 10 46.70131234 2.75)
           (cons 40 0)
           (cons 41 0)
           (cons 42 0)
           (cons 91 0)
           (list 10 47.167979 2.59333333)
           (cons 40 0)
           (cons 41 0)
           (cons 42 0)
           (cons 91 0)
           (list 10 47.167979 2.07333333)
           (cons 40 0)
           (cons 41 0)
           (cons 42 0)
           (cons 91 0)
           (list 10 46.70131234 1.91666667)
           (cons 40 0)
           (cons 41 0)
           (cons 42 0)
           (cons 91 0)
           (list 10 44.30131234 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 43.83464567 3.57333333)
           (cons 40 0)
           (cons 41 0)
           (cons 42 0)
           (cons 91 0)
           (list 10 43.83464567 4.09333333)
           (cons 40 0)
           (cons 41 0)
           (cons 42 0)
           (cons 91 0)
           (list 10 44.30131234 4.25)
           (cons 40 0)
           (cons 41 0)
           (cons 42 0)
           (cons 91 0)
           (list 10 46.70131234 4.25)
           (cons 40 0)
           (cons 41 0)
           (cons 42 0)
           (cons 91 0)
           (list 10 47.167979 4.09333333)
           (cons 40 0)
           (cons 41 0)
           (cons 42 0)
           (cons 91 0)
           (list 10 47.167979 3.57333333)
           (cons 40 0)
           (cons 41 0)
           (cons 42 0)
           (cons 91 0)
           (list 10 46.70131234 3.41666667)
           (cons 40 0)
           (cons 41 0)
           (cons 42 0)
           (cons 91 0)
           (list 10 44.30131234 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4.25 0)
           (cons 50 0)
          )
         )
         (entmake
          (list
           (cons 0 "POINT")
           (cons 100 "AcDbEntity")
           (cons 67 0)
           (cons 8 "0")
           (cons 100 "AcDbPoint")
           (list 10 48 -4.25 0)
           (cons 50 0)
          )
         )
         (entmake
          (list
           (cons 0 "POINT")
           (cons 100 "AcDbEntity")
           (cons 67 0)
           (cons 8 "0")
           (cons 100 "AcDbPoint")
           (list 10 0 4.25 0)
           (cons 50 0)
          )
         )
         (entmake
          (list
           (cons 0 "POINT")
           (cons 100 "AcDbEntity")
           (cons 67 0)
           (cons 8 "0")
           (cons 100 "AcDbPoint")
           (list 10 48 4.25 0)
           (cons 50 0)
          )
         )
         (entmake
          (list
           (cons 0 "POINT")
           (cons 100 "AcDbEntity")
           (cons 67 0)
           (cons 8 "0")
           (cons 100 "AcDbPoint")
           (list 10 3 0 0)
           (cons 50 0)
          )
         )
         (entmake
          (list
           (cons 0 "POINT")
           (cons 100 "AcDbEntity")
           (cons 67 0)
           (cons 8 "0")
           (cons 100 "AcDbPoint")
           (list 10 48 0 0)
           (cons 50 0)
          )
         )
         (entmake
          (list
           (cons 0 "POINT")
           (cons 100 "AcDbEntity")
           (cons 67 0)
           (cons 8 "0")
           (cons 100 "AcDbPoint")
           (list 10 43.5 4.25 0)
           (cons 50 0)
          )
         )
         (entmake
          (list
           (cons 0 "POINT")
           (cons 100 "AcDbEntity")
           (cons 67 0)
           (cons 8 "0")
           (cons 100 "AcDbPoint")
           (list 10 43.5 -4.25 0)
           (cons 50 0)
          )
         )
         (entmake
          (list
           (cons 0 "ATTDEF")
           (cons 100 "AcDbEntity")
           (cons 67 0)
           (cons 8 "0")
           (cons 100 "AcDbText")
           (list 10 0.70341207 1.85914261 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 0.76552931 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -0.32808399 0)
           (cons 40 0.65616798)
           (cons 1 "43.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -1.42169729 0)
           (cons 40 0.65616798)
           (cons 1 "48.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-109D-PUP"))
        (progn
         (entmake)
         (entmake
          (list
           (cons 0 "BLOCK")
           (cons 2 "AASHTO-2011-WB-109D-PUP")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 3)
           (cons 70 1)
           (cons 43 0)
           (cons 38 0)
           (cons 39 0)
           (list 10 0 0)
           (cons 40 0)
           (cons 41 0)
           (cons 42 0)
           (cons 91 0)
           (list 10 10 4.25)
           (cons 40 0)
           (cons 41 0)
           (cons 42 0)
           (cons 91 0)
           (list 10 10 -4.25)
           (cons 40 0)
           (cons 41 0)
           (cons 42 0)
           (cons 91 0)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 10 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.56666667)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.332021 -2.59333333)
           (cons 40 0)
           (cons 41 0)
           (cons 42 0)
           (cons 91 0)
           (list 10 6.332021 -2.07333333)
           (cons 40 0)
           (cons 41 0)
           (cons 42 0)
           (cons 91 0)
           (list 10 6.79868766 -1.91666667)
           (cons 40 0)
           (cons 41 0)
           (cons 42 0)
           (cons 91 0)
           (list 10 9.19868766 -1.91666667)
           (cons 40 0)
           (cons 41 0)
           (cons 42 0)
           (cons 91 0)
           (list 10 9.66535433 -2.07333333)
           (cons 40 0)
           (cons 41 0)
           (cons 42 0)
           (cons 91 0)
           (list 10 9.66535433 -2.59333333)
           (cons 40 0)
           (cons 41 0)
           (cons 42 0)
           (cons 91 0)
           (list 10 9.19868766 -2.75)
           (cons 40 0)
           (cons 41 0)
           (cons 42 0)
           (cons 91 0)
           (list 10 6.79868766 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.332021 -4.09333333)
           (cons 40 0)
           (cons 41 0)
           (cons 42 0)
           (cons 91 0)
           (list 10 6.332021 -3.57333333)
           (cons 40 0)
           (cons 41 0)
           (cons 42 0)
           (cons 91 0)
           (list 10 6.79868766 -3.41666667)
           (cons 40 0)
           (cons 41 0)
           (cons 42 0)
           (cons 91 0)
           (list 10 9.19868766 -3.41666667)
           (cons 40 0)
           (cons 41 0)
           (cons 42 0)
           (cons 91 0)
           (list 10 9.66535433 -3.57333333)
           (cons 40 0)
           (cons 41 0)
           (cons 42 0)
           (cons 91 0)
           (list 10 9.66535433 -4.09333333)
           (cons 40 0)
           (cons 41 0)
           (cons 42 0)
           (cons 91 0)
           (list 10 9.19868766 -4.25)
           (cons 40 0)
           (cons 41 0)
           (cons 42 0)
           (cons 91 0)
           (list 10 6.79868766 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.332021 2.07333333)
           (cons 40 0)
           (cons 41 0)
           (cons 42 0)
           (cons 91 0)
           (list 10 6.332021 2.59333333)
           (cons 40 0)
           (cons 41 0)
           (cons 42 0)
           (cons 91 0)
           (list 10 6.79868766 2.75)
           (cons 40 0)
           (cons 41 0)
           (cons 42 0)
           (cons 91 0)
           (list 10 9.19868766 2.75)
           (cons 40 0)
           (cons 41 0)
           (cons 42 0)
           (cons 91 0)
           (list 10 9.66535433 2.59333333)
           (cons 40 0)
           (cons 41 0)
           (cons 42 0)
           (cons 91 0)
           (list 10 9.66535433 2.07333333)
           (cons 40 0)
           (cons 41 0)
           (cons 42 0)
           (cons 91 0)
           (list 10 9.19868766 1.91666667)
           (cons 40 0)
           (cons 41 0)
           (cons 42 0)
           (cons 91 0)
           (list 10 6.79868766 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.332021 3.57333333)
           (cons 40 0)
           (cons 41 0)
           (cons 42 0)
           (cons 91 0)
           (list 10 6.332021 4.09333333)
           (cons 40 0)
           (cons 41 0)
           (cons 42 0)
           (cons 91 0)
           (list 10 6.79868766 4.25)
           (cons 40 0)
           (cons 41 0)
           (cons 42 0)
           (cons 91 0)
           (list 10 9.19868766 4.25)
           (cons 40 0)
           (cons 41 0)
           (cons 42 0)
           (cons 91 0)
           (list 10 9.66535433 4.09333333)
           (cons 40 0)
           (cons 41 0)
           (cons 42 0)
           (cons 91 0)
           (list 10 9.66535433 3.57333333)
           (cons 40 0)
           (cons 41 0)
           (cons 42 0)
           (cons 91 0)
           (list 10 9.19868766 3.41666667)
           (cons 40 0)
           (cons 41 0)
           (cons 42 0)
           (cons 91 0)
           (list 10 6.79868766 3.41666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.33464567 -2.59333333)
           (cons 40 0)
           (cons 41 0)
           (cons 42 0)
           (cons 91 0)
           (list 10 10.33464567 -2.07333333)
           (cons 40 0)
           (cons 41 0)
           (cons 42 0)
           (cons 91 0)
           (list 10 10.80131234 -1.91666667)
           (cons 40 0)
           (cons 41 0)
           (cons 42 0)
           (cons 91 0)
           (list 10 13.20131234 -1.91666667)
           (cons 40 0)
           (cons 41 0)
           (cons 42 0)
           (cons 91 0)
           (list 10 13.667979 -2.07333333)
           (cons 40 0)
           (cons 41 0)
           (cons 42 0)
           (cons 91 0)
           (list 10 13.667979 -2.59333333)
           (cons 40 0)
           (cons 41 0)
           (cons 42 0)
           (cons 91 0)
           (list 10 13.20131234 -2.75)
           (cons 40 0)
           (cons 41 0)
           (cons 42 0)
           (cons 91 0)
           (list 10 10.80131234 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.33464567 -4.09333333)
           (cons 40 0)
           (cons 41 0)
           (cons 42 0)
           (cons 91 0)
           (list 10 10.33464567 -3.57333333)
           (cons 40 0)
           (cons 41 0)
           (cons 42 0)
           (cons 91 0)
           (list 10 10.80131234 -3.41666667)
           (cons 40 0)
           (cons 41 0)
           (cons 42 0)
           (cons 91 0)
           (list 10 13.20131234 -3.41666667)
           (cons 40 0)
           (cons 41 0)
           (cons 42 0)
           (cons 91 0)
           (list 10 13.667979 -3.57333333)
           (cons 40 0)
           (cons 41 0)
           (cons 42 0)
           (cons 91 0)
           (list 10 13.667979 -4.09333333)
           (cons 40 0)
           (cons 41 0)
           (cons 42 0)
           (cons 91 0)
           (list 10 13.20131234 -4.25)
           (cons 40 0)
           (cons 41 0)
           (cons 42 0)
           (cons 91 0)
           (list 10 10.80131234 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.33464567 2.07333333)
           (cons 40 0)
           (cons 41 0)
           (cons 42 0)
           (cons 91 0)
           (list 10 10.33464567 2.59333333)
           (cons 40 0)
           (cons 41 0)
           (cons 42 0)
           (cons 91 0)
           (list 10 10.80131234 2.75)
           (cons 40 0)
           (cons 41 0)
           (cons 42 0)
           (cons 91 0)
           (list 10 13.20131234 2.75)
           (cons 40 0)
           (cons 41 0)
           (cons 42 0)
           (cons 91 0)
           (list 10 13.667979 2.59333333)
           (cons 40 0)
           (cons 41 0)
           (cons 42 0)
           (cons 91 0)
           (list 10 13.667979 2.07333333)
           (cons 40 0)
           (cons 41 0)
           (cons 42 0)
           (cons 91 0)
           (list 10 13.20131234 1.91666667)
           (cons 40 0)
           (cons 41 0)
           (cons 42 0)
           (cons 91 0)
           (list 10 10.80131234 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.33464567 3.57333333)
           (cons 40 0)
           (cons 41 0)
           (cons 42 0)
           (cons 91 0)
           (list 10 10.33464567 4.09333333)
           (cons 40 0)
           (cons 41 0)
           (cons 42 0)
           (cons 91 0)
           (list 10 10.80131234 4.25)
           (cons 40 0)
           (cons 41 0)
           (cons 42 0)
           (cons 91 0)
           (list 10 13.20131234 4.25)
           (cons 40 0)
           (cons 41 0)
           (cons 42 0)
           (cons 91 0)
           (list 10 13.667979 4.09333333)
           (cons 40 0)
           (cons 41 0)
           (cons 42 0)
           (cons 91 0)
           (list 10 13.667979 3.57333333)
           (cons 40 0)
           (cons 41 0)
           (cons 42 0)
           (cons 91 0)
           (list 10 13.20131234 3.41666667)
           (cons 40 0)
           (cons 41 0)
           (cons 42 0)
           (cons 91 0)
           (list 10 10.80131234 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 10 0 0)
           (cons 50 0)
          )
         )
         (entmake
          (list
           (cons 0 "POINT")
           (cons 100 "AcDbEntity")
           (cons 67 0)
           (cons 8 "0")
           (cons 100 "AcDbPoint")
           (list 10 10 4.25 0)
           (cons 50 0)
          )
         )
         (entmake
          (list
           (cons 0 "POINT")
           (cons 100 "AcDbEntity")
           (cons 67 0)
           (cons 8 "0")
           (cons 100 "AcDbPoint")
           (list 10 10 -4.25 0)
           (cons 50 0)
          )
         )
         (entmake
          (list
           (cons 0 "ATTDEF")
           (cons 100 "AcDbEntity")
           (cons 67 0)
           (cons 8 "0")
           (cons 100 "AcDbText")
           (list 10 -2.29658793 1.85914261 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 0.76552931 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -0.32808399 0)
           (cons 40 0.65616798)
           (cons 1 "10.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -1.42169729 0)
           (cons 40 0.65616798)
           (cons 1 "10.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-109D-TRAILER"))
        (progn
         (entmake)
         (entmake
          (list
           (cons 0 "BLOCK")
           (cons 2 "AASHTO-2011-WB-109D-TRAILER")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4.25)
           (cons 40 0)
           (cons 41 0)
           (cons 42 0)
           (cons 91 0)
           (list 10 48 -4.25)
           (cons 40 0)
           (cons 41 0)
           (cons 42 0)
           (cons 91 0)
           (list 10 48 4.25)
           (cons 40 0)
           (cons 41 0)
           (cons 42 0)
           (cons 91 0)
           (list 10 0 4.25)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 48 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 48 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 48 0 0)
           (list 11 48 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 48 0 0)
           (cons 40 0.33333333)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 3 0 0)
           (cons 40 0.34)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 39.832021 -2.59333333)
           (cons 40 0)
           (cons 41 0)
           (cons 42 0)
           (cons 91 0)
           (list 10 39.832021 -2.07333333)
           (cons 40 0)
           (cons 41 0)
           (cons 42 0)
           (cons 91 0)
           (list 10 40.29868766 -1.91666667)
           (cons 40 0)
           (cons 41 0)
           (cons 42 0)
           (cons 91 0)
           (list 10 42.69868766 -1.91666667)
           (cons 40 0)
           (cons 41 0)
           (cons 42 0)
           (cons 91 0)
           (list 10 43.16535433 -2.07333333)
           (cons 40 0)
           (cons 41 0)
           (cons 42 0)
           (cons 91 0)
           (list 10 43.16535433 -2.59333333)
           (cons 40 0)
           (cons 41 0)
           (cons 42 0)
           (cons 91 0)
           (list 10 42.69868766 -2.75)
           (cons 40 0)
           (cons 41 0)
           (cons 42 0)
           (cons 91 0)
           (list 10 40.29868766 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 39.832021 -4.09333333)
           (cons 40 0)
           (cons 41 0)
           (cons 42 0)
           (cons 91 0)
           (list 10 39.832021 -3.57333333)
           (cons 40 0)
           (cons 41 0)
           (cons 42 0)
           (cons 91 0)
           (list 10 40.29868766 -3.41666667)
           (cons 40 0)
           (cons 41 0)
           (cons 42 0)
           (cons 91 0)
           (list 10 42.69868766 -3.41666667)
           (cons 40 0)
           (cons 41 0)
           (cons 42 0)
           (cons 91 0)
           (list 10 43.16535433 -3.57333333)
           (cons 40 0)
           (cons 41 0)
           (cons 42 0)
           (cons 91 0)
           (list 10 43.16535433 -4.09333333)
           (cons 40 0)
           (cons 41 0)
           (cons 42 0)
           (cons 91 0)
           (list 10 42.69868766 -4.25)
           (cons 40 0)
           (cons 41 0)
           (cons 42 0)
           (cons 91 0)
           (list 10 40.29868766 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 39.832021 2.07333333)
           (cons 40 0)
           (cons 41 0)
           (cons 42 0)
           (cons 91 0)
           (list 10 39.832021 2.59333333)
           (cons 40 0)
           (cons 41 0)
           (cons 42 0)
           (cons 91 0)
           (list 10 40.29868766 2.75)
           (cons 40 0)
           (cons 41 0)
           (cons 42 0)
           (cons 91 0)
           (list 10 42.69868766 2.75)
           (cons 40 0)
           (cons 41 0)
           (cons 42 0)
           (cons 91 0)
           (list 10 43.16535433 2.59333333)
           (cons 40 0)
           (cons 41 0)
           (cons 42 0)
           (cons 91 0)
           (list 10 43.16535433 2.07333333)
           (cons 40 0)
           (cons 41 0)
           (cons 42 0)
           (cons 91 0)
           (list 10 42.69868766 1.91666667)
           (cons 40 0)
           (cons 41 0)
           (cons 42 0)
           (cons 91 0)
           (list 10 40.29868766 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 39.832021 3.57333333)
           (cons 40 0)
           (cons 41 0)
           (cons 42 0)
           (cons 91 0)
           (list 10 39.832021 4.09333333)
           (cons 40 0)
           (cons 41 0)
           (cons 42 0)
           (cons 91 0)
           (list 10 40.29868766 4.25)
           (cons 40 0)
           (cons 41 0)
           (cons 42 0)
           (cons 91 0)
           (list 10 42.69868766 4.25)
           (cons 40 0)
           (cons 41 0)
           (cons 42 0)
           (cons 91 0)
           (list 10 43.16535433 4.09333333)
           (cons 40 0)
           (cons 41 0)
           (cons 42 0)
           (cons 91 0)
           (list 10 43.16535433 3.57333333)
           (cons 40 0)
           (cons 41 0)
           (cons 42 0)
           (cons 91 0)
           (list 10 42.69868766 3.41666667)
           (cons 40 0)
           (cons 41 0)
           (cons 42 0)
           (cons 91 0)
           (list 10 40.29868766 3.41666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 43.83464567 -2.59333333)
           (cons 40 0)
           (cons 41 0)
           (cons 42 0)
           (cons 91 0)
           (list 10 43.83464567 -2.07333333)
           (cons 40 0)
           (cons 41 0)
           (cons 42 0)
           (cons 91 0)
           (list 10 44.30131234 -1.91666667)
           (cons 40 0)
           (cons 41 0)
           (cons 42 0)
           (cons 91 0)
           (list 10 46.70131234 -1.91666667)
           (cons 40 0)
           (cons 41 0)
           (cons 42 0)
           (cons 91 0)
           (list 10 47.167979 -2.07333333)
           (cons 40 0)
           (cons 41 0)
           (cons 42 0)
           (cons 91 0)
           (list 10 47.167979 -2.59333333)
           (cons 40 0)
           (cons 41 0)
           (cons 42 0)
           (cons 91 0)
           (list 10 46.70131234 -2.75)
           (cons 40 0)
           (cons 41 0)
           (cons 42 0)
           (cons 91 0)
           (list 10 44.30131234 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 43.83464567 -4.09333333)
           (cons 40 0)
           (cons 41 0)
           (cons 42 0)
           (cons 91 0)
           (list 10 43.83464567 -3.57333333)
           (cons 40 0)
           (cons 41 0)
           (cons 42 0)
           (cons 91 0)
           (list 10 44.30131234 -3.41666667)
           (cons 40 0)
           (cons 41 0)
           (cons 42 0)
           (cons 91 0)
           (list 10 46.70131234 -3.41666667)
           (cons 40 0)
           (cons 41 0)
           (cons 42 0)
           (cons 91 0)
           (list 10 47.167979 -3.57333333)
           (cons 40 0)
           (cons 41 0)
           (cons 42 0)
           (cons 91 0)
           (list 10 47.167979 -4.09333333)
           (cons 40 0)
           (cons 41 0)
           (cons 42 0)
           (cons 91 0)
           (list 10 46.70131234 -4.25)
           (cons 40 0)
           (cons 41 0)
           (cons 42 0)
           (cons 91 0)
           (list 10 44.30131234 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 43.83464567 2.07333333)
           (cons 40 0)
           (cons 41 0)
           (cons 42 0)
           (cons 91 0)
           (list 10 43.83464567 2.59333333)
           (cons 40 0)
           (cons 41 0)
           (cons 42 0)
           (cons 91 0)
           (list 10 44.30131234 2.75)
           (cons 40 0)
           (cons 41 0)
           (cons 42 0)
           (cons 91 0)
           (list 10 46.70131234 2.75)
           (cons 40 0)
           (cons 41 0)
           (cons 42 0)
           (cons 91 0)
           (list 10 47.167979 2.59333333)
           (cons 40 0)
           (cons 41 0)
           (cons 42 0)
           (cons 91 0)
           (list 10 47.167979 2.07333333)
           (cons 40 0)
           (cons 41 0)
           (cons 42 0)
           (cons 91 0)
           (list 10 46.70131234 1.91666667)
           (cons 40 0)
           (cons 41 0)
           (cons 42 0)
           (cons 91 0)
           (list 10 44.30131234 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 43.83464567 3.57333333)
           (cons 40 0)
           (cons 41 0)
           (cons 42 0)
           (cons 91 0)
           (list 10 43.83464567 4.09333333)
           (cons 40 0)
           (cons 41 0)
           (cons 42 0)
           (cons 91 0)
           (list 10 44.30131234 4.25)
           (cons 40 0)
           (cons 41 0)
           (cons 42 0)
           (cons 91 0)
           (list 10 46.70131234 4.25)
           (cons 40 0)
           (cons 41 0)
           (cons 42 0)
           (cons 91 0)
           (list 10 47.167979 4.09333333)
           (cons 40 0)
           (cons 41 0)
           (cons 42 0)
           (cons 91 0)
           (list 10 47.167979 3.57333333)
           (cons 40 0)
           (cons 41 0)
           (cons 42 0)
           (cons 91 0)
           (list 10 46.70131234 3.41666667)
           (cons 40 0)
           (cons 41 0)
           (cons 42 0)
           (cons 91 0)
           (list 10 44.30131234 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4.25 0)
           (cons 50 0)
          )
         )
         (entmake
          (list
           (cons 0 "POINT")
           (cons 100 "AcDbEntity")
           (cons 67 0)
           (cons 8 "0")
           (cons 100 "AcDbPoint")
           (list 10 48 -4.25 0)
           (cons 50 0)
          )
         )
         (entmake
          (list
           (cons 0 "POINT")
           (cons 100 "AcDbEntity")
           (cons 67 0)
           (cons 8 "0")
           (cons 100 "AcDbPoint")
           (list 10 0 4.25 0)
           (cons 50 0)
          )
         )
         (entmake
          (list
           (cons 0 "POINT")
           (cons 100 "AcDbEntity")
           (cons 67 0)
           (cons 8 "0")
           (cons 100 "AcDbPoint")
           (list 10 48 4.25 0)
           (cons 50 0)
          )
         )
         (entmake
          (list
           (cons 0 "POINT")
           (cons 100 "AcDbEntity")
           (cons 67 0)
           (cons 8 "0")
           (cons 100 "AcDbPoint")
           (list 10 3 0 0)
           (cons 50 0)
          )
         )
         (entmake
          (list
           (cons 0 "POINT")
           (cons 100 "AcDbEntity")
           (cons 67 0)
           (cons 8 "0")
           (cons 100 "AcDbPoint")
           (list 10 48 0 0)
           (cons 50 0)
          )
         )
         (entmake
          (list
           (cons 0 "POINT")
           (cons 100 "AcDbEntity")
           (cons 67 0)
           (cons 8 "0")
           (cons 100 "AcDbPoint")
           (list 10 43.5 4.25 0)
           (cons 50 0)
          )
         )
         (entmake
          (list
           (cons 0 "POINT")
           (cons 100 "AcDbEntity")
           (cons 67 0)
           (cons 8 "0")
           (cons 100 "AcDbPoint")
           (list 10 43.5 -4.25 0)
           (cons 50 0)
          )
         )
         (entmake
          (list
           (cons 0 "ATTDEF")
           (cons 100 "AcDbEntity")
           (cons 67 0)
           (cons 8 "0")
           (cons 100 "AcDbText")
           (list 10 0.70341207 1.85914261 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 0.76552931 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -0.32808399 0)
           (cons 40 0.65616798)
           (cons 1 "43.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -1.42169729 0)
           (cons 40 0.65616798)
           (cons 1 "48.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-109D-TRUCK"))
        (progn
         (entmake)
         (entmake
          (list
           (cons 0 "BLOCK")
           (cons 2 "AASHTO-2011-WB-109D-TRUCK")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4)
           (cons 40 0)
           (cons 41 0)
           (cons 42 0)
           (cons 91 0)
           (list 10 16.6 -4)
           (cons 40 0)
           (cons 41 0)
           (cons 42 0)
           (cons 91 0)
           (list 10 16.6 4)
           (cons 40 0)
           (cons 41 0)
           (cons 42 0)
           (cons 91 0)
           (list 10 0 4)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.5 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.5 -1.66666667 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 16.6 -1.66666667 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 16.6 1.66666667 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.5 1.66666667 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.5 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 14 0 0)
           (cons 40 1.14285714)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 14.80812204 -0.80812204 0)
           (list 11 14.80812204 0.80812204 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.73333333 -2.34333333)
           (cons 40 0)
           (cons 41 0)
           (cons 42 0)
           (cons 91 0)
           (list 10 10.73333333 -1.82333333)
           (cons 40 0)
           (cons 41 0)
           (cons 42 0)
           (cons 91 0)
           (list 10 11.2 -1.66666667)
           (cons 40 0)
           (cons 41 0)
           (cons 42 0)
           (cons 91 0)
           (list 10 13.6 -1.66666667)
           (cons 40 0)
           (cons 41 0)
           (cons 42 0)
           (cons 91 0)
           (list 10 14.06666667 -1.82333333)
           (cons 40 0)
           (cons 41 0)
           (cons 42 0)
           (cons 91 0)
           (list 10 14.06666667 -2.34333333)
           (cons 40 0)
           (cons 41 0)
           (cons 42 0)
           (cons 91 0)
           (list 10 13.6 -2.5)
           (cons 40 0)
           (cons 41 0)
           (cons 42 0)
           (cons 91 0)
           (list 10 11.2 -2.5)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.73333333 -3.84333333)
           (cons 40 0)
           (cons 41 0)
           (cons 42 0)
           (cons 91 0)
           (list 10 10.73333333 -3.32333333)
           (cons 40 0)
           (cons 41 0)
           (cons 42 0)
           (cons 91 0)
           (list 10 11.2 -3.16666667)
           (cons 40 0)
           (cons 41 0)
           (cons 42 0)
           (cons 91 0)
           (list 10 13.6 -3.16666667)
           (cons 40 0)
           (cons 41 0)
           (cons 42 0)
           (cons 91 0)
           (list 10 14.06666667 -3.32333333)
           (cons 40 0)
           (cons 41 0)
           (cons 42 0)
           (cons 91 0)
           (list 10 14.06666667 -3.84333333)
           (cons 40 0)
           (cons 41 0)
           (cons 42 0)
           (cons 91 0)
           (list 10 13.6 -4)
           (cons 40 0)
           (cons 41 0)
           (cons 42 0)
           (cons 91 0)
           (list 10 11.2 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.73333333 1.82333333)
           (cons 40 0)
           (cons 41 0)
           (cons 42 0)
           (cons 91 0)
           (list 10 10.73333333 2.34333333)
           (cons 40 0)
           (cons 41 0)
           (cons 42 0)
           (cons 91 0)
           (list 10 11.2 2.5)
           (cons 40 0)
           (cons 41 0)
           (cons 42 0)
           (cons 91 0)
           (list 10 13.6 2.5)
           (cons 40 0)
           (cons 41 0)
           (cons 42 0)
           (cons 91 0)
           (list 10 14.06666667 2.34333333)
           (cons 40 0)
           (cons 41 0)
           (cons 42 0)
           (cons 91 0)
           (list 10 14.06666667 1.82333333)
           (cons 40 0)
           (cons 41 0)
           (cons 42 0)
           (cons 91 0)
           (list 10 13.6 1.66666667)
           (cons 40 0)
           (cons 41 0)
           (cons 42 0)
           (cons 91 0)
           (list 10 11.2 1.66666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.73333333 3.32333333)
           (cons 40 0)
           (cons 41 0)
           (cons 42 0)
           (cons 91 0)
           (list 10 10.73333333 3.84333333)
           (cons 40 0)
           (cons 41 0)
           (cons 42 0)
           (cons 91 0)
           (list 10 11.2 4)
           (cons 40 0)
           (cons 41 0)
           (cons 42 0)
           (cons 91 0)
           (list 10 13.6 4)
           (cons 40 0)
           (cons 41 0)
           (cons 42 0)
           (cons 91 0)
           (list 10 14.06666667 3.84333333)
           (cons 40 0)
           (cons 41 0)
           (cons 42 0)
           (cons 91 0)
           (list 10 14.06666667 3.32333333)
           (cons 40 0)
           (cons 41 0)
           (cons 42 0)
           (cons 91 0)
           (list 10 13.6 3.16666667)
           (cons 40 0)
           (cons 41 0)
           (cons 42 0)
           (cons 91 0)
           (list 10 11.2 3.16666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.93333333 -2.34333333)
           (cons 40 0)
           (cons 41 0)
           (cons 42 0)
           (cons 91 0)
           (list 10 14.93333333 -1.82333333)
           (cons 40 0)
           (cons 41 0)
           (cons 42 0)
           (cons 91 0)
           (list 10 15.4 -1.66666667)
           (cons 40 0)
           (cons 41 0)
           (cons 42 0)
           (cons 91 0)
           (list 10 17.8 -1.66666667)
           (cons 40 0)
           (cons 41 0)
           (cons 42 0)
           (cons 91 0)
           (list 10 18.26666667 -1.82333333)
           (cons 40 0)
           (cons 41 0)
           (cons 42 0)
           (cons 91 0)
           (list 10 18.26666667 -2.34333333)
           (cons 40 0)
           (cons 41 0)
           (cons 42 0)
           (cons 91 0)
           (list 10 17.8 -2.5)
           (cons 40 0)
           (cons 41 0)
           (cons 42 0)
           (cons 91 0)
           (list 10 15.4 -2.5)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.93333333 -3.84333333)
           (cons 40 0)
           (cons 41 0)
           (cons 42 0)
           (cons 91 0)
           (list 10 14.93333333 -3.32333333)
           (cons 40 0)
           (cons 41 0)
           (cons 42 0)
           (cons 91 0)
           (list 10 15.4 -3.16666667)
           (cons 40 0)
           (cons 41 0)
           (cons 42 0)
           (cons 91 0)
           (list 10 17.8 -3.16666667)
           (cons 40 0)
           (cons 41 0)
           (cons 42 0)
           (cons 91 0)
           (list 10 18.26666667 -3.32333333)
           (cons 40 0)
           (cons 41 0)
           (cons 42 0)
           (cons 91 0)
           (list 10 18.26666667 -3.84333333)
           (cons 40 0)
           (cons 41 0)
           (cons 42 0)
           (cons 91 0)
           (list 10 17.8 -4)
           (cons 40 0)
           (cons 41 0)
           (cons 42 0)
           (cons 91 0)
           (list 10 15.4 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.93333333 1.82333333)
           (cons 40 0)
           (cons 41 0)
           (cons 42 0)
           (cons 91 0)
           (list 10 14.93333333 2.34333333)
           (cons 40 0)
           (cons 41 0)
           (cons 42 0)
           (cons 91 0)
           (list 10 15.4 2.5)
           (cons 40 0)
           (cons 41 0)
           (cons 42 0)
           (cons 91 0)
           (list 10 17.8 2.5)
           (cons 40 0)
           (cons 41 0)
           (cons 42 0)
           (cons 91 0)
           (list 10 18.26666667 2.34333333)
           (cons 40 0)
           (cons 41 0)
           (cons 42 0)
           (cons 91 0)
           (list 10 18.26666667 1.82333333)
           (cons 40 0)
           (cons 41 0)
           (cons 42 0)
           (cons 91 0)
           (list 10 17.8 1.66666667)
           (cons 40 0)
           (cons 41 0)
           (cons 42 0)
           (cons 91 0)
           (list 10 15.4 1.66666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.93333333 3.32333333)
           (cons 40 0)
           (cons 41 0)
           (cons 42 0)
           (cons 91 0)
           (list 10 14.93333333 3.84333333)
           (cons 40 0)
           (cons 41 0)
           (cons 42 0)
           (cons 91 0)
           (list 10 15.4 4)
           (cons 40 0)
           (cons 41 0)
           (cons 42 0)
           (cons 91 0)
           (list 10 17.8 4)
           (cons 40 0)
           (cons 41 0)
           (cons 42 0)
           (cons 91 0)
           (list 10 18.26666667 3.84333333)
           (cons 40 0)
           (cons 41 0)
           (cons 42 0)
           (cons 91 0)
           (list 10 18.26666667 3.32333333)
           (cons 40 0)
           (cons 41 0)
           (cons 42 0)
           (cons 91 0)
           (list 10 17.8 3.16666667)
           (cons 40 0)
           (cons 41 0)
           (cons 42 0)
           (cons 91 0)
           (list 10 15.4 3.16666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4 0)
           (cons 50 0)
          )
         )
         (entmake
          (list
           (cons 0 "POINT")
           (cons 100 "AcDbEntity")
           (cons 67 0)
           (cons 8 "0")
           (cons 100 "AcDbPoint")
           (list 10 2.3 -4 0)
           (cons 50 0)
          )
         )
         (entmake
          (list
           (cons 0 "POINT")
           (cons 100 "AcDbEntity")
           (cons 67 0)
           (cons 8 "0")
           (cons 100 "AcDbPoint")
           (list 10 0 4 0)
           (cons 50 0)
          )
         )
         (entmake
          (list
           (cons 0 "POINT")
           (cons 100 "AcDbEntity")
           (cons 67 0)
           (cons 8 "0")
           (cons 100 "AcDbPoint")
           (list 10 2.3 4 0)
           (cons 50 0)
          )
         )
         (entmake
          (list
           (cons 0 "POINT")
           (cons 100 "AcDbEntity")
           (cons 67 0)
           (cons 8 "0")
           (cons 100 "AcDbPoint")
           (list 10 2.3 0 0)
           (cons 50 0)
          )
         )
         (entmake
          (list
           (cons 0 "POINT")
           (cons 100 "AcDbEntity")
           (cons 67 0)
           (cons 8 "0")
           (cons 100 "AcDbPoint")
           (list 10 14 0 0)
           (cons 50 0)
          )
         )
         (entmake
          (list
           (cons 0 "POINT")
           (cons 100 "AcDbEntity")
           (cons 67 0)
           (cons 8 "0")
           (cons 100 "AcDbPoint")
           (list 10 14.5 4 0)
           (cons 50 0)
          )
         )
         (entmake
          (list
           (cons 0 "POINT")
           (cons 100 "AcDbEntity")
           (cons 67 0)
           (cons 8 "0")
           (cons 100 "AcDbPoint")
           (list 10 14.5 -4 0)
           (cons 50 0)
          )
         )
         (entmake
          (list
           (cons 0 "INSERT")
           (cons 100 "AcDbEntity")
           (cons 67 0)
           (cons 8 "0")
           (cons 100 "AcDbBlockReference")
           (cons 2 "WheelLeft2")
           (list 10 2.3 -3.16666667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRight2")
           (list 10 2.3 3.16666667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 0.0328084 1.85914261 0)
           (cons 40 0.65616798)
           (cons 1 "2.300")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.0328084 0.76552931 0)
           (cons 40 0.65616798)
           (cons 1 "2.300")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.0328084 -0.32808399 0)
           (cons 40 0.65616798)
           (cons 1 "14.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.0328084 -1.42169729 0)
           (cons 40 0.65616798)
           (cons 1 "14.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.0328084 -2.51531059 0)
           (cons 40 0.65616798)
           (cons 1 "12.6")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-100T-TRAILER"))
        (progn
         (entmake)
         (entmake
          (list
           (cons 0 "BLOCK")
           (cons 2 "AASHTO-2011-WB-100T-TRAILER")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4.25)
           (cons 40 0)
           (cons 41 0)
           (cons 42 0)
           (cons 91 0)
           (list 10 28.5 -4.25)
           (cons 40 0)
           (cons 41 0)
           (cons 42 0)
           (cons 91 0)
           (list 10 28.5 4.25)
           (cons 40 0)
           (cons 41 0)
           (cons 42 0)
           (cons 91 0)
           (list 10 0 4.25)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 28.5 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 28.5 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 2.5 0 0)
           (cons 40 0.34)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 -2.59333333)
           (cons 40 0)
           (cons 41 0)
           (cons 42 0)
           (cons 91 0)
           (list 10 23.83333333 -2.07333333)
           (cons 40 0)
           (cons 41 0)
           (cons 42 0)
           (cons 91 0)
           (list 10 24.3 -1.91666667)
           (cons 40 0)
           (cons 41 0)
           (cons 42 0)
           (cons 91 0)
           (list 10 26.7 -1.91666667)
           (cons 40 0)
           (cons 41 0)
           (cons 42 0)
           (cons 91 0)
           (list 10 27.16666667 -2.07333333)
           (cons 40 0)
           (cons 41 0)
           (cons 42 0)
           (cons 91 0)
           (list 10 27.16666667 -2.59333333)
           (cons 40 0)
           (cons 41 0)
           (cons 42 0)
           (cons 91 0)
           (list 10 26.7 -2.75)
           (cons 40 0)
           (cons 41 0)
           (cons 42 0)
           (cons 91 0)
           (list 10 24.3 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 -4.09333333)
           (cons 40 0)
           (cons 41 0)
           (cons 42 0)
           (cons 91 0)
           (list 10 23.83333333 -3.57333333)
           (cons 40 0)
           (cons 41 0)
           (cons 42 0)
           (cons 91 0)
           (list 10 24.3 -3.41666667)
           (cons 40 0)
           (cons 41 0)
           (cons 42 0)
           (cons 91 0)
           (list 10 26.7 -3.41666667)
           (cons 40 0)
           (cons 41 0)
           (cons 42 0)
           (cons 91 0)
           (list 10 27.16666667 -3.57333333)
           (cons 40 0)
           (cons 41 0)
           (cons 42 0)
           (cons 91 0)
           (list 10 27.16666667 -4.09333333)
           (cons 40 0)
           (cons 41 0)
           (cons 42 0)
           (cons 91 0)
           (list 10 26.7 -4.25)
           (cons 40 0)
           (cons 41 0)
           (cons 42 0)
           (cons 91 0)
           (list 10 24.3 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 2.07333333)
           (cons 40 0)
           (cons 41 0)
           (cons 42 0)
           (cons 91 0)
           (list 10 23.83333333 2.59333333)
           (cons 40 0)
           (cons 41 0)
           (cons 42 0)
           (cons 91 0)
           (list 10 24.3 2.75)
           (cons 40 0)
           (cons 41 0)
           (cons 42 0)
           (cons 91 0)
           (list 10 26.7 2.75)
           (cons 40 0)
           (cons 41 0)
           (cons 42 0)
           (cons 91 0)
           (list 10 27.16666667 2.59333333)
           (cons 40 0)
           (cons 41 0)
           (cons 42 0)
           (cons 91 0)
           (list 10 27.16666667 2.07333333)
           (cons 40 0)
           (cons 41 0)
           (cons 42 0)
           (cons 91 0)
           (list 10 26.7 1.91666667)
           (cons 40 0)
           (cons 41 0)
           (cons 42 0)
           (cons 91 0)
           (list 10 24.3 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 3.57333333)
           (cons 40 0)
           (cons 41 0)
           (cons 42 0)
           (cons 91 0)
           (list 10 23.83333333 4.09333333)
           (cons 40 0)
           (cons 41 0)
           (cons 42 0)
           (cons 91 0)
           (list 10 24.3 4.25)
           (cons 40 0)
           (cons 41 0)
           (cons 42 0)
           (cons 91 0)
           (list 10 26.7 4.25)
           (cons 40 0)
           (cons 41 0)
           (cons 42 0)
           (cons 91 0)
           (list 10 27.16666667 4.09333333)
           (cons 40 0)
           (cons 41 0)
           (cons 42 0)
           (cons 91 0)
           (list 10 27.16666667 3.57333333)
           (cons 40 0)
           (cons 41 0)
           (cons 42 0)
           (cons 91 0)
           (list 10 26.7 3.41666667)
           (cons 40 0)
           (cons 41 0)
           (cons 42 0)
           (cons 91 0)
           (list 10 24.3 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4.25 0)
           (cons 50 0)
          )
         )
         (entmake
          (list
           (cons 0 "POINT")
           (cons 100 "AcDbEntity")
           (cons 67 0)
           (cons 8 "0")
           (cons 100 "AcDbPoint")
           (list 10 25.5 -4.25 0)
           (cons 50 0)
          )
         )
         (entmake
          (list
           (cons 0 "POINT")
           (cons 100 "AcDbEntity")
           (cons 67 0)
           (cons 8 "0")
           (cons 100 "AcDbPoint")
           (list 10 28.5 -4.25 0)
           (cons 50 0)
          )
         )
         (entmake
          (list
           (cons 0 "POINT")
           (cons 100 "AcDbEntity")
           (cons 67 0)
           (cons 8 "0")
           (cons 100 "AcDbPoint")
           (list 10 28.5 0 0)
           (cons 50 0)
          )
         )
         (entmake
          (list
           (cons 0 "POINT")
           (cons 100 "AcDbEntity")
           (cons 67 0)
           (cons 8 "0")
           (cons 100 "AcDbPoint")
           (list 10 28.5 4.25 0)
           (cons 50 0)
          )
         )
         (entmake
          (list
           (cons 0 "POINT")
           (cons 100 "AcDbEntity")
           (cons 67 0)
           (cons 8 "0")
           (cons 100 "AcDbPoint")
           (list 10 25.5 4.25 0)
           (cons 50 0)
          )
         )
         (entmake
          (list
           (cons 0 "POINT")
           (cons 100 "AcDbEntity")
           (cons 67 0)
           (cons 8 "0")
           (cons 100 "AcDbPoint")
           (list 10 0 4.25 0)
           (cons 50 0)
          )
         )
         (entmake
          (list
           (cons 0 "POINT")
           (cons 100 "AcDbEntity")
           (cons 67 0)
           (cons 8 "0")
           (cons 100 "AcDbPoint")
           (list 10 2.5 0 0)
           (cons 50 0)
          )
         )
         (entmake
          (list
           (cons 0 "ATTDEF")
           (cons 100 "AcDbEntity")
           (cons 67 0)
           (cons 8 "0")
           (cons 100 "AcDbText")
           (list 10 0.20341207 1.85914261 0)
           (cons 40 0.65616798)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 0.76552931 0)
           (cons 40 0.65616798)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -0.32808399 0)
           (cons 40 0.65616798)
           (cons 1 "25.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -1.42169729 0)
           (cons 40 0.65616798)
           (cons 1 "28.500")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-100T-PUP"))
        (progn
         (entmake)
         (entmake
          (list
           (cons 0 "BLOCK")
           (cons 2 "AASHTO-2011-WB-100T-PUP")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 3)
           (cons 70 1)
           (cons 43 0)
           (cons 38 0)
           (cons 39 0)
           (list 10 0 0)
           (cons 40 0)
           (cons 41 0)
           (cons 42 0)
           (cons 91 0)
           (list 10 7 4.25)
           (cons 40 0)
           (cons 41 0)
           (cons 42 0)
           (cons 91 0)
           (list 10 7 -4.25)
           (cons 40 0)
           (cons 41 0)
           (cons 42 0)
           (cons 91 0)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 7 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.56666667)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.33333333 -4.09333333)
           (cons 40 0)
           (cons 41 0)
           (cons 42 0)
           (cons 91 0)
           (list 10 5.33333333 -3.57333333)
           (cons 40 0)
           (cons 41 0)
           (cons 42 0)
           (cons 91 0)
           (list 10 5.8 -3.41666667)
           (cons 40 0)
           (cons 41 0)
           (cons 42 0)
           (cons 91 0)
           (list 10 8.2 -3.41666667)
           (cons 40 0)
           (cons 41 0)
           (cons 42 0)
           (cons 91 0)
           (list 10 8.66666667 -3.57333333)
           (cons 40 0)
           (cons 41 0)
           (cons 42 0)
           (cons 91 0)
           (list 10 8.66666667 -4.09333333)
           (cons 40 0)
           (cons 41 0)
           (cons 42 0)
           (cons 91 0)
           (list 10 8.2 -4.25)
           (cons 40 0)
           (cons 41 0)
           (cons 42 0)
           (cons 91 0)
           (list 10 5.8 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.33333333 3.57333333)
           (cons 40 0)
           (cons 41 0)
           (cons 42 0)
           (cons 91 0)
           (list 10 5.33333333 4.09333333)
           (cons 40 0)
           (cons 41 0)
           (cons 42 0)
           (cons 91 0)
           (list 10 5.8 4.25)
           (cons 40 0)
           (cons 41 0)
           (cons 42 0)
           (cons 91 0)
           (list 10 8.2 4.25)
           (cons 40 0)
           (cons 41 0)
           (cons 42 0)
           (cons 91 0)
           (list 10 8.66666667 4.09333333)
           (cons 40 0)
           (cons 41 0)
           (cons 42 0)
           (cons 91 0)
           (list 10 8.66666667 3.57333333)
           (cons 40 0)
           (cons 41 0)
           (cons 42 0)
           (cons 91 0)
           (list 10 8.2 3.41666667)
           (cons 40 0)
           (cons 41 0)
           (cons 42 0)
           (cons 91 0)
           (list 10 5.8 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 7 0 0)
           (cons 50 0)
          )
         )
         (entmake
          (list
           (cons 0 "POINT")
           (cons 100 "AcDbEntity")
           (cons 67 0)
           (cons 8 "0")
           (cons 100 "AcDbPoint")
           (list 10 7 4.25 0)
           (cons 50 0)
          )
         )
         (entmake
          (list
           (cons 0 "POINT")
           (cons 100 "AcDbEntity")
           (cons 67 0)
           (cons 8 "0")
           (cons 100 "AcDbPoint")
           (list 10 7 -4.25 0)
           (cons 50 0)
          )
         )
         (entmake
          (list
           (cons 0 "ATTDEF")
           (cons 100 "AcDbEntity")
           (cons 67 0)
           (cons 8 "0")
           (cons 100 "AcDbText")
           (list 10 -2.29658793 1.85914261 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 0.76552931 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -0.32808399 0)
           (cons 40 0.65616798)
           (cons 1 "7.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -1.42169729 0)
           (cons 40 0.65616798)
           (cons 1 "7.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-100T-TRAILER"))
        (progn
         (entmake)
         (entmake
          (list
           (cons 0 "BLOCK")
           (cons 2 "AASHTO-2011-WB-100T-TRAILER")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4.25)
           (cons 40 0)
           (cons 41 0)
           (cons 42 0)
           (cons 91 0)
           (list 10 28.5 -4.25)
           (cons 40 0)
           (cons 41 0)
           (cons 42 0)
           (cons 91 0)
           (list 10 28.5 4.25)
           (cons 40 0)
           (cons 41 0)
           (cons 42 0)
           (cons 91 0)
           (list 10 0 4.25)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 28.5 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 28.5 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 2.5 0 0)
           (cons 40 0.34)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 -2.59333333)
           (cons 40 0)
           (cons 41 0)
           (cons 42 0)
           (cons 91 0)
           (list 10 23.83333333 -2.07333333)
           (cons 40 0)
           (cons 41 0)
           (cons 42 0)
           (cons 91 0)
           (list 10 24.3 -1.91666667)
           (cons 40 0)
           (cons 41 0)
           (cons 42 0)
           (cons 91 0)
           (list 10 26.7 -1.91666667)
           (cons 40 0)
           (cons 41 0)
           (cons 42 0)
           (cons 91 0)
           (list 10 27.16666667 -2.07333333)
           (cons 40 0)
           (cons 41 0)
           (cons 42 0)
           (cons 91 0)
           (list 10 27.16666667 -2.59333333)
           (cons 40 0)
           (cons 41 0)
           (cons 42 0)
           (cons 91 0)
           (list 10 26.7 -2.75)
           (cons 40 0)
           (cons 41 0)
           (cons 42 0)
           (cons 91 0)
           (list 10 24.3 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 -4.09333333)
           (cons 40 0)
           (cons 41 0)
           (cons 42 0)
           (cons 91 0)
           (list 10 23.83333333 -3.57333333)
           (cons 40 0)
           (cons 41 0)
           (cons 42 0)
           (cons 91 0)
           (list 10 24.3 -3.41666667)
           (cons 40 0)
           (cons 41 0)
           (cons 42 0)
           (cons 91 0)
           (list 10 26.7 -3.41666667)
           (cons 40 0)
           (cons 41 0)
           (cons 42 0)
           (cons 91 0)
           (list 10 27.16666667 -3.57333333)
           (cons 40 0)
           (cons 41 0)
           (cons 42 0)
           (cons 91 0)
           (list 10 27.16666667 -4.09333333)
           (cons 40 0)
           (cons 41 0)
           (cons 42 0)
           (cons 91 0)
           (list 10 26.7 -4.25)
           (cons 40 0)
           (cons 41 0)
           (cons 42 0)
           (cons 91 0)
           (list 10 24.3 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 2.07333333)
           (cons 40 0)
           (cons 41 0)
           (cons 42 0)
           (cons 91 0)
           (list 10 23.83333333 2.59333333)
           (cons 40 0)
           (cons 41 0)
           (cons 42 0)
           (cons 91 0)
           (list 10 24.3 2.75)
           (cons 40 0)
           (cons 41 0)
           (cons 42 0)
           (cons 91 0)
           (list 10 26.7 2.75)
           (cons 40 0)
           (cons 41 0)
           (cons 42 0)
           (cons 91 0)
           (list 10 27.16666667 2.59333333)
           (cons 40 0)
           (cons 41 0)
           (cons 42 0)
           (cons 91 0)
           (list 10 27.16666667 2.07333333)
           (cons 40 0)
           (cons 41 0)
           (cons 42 0)
           (cons 91 0)
           (list 10 26.7 1.91666667)
           (cons 40 0)
           (cons 41 0)
           (cons 42 0)
           (cons 91 0)
           (list 10 24.3 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 3.57333333)
           (cons 40 0)
           (cons 41 0)
           (cons 42 0)
           (cons 91 0)
           (list 10 23.83333333 4.09333333)
           (cons 40 0)
           (cons 41 0)
           (cons 42 0)
           (cons 91 0)
           (list 10 24.3 4.25)
           (cons 40 0)
           (cons 41 0)
           (cons 42 0)
           (cons 91 0)
           (list 10 26.7 4.25)
           (cons 40 0)
           (cons 41 0)
           (cons 42 0)
           (cons 91 0)
           (list 10 27.16666667 4.09333333)
           (cons 40 0)
           (cons 41 0)
           (cons 42 0)
           (cons 91 0)
           (list 10 27.16666667 3.57333333)
           (cons 40 0)
           (cons 41 0)
           (cons 42 0)
           (cons 91 0)
           (list 10 26.7 3.41666667)
           (cons 40 0)
           (cons 41 0)
           (cons 42 0)
           (cons 91 0)
           (list 10 24.3 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4.25 0)
           (cons 50 0)
          )
         )
         (entmake
          (list
           (cons 0 "POINT")
           (cons 100 "AcDbEntity")
           (cons 67 0)
           (cons 8 "0")
           (cons 100 "AcDbPoint")
           (list 10 25.5 -4.25 0)
           (cons 50 0)
          )
         )
         (entmake
          (list
           (cons 0 "POINT")
           (cons 100 "AcDbEntity")
           (cons 67 0)
           (cons 8 "0")
           (cons 100 "AcDbPoint")
           (list 10 28.5 -4.25 0)
           (cons 50 0)
          )
         )
         (entmake
          (list
           (cons 0 "POINT")
           (cons 100 "AcDbEntity")
           (cons 67 0)
           (cons 8 "0")
           (cons 100 "AcDbPoint")
           (list 10 28.5 0 0)
           (cons 50 0)
          )
         )
         (entmake
          (list
           (cons 0 "POINT")
           (cons 100 "AcDbEntity")
           (cons 67 0)
           (cons 8 "0")
           (cons 100 "AcDbPoint")
           (list 10 28.5 4.25 0)
           (cons 50 0)
          )
         )
         (entmake
          (list
           (cons 0 "POINT")
           (cons 100 "AcDbEntity")
           (cons 67 0)
           (cons 8 "0")
           (cons 100 "AcDbPoint")
           (list 10 25.5 4.25 0)
           (cons 50 0)
          )
         )
         (entmake
          (list
           (cons 0 "POINT")
           (cons 100 "AcDbEntity")
           (cons 67 0)
           (cons 8 "0")
           (cons 100 "AcDbPoint")
           (list 10 0 4.25 0)
           (cons 50 0)
          )
         )
         (entmake
          (list
           (cons 0 "POINT")
           (cons 100 "AcDbEntity")
           (cons 67 0)
           (cons 8 "0")
           (cons 100 "AcDbPoint")
           (list 10 2.5 0 0)
           (cons 50 0)
          )
         )
         (entmake
          (list
           (cons 0 "ATTDEF")
           (cons 100 "AcDbEntity")
           (cons 67 0)
           (cons 8 "0")
           (cons 100 "AcDbText")
           (list 10 0.20341207 1.85914261 0)
           (cons 40 0.65616798)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 0.76552931 0)
           (cons 40 0.65616798)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -0.32808399 0)
           (cons 40 0.65616798)
           (cons 1 "25.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -1.42169729 0)
           (cons 40 0.65616798)
           (cons 1 "28.500")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-100T-PUP"))
        (progn
         (entmake)
         (entmake
          (list
           (cons 0 "BLOCK")
           (cons 2 "AASHTO-2011-WB-100T-PUP")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 3)
           (cons 70 1)
           (cons 43 0)
           (cons 38 0)
           (cons 39 0)
           (list 10 0 0)
           (cons 40 0)
           (cons 41 0)
           (cons 42 0)
           (cons 91 0)
           (list 10 7 4.25)
           (cons 40 0)
           (cons 41 0)
           (cons 42 0)
           (cons 91 0)
           (list 10 7 -4.25)
           (cons 40 0)
           (cons 41 0)
           (cons 42 0)
           (cons 91 0)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 7 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.56666667)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.33333333 -4.09333333)
           (cons 40 0)
           (cons 41 0)
           (cons 42 0)
           (cons 91 0)
           (list 10 5.33333333 -3.57333333)
           (cons 40 0)
           (cons 41 0)
           (cons 42 0)
           (cons 91 0)
           (list 10 5.8 -3.41666667)
           (cons 40 0)
           (cons 41 0)
           (cons 42 0)
           (cons 91 0)
           (list 10 8.2 -3.41666667)
           (cons 40 0)
           (cons 41 0)
           (cons 42 0)
           (cons 91 0)
           (list 10 8.66666667 -3.57333333)
           (cons 40 0)
           (cons 41 0)
           (cons 42 0)
           (cons 91 0)
           (list 10 8.66666667 -4.09333333)
           (cons 40 0)
           (cons 41 0)
           (cons 42 0)
           (cons 91 0)
           (list 10 8.2 -4.25)
           (cons 40 0)
           (cons 41 0)
           (cons 42 0)
           (cons 91 0)
           (list 10 5.8 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.33333333 3.57333333)
           (cons 40 0)
           (cons 41 0)
           (cons 42 0)
           (cons 91 0)
           (list 10 5.33333333 4.09333333)
           (cons 40 0)
           (cons 41 0)
           (cons 42 0)
           (cons 91 0)
           (list 10 5.8 4.25)
           (cons 40 0)
           (cons 41 0)
           (cons 42 0)
           (cons 91 0)
           (list 10 8.2 4.25)
           (cons 40 0)
           (cons 41 0)
           (cons 42 0)
           (cons 91 0)
           (list 10 8.66666667 4.09333333)
           (cons 40 0)
           (cons 41 0)
           (cons 42 0)
           (cons 91 0)
           (list 10 8.66666667 3.57333333)
           (cons 40 0)
           (cons 41 0)
           (cons 42 0)
           (cons 91 0)
           (list 10 8.2 3.41666667)
           (cons 40 0)
           (cons 41 0)
           (cons 42 0)
           (cons 91 0)
           (list 10 5.8 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 7 0 0)
           (cons 50 0)
          )
         )
         (entmake
          (list
           (cons 0 "POINT")
           (cons 100 "AcDbEntity")
           (cons 67 0)
           (cons 8 "0")
           (cons 100 "AcDbPoint")
           (list 10 7 4.25 0)
           (cons 50 0)
          )
         )
         (entmake
          (list
           (cons 0 "POINT")
           (cons 100 "AcDbEntity")
           (cons 67 0)
           (cons 8 "0")
           (cons 100 "AcDbPoint")
           (list 10 7 -4.25 0)
           (cons 50 0)
          )
         )
         (entmake
          (list
           (cons 0 "ATTDEF")
           (cons 100 "AcDbEntity")
           (cons 67 0)
           (cons 8 "0")
           (cons 100 "AcDbText")
           (list 10 -2.29658793 1.85914261 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 0.76552931 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -0.32808399 0)
           (cons 40 0.65616798)
           (cons 1 "7.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -1.42169729 0)
           (cons 40 0.65616798)
           (cons 1 "7.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-100T-TRAILER"))
        (progn
         (entmake)
         (entmake
          (list
           (cons 0 "BLOCK")
           (cons 2 "AASHTO-2011-WB-100T-TRAILER")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4.25)
           (cons 40 0)
           (cons 41 0)
           (cons 42 0)
           (cons 91 0)
           (list 10 28.5 -4.25)
           (cons 40 0)
           (cons 41 0)
           (cons 42 0)
           (cons 91 0)
           (list 10 28.5 4.25)
           (cons 40 0)
           (cons 41 0)
           (cons 42 0)
           (cons 91 0)
           (list 10 0 4.25)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 28.5 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 28.5 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 2.5 0 0)
           (cons 40 0.34)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 -2.59333333)
           (cons 40 0)
           (cons 41 0)
           (cons 42 0)
           (cons 91 0)
           (list 10 23.83333333 -2.07333333)
           (cons 40 0)
           (cons 41 0)
           (cons 42 0)
           (cons 91 0)
           (list 10 24.3 -1.91666667)
           (cons 40 0)
           (cons 41 0)
           (cons 42 0)
           (cons 91 0)
           (list 10 26.7 -1.91666667)
           (cons 40 0)
           (cons 41 0)
           (cons 42 0)
           (cons 91 0)
           (list 10 27.16666667 -2.07333333)
           (cons 40 0)
           (cons 41 0)
           (cons 42 0)
           (cons 91 0)
           (list 10 27.16666667 -2.59333333)
           (cons 40 0)
           (cons 41 0)
           (cons 42 0)
           (cons 91 0)
           (list 10 26.7 -2.75)
           (cons 40 0)
           (cons 41 0)
           (cons 42 0)
           (cons 91 0)
           (list 10 24.3 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 -4.09333333)
           (cons 40 0)
           (cons 41 0)
           (cons 42 0)
           (cons 91 0)
           (list 10 23.83333333 -3.57333333)
           (cons 40 0)
           (cons 41 0)
           (cons 42 0)
           (cons 91 0)
           (list 10 24.3 -3.41666667)
           (cons 40 0)
           (cons 41 0)
           (cons 42 0)
           (cons 91 0)
           (list 10 26.7 -3.41666667)
           (cons 40 0)
           (cons 41 0)
           (cons 42 0)
           (cons 91 0)
           (list 10 27.16666667 -3.57333333)
           (cons 40 0)
           (cons 41 0)
           (cons 42 0)
           (cons 91 0)
           (list 10 27.16666667 -4.09333333)
           (cons 40 0)
           (cons 41 0)
           (cons 42 0)
           (cons 91 0)
           (list 10 26.7 -4.25)
           (cons 40 0)
           (cons 41 0)
           (cons 42 0)
           (cons 91 0)
           (list 10 24.3 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 2.07333333)
           (cons 40 0)
           (cons 41 0)
           (cons 42 0)
           (cons 91 0)
           (list 10 23.83333333 2.59333333)
           (cons 40 0)
           (cons 41 0)
           (cons 42 0)
           (cons 91 0)
           (list 10 24.3 2.75)
           (cons 40 0)
           (cons 41 0)
           (cons 42 0)
           (cons 91 0)
           (list 10 26.7 2.75)
           (cons 40 0)
           (cons 41 0)
           (cons 42 0)
           (cons 91 0)
           (list 10 27.16666667 2.59333333)
           (cons 40 0)
           (cons 41 0)
           (cons 42 0)
           (cons 91 0)
           (list 10 27.16666667 2.07333333)
           (cons 40 0)
           (cons 41 0)
           (cons 42 0)
           (cons 91 0)
           (list 10 26.7 1.91666667)
           (cons 40 0)
           (cons 41 0)
           (cons 42 0)
           (cons 91 0)
           (list 10 24.3 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 3.57333333)
           (cons 40 0)
           (cons 41 0)
           (cons 42 0)
           (cons 91 0)
           (list 10 23.83333333 4.09333333)
           (cons 40 0)
           (cons 41 0)
           (cons 42 0)
           (cons 91 0)
           (list 10 24.3 4.25)
           (cons 40 0)
           (cons 41 0)
           (cons 42 0)
           (cons 91 0)
           (list 10 26.7 4.25)
           (cons 40 0)
           (cons 41 0)
           (cons 42 0)
           (cons 91 0)
           (list 10 27.16666667 4.09333333)
           (cons 40 0)
           (cons 41 0)
           (cons 42 0)
           (cons 91 0)
           (list 10 27.16666667 3.57333333)
           (cons 40 0)
           (cons 41 0)
           (cons 42 0)
           (cons 91 0)
           (list 10 26.7 3.41666667)
           (cons 40 0)
           (cons 41 0)
           (cons 42 0)
           (cons 91 0)
           (list 10 24.3 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4.25 0)
           (cons 50 0)
          )
         )
         (entmake
          (list
           (cons 0 "POINT")
           (cons 100 "AcDbEntity")
           (cons 67 0)
           (cons 8 "0")
           (cons 100 "AcDbPoint")
           (list 10 25.5 -4.25 0)
           (cons 50 0)
          )
         )
         (entmake
          (list
           (cons 0 "POINT")
           (cons 100 "AcDbEntity")
           (cons 67 0)
           (cons 8 "0")
           (cons 100 "AcDbPoint")
           (list 10 28.5 -4.25 0)
           (cons 50 0)
          )
         )
         (entmake
          (list
           (cons 0 "POINT")
           (cons 100 "AcDbEntity")
           (cons 67 0)
           (cons 8 "0")
           (cons 100 "AcDbPoint")
           (list 10 28.5 0 0)
           (cons 50 0)
          )
         )
         (entmake
          (list
           (cons 0 "POINT")
           (cons 100 "AcDbEntity")
           (cons 67 0)
           (cons 8 "0")
           (cons 100 "AcDbPoint")
           (list 10 28.5 4.25 0)
           (cons 50 0)
          )
         )
         (entmake
          (list
           (cons 0 "POINT")
           (cons 100 "AcDbEntity")
           (cons 67 0)
           (cons 8 "0")
           (cons 100 "AcDbPoint")
           (list 10 25.5 4.25 0)
           (cons 50 0)
          )
         )
         (entmake
          (list
           (cons 0 "POINT")
           (cons 100 "AcDbEntity")
           (cons 67 0)
           (cons 8 "0")
           (cons 100 "AcDbPoint")
           (list 10 0 4.25 0)
           (cons 50 0)
          )
         )
         (entmake
          (list
           (cons 0 "POINT")
           (cons 100 "AcDbEntity")
           (cons 67 0)
           (cons 8 "0")
           (cons 100 "AcDbPoint")
           (list 10 2.5 0 0)
           (cons 50 0)
          )
         )
         (entmake
          (list
           (cons 0 "ATTDEF")
           (cons 100 "AcDbEntity")
           (cons 67 0)
           (cons 8 "0")
           (cons 100 "AcDbText")
           (list 10 0.20341207 1.85914261 0)
           (cons 40 0.65616798)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 0.76552931 0)
           (cons 40 0.65616798)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -0.32808399 0)
           (cons 40 0.65616798)
           (cons 1 "25.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -1.42169729 0)
           (cons 40 0.65616798)
           (cons 1 "28.500")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-100T-TRUCK"))
        (progn
         (entmake)
         (entmake
          (list
           (cons 0 "BLOCK")
           (cons 2 "AASHTO-2011-WB-100T-TRUCK")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4)
           (cons 40 0)
           (cons 41 0)
           (cons 42 0)
           (cons 91 0)
           (list 10 13.3 -4)
           (cons 40 0)
           (cons 41 0)
           (cons 42 0)
           (cons 91 0)
           (list 10 13.3 4)
           (cons 40 0)
           (cons 41 0)
           (cons 42 0)
           (cons 91 0)
           (list 10 0 4)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.5 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.5 -1.66666667 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 13.3 -1.66666667 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 13.3 1.66666667 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.5 1.66666667 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.5 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 12.8 0 0)
           (cons 40 1.14285714)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 13.60812204 -0.80812204 0)
           (list 11 13.60812204 0.80812204 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.63333333 -2.34333333)
           (cons 40 0)
           (cons 41 0)
           (cons 42 0)
           (cons 91 0)
           (list 10 11.63333333 -1.82333333)
           (cons 40 0)
           (cons 41 0)
           (cons 42 0)
           (cons 91 0)
           (list 10 12.1 -1.66666667)
           (cons 40 0)
           (cons 41 0)
           (cons 42 0)
           (cons 91 0)
           (list 10 14.5 -1.66666667)
           (cons 40 0)
           (cons 41 0)
           (cons 42 0)
           (cons 91 0)
           (list 10 14.96666667 -1.82333333)
           (cons 40 0)
           (cons 41 0)
           (cons 42 0)
           (cons 91 0)
           (list 10 14.96666667 -2.34333333)
           (cons 40 0)
           (cons 41 0)
           (cons 42 0)
           (cons 91 0)
           (list 10 14.5 -2.5)
           (cons 40 0)
           (cons 41 0)
           (cons 42 0)
           (cons 91 0)
           (list 10 12.1 -2.5)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.63333333 -3.84333333)
           (cons 40 0)
           (cons 41 0)
           (cons 42 0)
           (cons 91 0)
           (list 10 11.63333333 -3.32333333)
           (cons 40 0)
           (cons 41 0)
           (cons 42 0)
           (cons 91 0)
           (list 10 12.1 -3.16666667)
           (cons 40 0)
           (cons 41 0)
           (cons 42 0)
           (cons 91 0)
           (list 10 14.5 -3.16666667)
           (cons 40 0)
           (cons 41 0)
           (cons 42 0)
           (cons 91 0)
           (list 10 14.96666667 -3.32333333)
           (cons 40 0)
           (cons 41 0)
           (cons 42 0)
           (cons 91 0)
           (list 10 14.96666667 -3.84333333)
           (cons 40 0)
           (cons 41 0)
           (cons 42 0)
           (cons 91 0)
           (list 10 14.5 -4)
           (cons 40 0)
           (cons 41 0)
           (cons 42 0)
           (cons 91 0)
           (list 10 12.1 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.63333333 1.82333333)
           (cons 40 0)
           (cons 41 0)
           (cons 42 0)
           (cons 91 0)
           (list 10 11.63333333 2.34333333)
           (cons 40 0)
           (cons 41 0)
           (cons 42 0)
           (cons 91 0)
           (list 10 12.1 2.5)
           (cons 40 0)
           (cons 41 0)
           (cons 42 0)
           (cons 91 0)
           (list 10 14.5 2.5)
           (cons 40 0)
           (cons 41 0)
           (cons 42 0)
           (cons 91 0)
           (list 10 14.96666667 2.34333333)
           (cons 40 0)
           (cons 41 0)
           (cons 42 0)
           (cons 91 0)
           (list 10 14.96666667 1.82333333)
           (cons 40 0)
           (cons 41 0)
           (cons 42 0)
           (cons 91 0)
           (list 10 14.5 1.66666667)
           (cons 40 0)
           (cons 41 0)
           (cons 42 0)
           (cons 91 0)
           (list 10 12.1 1.66666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.63333333 3.32333333)
           (cons 40 0)
           (cons 41 0)
           (cons 42 0)
           (cons 91 0)
           (list 10 11.63333333 3.84333333)
           (cons 40 0)
           (cons 41 0)
           (cons 42 0)
           (cons 91 0)
           (list 10 12.1 4)
           (cons 40 0)
           (cons 41 0)
           (cons 42 0)
           (cons 91 0)
           (list 10 14.5 4)
           (cons 40 0)
           (cons 41 0)
           (cons 42 0)
           (cons 91 0)
           (list 10 14.96666667 3.84333333)
           (cons 40 0)
           (cons 41 0)
           (cons 42 0)
           (cons 91 0)
           (list 10 14.96666667 3.32333333)
           (cons 40 0)
           (cons 41 0)
           (cons 42 0)
           (cons 91 0)
           (list 10 14.5 3.16666667)
           (cons 40 0)
           (cons 41 0)
           (cons 42 0)
           (cons 91 0)
           (list 10 12.1 3.16666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4 0)
           (cons 50 0)
          )
         )
         (entmake
          (list
           (cons 0 "POINT")
           (cons 100 "AcDbEntity")
           (cons 67 0)
           (cons 8 "0")
           (cons 100 "AcDbPoint")
           (list 10 2.3 -4 0)
           (cons 50 0)
          )
         )
         (entmake
          (list
           (cons 0 "POINT")
           (cons 100 "AcDbEntity")
           (cons 67 0)
           (cons 8 "0")
           (cons 100 "AcDbPoint")
           (list 10 13.3 -4 0)
           (cons 50 0)
          )
         )
         (entmake
          (list
           (cons 0 "POINT")
           (cons 100 "AcDbEntity")
           (cons 67 0)
           (cons 8 "0")
           (cons 100 "AcDbPoint")
           (list 10 13.3 4 0)
           (cons 50 0)
          )
         )
         (entmake
          (list
           (cons 0 "POINT")
           (cons 100 "AcDbEntity")
           (cons 67 0)
           (cons 8 "0")
           (cons 100 "AcDbPoint")
           (list 10 2.3 4 0)
           (cons 50 0)
          )
         )
         (entmake
          (list
           (cons 0 "POINT")
           (cons 100 "AcDbEntity")
           (cons 67 0)
           (cons 8 "0")
           (cons 100 "AcDbPoint")
           (list 10 0 4 0)
           (cons 50 0)
          )
         )
         (entmake
          (list
           (cons 0 "POINT")
           (cons 100 "AcDbEntity")
           (cons 67 0)
           (cons 8 "0")
           (cons 100 "AcDbPoint")
           (list 10 12.8 0 0)
           (cons 50 0)
          )
         )
         (entmake
          (list
           (cons 0 "POINT")
           (cons 100 "AcDbEntity")
           (cons 67 0)
           (cons 8 "0")
           (cons 100 "AcDbPoint")
           (list 10 2.3 0 0)
           (cons 50 0)
          )
         )
         (entmake
          (list
           (cons 0 "INSERT")
           (cons 100 "AcDbEntity")
           (cons 67 0)
           (cons 8 "0")
           (cons 100 "AcDbBlockReference")
           (cons 2 "WheelLeft2")
           (list 10 2.3 -3.16666667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRight2")
           (list 10 2.3 3.16666667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 0.0328084 1.85914261 0)
           (cons 40 0.65616798)
           (cons 1 "2.300")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.0328084 0.76552931 0)
           (cons 40 0.65616798)
           (cons 1 "2.300")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.0328084 -0.32808399 0)
           (cons 40 0.65616798)
           (cons 1 "13.300")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.0328084 -1.42169729 0)
           (cons 40 0.65616798)
           (cons 1 "12.800")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.0328084 -2.51531059 0)
           (cons 40 0.65616798)
           (cons 1 "15.6")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-92D-TRAILER2"))
        (progn
         (entmake)
         (entmake
          (list
           (cons 0 "BLOCK")
           (cons 2 "AASHTO-2011-WB-92D-TRAILER2")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 28.5 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 28.5 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 2.5 0 0)
           (cons 40 0.56666667)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 -2.59333333)
           (cons 40 0)
           (cons 41 0)
           (cons 42 0)
           (cons 91 0)
           (list 10 23.83333333 -2.07333333)
           (cons 40 0)
           (cons 41 0)
           (cons 42 0)
           (cons 91 0)
           (list 10 24.3 -1.91666667)
           (cons 40 0)
           (cons 41 0)
           (cons 42 0)
           (cons 91 0)
           (list 10 26.7 -1.91666667)
           (cons 40 0)
           (cons 41 0)
           (cons 42 0)
           (cons 91 0)
           (list 10 27.16666667 -2.07333333)
           (cons 40 0)
           (cons 41 0)
           (cons 42 0)
           (cons 91 0)
           (list 10 27.16666667 -2.59333333)
           (cons 40 0)
           (cons 41 0)
           (cons 42 0)
           (cons 91 0)
           (list 10 26.7 -2.75)
           (cons 40 0)
           (cons 41 0)
           (cons 42 0)
           (cons 91 0)
           (list 10 24.3 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 -4.09333333)
           (cons 40 0)
           (cons 41 0)
           (cons 42 0)
           (cons 91 0)
           (list 10 23.83333333 -3.57333333)
           (cons 40 0)
           (cons 41 0)
           (cons 42 0)
           (cons 91 0)
           (list 10 24.3 -3.41666667)
           (cons 40 0)
           (cons 41 0)
           (cons 42 0)
           (cons 91 0)
           (list 10 26.7 -3.41666667)
           (cons 40 0)
           (cons 41 0)
           (cons 42 0)
           (cons 91 0)
           (list 10 27.16666667 -3.57333333)
           (cons 40 0)
           (cons 41 0)
           (cons 42 0)
           (cons 91 0)
           (list 10 27.16666667 -4.09333333)
           (cons 40 0)
           (cons 41 0)
           (cons 42 0)
           (cons 91 0)
           (list 10 26.7 -4.25)
           (cons 40 0)
           (cons 41 0)
           (cons 42 0)
           (cons 91 0)
           (list 10 24.3 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 2.07333333)
           (cons 40 0)
           (cons 41 0)
           (cons 42 0)
           (cons 91 0)
           (list 10 23.83333333 2.59333333)
           (cons 40 0)
           (cons 41 0)
           (cons 42 0)
           (cons 91 0)
           (list 10 24.3 2.75)
           (cons 40 0)
           (cons 41 0)
           (cons 42 0)
           (cons 91 0)
           (list 10 26.7 2.75)
           (cons 40 0)
           (cons 41 0)
           (cons 42 0)
           (cons 91 0)
           (list 10 27.16666667 2.59333333)
           (cons 40 0)
           (cons 41 0)
           (cons 42 0)
           (cons 91 0)
           (list 10 27.16666667 2.07333333)
           (cons 40 0)
           (cons 41 0)
           (cons 42 0)
           (cons 91 0)
           (list 10 26.7 1.91666667)
           (cons 40 0)
           (cons 41 0)
           (cons 42 0)
           (cons 91 0)
           (list 10 24.3 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 3.57333333)
           (cons 40 0)
           (cons 41 0)
           (cons 42 0)
           (cons 91 0)
           (list 10 23.83333333 4.09333333)
           (cons 40 0)
           (cons 41 0)
           (cons 42 0)
           (cons 91 0)
           (list 10 24.3 4.25)
           (cons 40 0)
           (cons 41 0)
           (cons 42 0)
           (cons 91 0)
           (list 10 26.7 4.25)
           (cons 40 0)
           (cons 41 0)
           (cons 42 0)
           (cons 91 0)
           (list 10 27.16666667 4.09333333)
           (cons 40 0)
           (cons 41 0)
           (cons 42 0)
           (cons 91 0)
           (list 10 27.16666667 3.57333333)
           (cons 40 0)
           (cons 41 0)
           (cons 42 0)
           (cons 91 0)
           (list 10 26.7 3.41666667)
           (cons 40 0)
           (cons 41 0)
           (cons 42 0)
           (cons 91 0)
           (list 10 24.3 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4.25 0)
           (cons 50 0)
          )
         )
         (entmake
          (list
           (cons 0 "POINT")
           (cons 100 "AcDbEntity")
           (cons 67 0)
           (cons 8 "0")
           (cons 100 "AcDbPoint")
           (list 10 25.5 -4.25 0)
           (cons 50 0)
          )
         )
         (entmake
          (list
           (cons 0 "POINT")
           (cons 100 "AcDbEntity")
           (cons 67 0)
           (cons 8 "0")
           (cons 100 "AcDbPoint")
           (list 10 28.5 -4.25 0)
           (cons 50 0)
          )
         )
         (entmake
          (list
           (cons 0 "POINT")
           (cons 100 "AcDbEntity")
           (cons 67 0)
           (cons 8 "0")
           (cons 100 "AcDbPoint")
           (list 10 28.5 4.25 0)
           (cons 50 0)
          )
         )
         (entmake
          (list
           (cons 0 "POINT")
           (cons 100 "AcDbEntity")
           (cons 67 0)
           (cons 8 "0")
           (cons 100 "AcDbPoint")
           (list 10 25.5 4.25 0)
           (cons 50 0)
          )
         )
         (entmake
          (list
           (cons 0 "POINT")
           (cons 100 "AcDbEntity")
           (cons 67 0)
           (cons 8 "0")
           (cons 100 "AcDbPoint")
           (list 10 0 4.25 0)
           (cons 50 0)
          )
         )
         (entmake
          (list
           (cons 0 "POINT")
           (cons 100 "AcDbEntity")
           (cons 67 0)
           (cons 8 "0")
           (cons 100 "AcDbPoint")
           (list 10 2.5 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4.25)
           (cons 40 0)
           (cons 41 0)
           (cons 42 0)
           (cons 91 0)
           (list 10 28.5 -4.25)
           (cons 40 0)
           (cons 41 0)
           (cons 42 0)
           (cons 91 0)
           (list 10 28.5 4.25)
           (cons 40 0)
           (cons 41 0)
           (cons 42 0)
           (cons 91 0)
           (list 10 0 4.25)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.20341207 1.85914261 0)
           (cons 40 0.65616798)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 0.76552931 0)
           (cons 40 0.65616798)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -0.32808399 0)
           (cons 40 0.65616798)
           (cons 1 "25.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-92D-PUP"))
        (progn
         (entmake)
         (entmake
          (list
           (cons 0 "BLOCK")
           (cons 2 "AASHTO-2011-WB-92D-PUP")
           (cons 70 2)
           (cons 4 "")
           (list 10 0 0 0)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 7 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.56666667)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.33333333 -2.59333333)
           (cons 40 0)
           (cons 41 0)
           (cons 42 0)
           (cons 91 0)
           (list 10 5.33333333 -2.07333333)
           (cons 40 0)
           (cons 41 0)
           (cons 42 0)
           (cons 91 0)
           (list 10 5.8 -1.91666667)
           (cons 40 0)
           (cons 41 0)
           (cons 42 0)
           (cons 91 0)
           (list 10 8.2 -1.91666667)
           (cons 40 0)
           (cons 41 0)
           (cons 42 0)
           (cons 91 0)
           (list 10 8.66666667 -2.07333333)
           (cons 40 0)
           (cons 41 0)
           (cons 42 0)
           (cons 91 0)
           (list 10 8.66666667 -2.59333333)
           (cons 40 0)
           (cons 41 0)
           (cons 42 0)
           (cons 91 0)
           (list 10 8.2 -2.75)
           (cons 40 0)
           (cons 41 0)
           (cons 42 0)
           (cons 91 0)
           (list 10 5.8 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.33333333 -4.09333333)
           (cons 40 0)
           (cons 41 0)
           (cons 42 0)
           (cons 91 0)
           (list 10 5.33333333 -3.57333333)
           (cons 40 0)
           (cons 41 0)
           (cons 42 0)
           (cons 91 0)
           (list 10 5.8 -3.41666667)
           (cons 40 0)
           (cons 41 0)
           (cons 42 0)
           (cons 91 0)
           (list 10 8.2 -3.41666667)
           (cons 40 0)
           (cons 41 0)
           (cons 42 0)
           (cons 91 0)
           (list 10 8.66666667 -3.57333333)
           (cons 40 0)
           (cons 41 0)
           (cons 42 0)
           (cons 91 0)
           (list 10 8.66666667 -4.09333333)
           (cons 40 0)
           (cons 41 0)
           (cons 42 0)
           (cons 91 0)
           (list 10 8.2 -4.25)
           (cons 40 0)
           (cons 41 0)
           (cons 42 0)
           (cons 91 0)
           (list 10 5.8 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.33333333 2.07333333)
           (cons 40 0)
           (cons 41 0)
           (cons 42 0)
           (cons 91 0)
           (list 10 5.33333333 2.59333333)
           (cons 40 0)
           (cons 41 0)
           (cons 42 0)
           (cons 91 0)
           (list 10 5.8 2.75)
           (cons 40 0)
           (cons 41 0)
           (cons 42 0)
           (cons 91 0)
           (list 10 8.2 2.75)
           (cons 40 0)
           (cons 41 0)
           (cons 42 0)
           (cons 91 0)
           (list 10 8.66666667 2.59333333)
           (cons 40 0)
           (cons 41 0)
           (cons 42 0)
           (cons 91 0)
           (list 10 8.66666667 2.07333333)
           (cons 40 0)
           (cons 41 0)
           (cons 42 0)
           (cons 91 0)
           (list 10 8.2 1.91666667)
           (cons 40 0)
           (cons 41 0)
           (cons 42 0)
           (cons 91 0)
           (list 10 5.8 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.33333333 3.57333333)
           (cons 40 0)
           (cons 41 0)
           (cons 42 0)
           (cons 91 0)
           (list 10 5.33333333 4.09333333)
           (cons 40 0)
           (cons 41 0)
           (cons 42 0)
           (cons 91 0)
           (list 10 5.8 4.25)
           (cons 40 0)
           (cons 41 0)
           (cons 42 0)
           (cons 91 0)
           (list 10 8.2 4.25)
           (cons 40 0)
           (cons 41 0)
           (cons 42 0)
           (cons 91 0)
           (list 10 8.66666667 4.09333333)
           (cons 40 0)
           (cons 41 0)
           (cons 42 0)
           (cons 91 0)
           (list 10 8.66666667 3.57333333)
           (cons 40 0)
           (cons 41 0)
           (cons 42 0)
           (cons 91 0)
           (list 10 8.2 3.41666667)
           (cons 40 0)
           (cons 41 0)
           (cons 42 0)
           (cons 91 0)
           (list 10 5.8 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 7 -4.25 0)
           (cons 50 0)
          )
         )
         (entmake
          (list
           (cons 0 "POINT")
           (cons 100 "AcDbEntity")
           (cons 67 0)
           (cons 8 "0")
           (cons 100 "AcDbPoint")
           (list 10 7 4.25 0)
           (cons 50 0)
          )
         )
         (entmake
          (list
           (cons 0 "POINT")
           (cons 100 "AcDbEntity")
           (cons 67 0)
           (cons 8 "0")
           (cons 100 "AcDbPoint")
           (list 10 7 0 0)
           (cons 50 0)
          )
         )
         (entmake
          (list
           (cons 0 "LWPOLYLINE")
           (cons 100 "AcDbEntity")
           (cons 67 0)
           (cons 8 "Defpoints")
           (cons 100 "AcDbPolyline")
           (cons 90 3)
           (cons 70 1)
           (cons 43 0)
           (cons 38 0)
           (cons 39 0)
           (list 10 0 0)
           (cons 40 0)
           (cons 41 0)
           (cons 42 0)
           (cons 91 0)
           (list 10 7 4.25)
           (cons 40 0)
           (cons 41 0)
           (cons 42 0)
           (cons 91 0)
           (list 10 7 -4.25)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 -2.29658793 1.85914261 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 0.76552931 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -0.32808399 0)
           (cons 40 0.65616798)
           (cons 1 "7.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -1.42169729 0)
           (cons 40 0.65616798)
           (cons 1 "7.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-92D-TRAILER1"))
        (progn
         (entmake)
         (entmake
          (list
           (cons 0 "BLOCK")
           (cons 2 "AASHTO-2011-WB-92D-TRAILER1")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 48 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 48 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 48 0 0)
           (list 11 48 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 48 0 0)
           (cons 40 0.33333333)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 3 0 0)
           (cons 40 0.34)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 39.75 -2.59333333)
           (cons 40 0)
           (cons 41 0)
           (cons 42 0)
           (cons 91 0)
           (list 10 39.75 -2.07333333)
           (cons 40 0)
           (cons 41 0)
           (cons 42 0)
           (cons 91 0)
           (list 10 40.21666667 -1.91666667)
           (cons 40 0)
           (cons 41 0)
           (cons 42 0)
           (cons 91 0)
           (list 10 42.61666667 -1.91666667)
           (cons 40 0)
           (cons 41 0)
           (cons 42 0)
           (cons 91 0)
           (list 10 43.08333333 -2.07333333)
           (cons 40 0)
           (cons 41 0)
           (cons 42 0)
           (cons 91 0)
           (list 10 43.08333333 -2.59333333)
           (cons 40 0)
           (cons 41 0)
           (cons 42 0)
           (cons 91 0)
           (list 10 42.61666667 -2.75)
           (cons 40 0)
           (cons 41 0)
           (cons 42 0)
           (cons 91 0)
           (list 10 40.21666667 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 39.75 -4.09333333)
           (cons 40 0)
           (cons 41 0)
           (cons 42 0)
           (cons 91 0)
           (list 10 39.75 -3.57333333)
           (cons 40 0)
           (cons 41 0)
           (cons 42 0)
           (cons 91 0)
           (list 10 40.21666667 -3.41666667)
           (cons 40 0)
           (cons 41 0)
           (cons 42 0)
           (cons 91 0)
           (list 10 42.61666667 -3.41666667)
           (cons 40 0)
           (cons 41 0)
           (cons 42 0)
           (cons 91 0)
           (list 10 43.08333333 -3.57333333)
           (cons 40 0)
           (cons 41 0)
           (cons 42 0)
           (cons 91 0)
           (list 10 43.08333333 -4.09333333)
           (cons 40 0)
           (cons 41 0)
           (cons 42 0)
           (cons 91 0)
           (list 10 42.61666667 -4.25)
           (cons 40 0)
           (cons 41 0)
           (cons 42 0)
           (cons 91 0)
           (list 10 40.21666667 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 39.75 2.07333333)
           (cons 40 0)
           (cons 41 0)
           (cons 42 0)
           (cons 91 0)
           (list 10 39.75 2.59333333)
           (cons 40 0)
           (cons 41 0)
           (cons 42 0)
           (cons 91 0)
           (list 10 40.21666667 2.75)
           (cons 40 0)
           (cons 41 0)
           (cons 42 0)
           (cons 91 0)
           (list 10 42.61666667 2.75)
           (cons 40 0)
           (cons 41 0)
           (cons 42 0)
           (cons 91 0)
           (list 10 43.08333333 2.59333333)
           (cons 40 0)
           (cons 41 0)
           (cons 42 0)
           (cons 91 0)
           (list 10 43.08333333 2.07333333)
           (cons 40 0)
           (cons 41 0)
           (cons 42 0)
           (cons 91 0)
           (list 10 42.61666667 1.91666667)
           (cons 40 0)
           (cons 41 0)
           (cons 42 0)
           (cons 91 0)
           (list 10 40.21666667 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 39.75 3.57333333)
           (cons 40 0)
           (cons 41 0)
           (cons 42 0)
           (cons 91 0)
           (list 10 39.75 4.09333333)
           (cons 40 0)
           (cons 41 0)
           (cons 42 0)
           (cons 91 0)
           (list 10 40.21666667 4.25)
           (cons 40 0)
           (cons 41 0)
           (cons 42 0)
           (cons 91 0)
           (list 10 42.61666667 4.25)
           (cons 40 0)
           (cons 41 0)
           (cons 42 0)
           (cons 91 0)
           (list 10 43.08333333 4.09333333)
           (cons 40 0)
           (cons 41 0)
           (cons 42 0)
           (cons 91 0)
           (list 10 43.08333333 3.57333333)
           (cons 40 0)
           (cons 41 0)
           (cons 42 0)
           (cons 91 0)
           (list 10 42.61666667 3.41666667)
           (cons 40 0)
           (cons 41 0)
           (cons 42 0)
           (cons 91 0)
           (list 10 40.21666667 3.41666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 43.91666667 -2.59333333)
           (cons 40 0)
           (cons 41 0)
           (cons 42 0)
           (cons 91 0)
           (list 10 43.91666667 -2.07333333)
           (cons 40 0)
           (cons 41 0)
           (cons 42 0)
           (cons 91 0)
           (list 10 44.38333333 -1.91666667)
           (cons 40 0)
           (cons 41 0)
           (cons 42 0)
           (cons 91 0)
           (list 10 46.78333333 -1.91666667)
           (cons 40 0)
           (cons 41 0)
           (cons 42 0)
           (cons 91 0)
           (list 10 47.25 -2.07333333)
           (cons 40 0)
           (cons 41 0)
           (cons 42 0)
           (cons 91 0)
           (list 10 47.25 -2.59333333)
           (cons 40 0)
           (cons 41 0)
           (cons 42 0)
           (cons 91 0)
           (list 10 46.78333333 -2.75)
           (cons 40 0)
           (cons 41 0)
           (cons 42 0)
           (cons 91 0)
           (list 10 44.38333333 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 43.91666667 -4.09333333)
           (cons 40 0)
           (cons 41 0)
           (cons 42 0)
           (cons 91 0)
           (list 10 43.91666667 -3.57333333)
           (cons 40 0)
           (cons 41 0)
           (cons 42 0)
           (cons 91 0)
           (list 10 44.38333333 -3.41666667)
           (cons 40 0)
           (cons 41 0)
           (cons 42 0)
           (cons 91 0)
           (list 10 46.78333333 -3.41666667)
           (cons 40 0)
           (cons 41 0)
           (cons 42 0)
           (cons 91 0)
           (list 10 47.25 -3.57333333)
           (cons 40 0)
           (cons 41 0)
           (cons 42 0)
           (cons 91 0)
           (list 10 47.25 -4.09333333)
           (cons 40 0)
           (cons 41 0)
           (cons 42 0)
           (cons 91 0)
           (list 10 46.78333333 -4.25)
           (cons 40 0)
           (cons 41 0)
           (cons 42 0)
           (cons 91 0)
           (list 10 44.38333333 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 43.91666667 2.07333333)
           (cons 40 0)
           (cons 41 0)
           (cons 42 0)
           (cons 91 0)
           (list 10 43.91666667 2.59333333)
           (cons 40 0)
           (cons 41 0)
           (cons 42 0)
           (cons 91 0)
           (list 10 44.38333333 2.75)
           (cons 40 0)
           (cons 41 0)
           (cons 42 0)
           (cons 91 0)
           (list 10 46.78333333 2.75)
           (cons 40 0)
           (cons 41 0)
           (cons 42 0)
           (cons 91 0)
           (list 10 47.25 2.59333333)
           (cons 40 0)
           (cons 41 0)
           (cons 42 0)
           (cons 91 0)
           (list 10 47.25 2.07333333)
           (cons 40 0)
           (cons 41 0)
           (cons 42 0)
           (cons 91 0)
           (list 10 46.78333333 1.91666667)
           (cons 40 0)
           (cons 41 0)
           (cons 42 0)
           (cons 91 0)
           (list 10 44.38333333 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 43.91666667 3.57333333)
           (cons 40 0)
           (cons 41 0)
           (cons 42 0)
           (cons 91 0)
           (list 10 43.91666667 4.09333333)
           (cons 40 0)
           (cons 41 0)
           (cons 42 0)
           (cons 91 0)
           (list 10 44.38333333 4.25)
           (cons 40 0)
           (cons 41 0)
           (cons 42 0)
           (cons 91 0)
           (list 10 46.78333333 4.25)
           (cons 40 0)
           (cons 41 0)
           (cons 42 0)
           (cons 91 0)
           (list 10 47.25 4.09333333)
           (cons 40 0)
           (cons 41 0)
           (cons 42 0)
           (cons 91 0)
           (list 10 47.25 3.57333333)
           (cons 40 0)
           (cons 41 0)
           (cons 42 0)
           (cons 91 0)
           (list 10 46.78333333 3.41666667)
           (cons 40 0)
           (cons 41 0)
           (cons 42 0)
           (cons 91 0)
           (list 10 44.38333333 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 3 0 0)
           (cons 50 0)
          )
         )
         (entmake
          (list
           (cons 0 "POINT")
           (cons 100 "AcDbEntity")
           (cons 67 0)
           (cons 8 "0")
           (cons 100 "AcDbPoint")
           (list 10 48 0 0)
           (cons 50 0)
          )
         )
         (entmake
          (list
           (cons 0 "POINT")
           (cons 100 "AcDbEntity")
           (cons 67 0)
           (cons 8 "0")
           (cons 100 "AcDbPoint")
           (list 10 43.5 4.25 0)
           (cons 50 0)
          )
         )
         (entmake
          (list
           (cons 0 "POINT")
           (cons 100 "AcDbEntity")
           (cons 67 0)
           (cons 8 "0")
           (cons 100 "AcDbPoint")
           (list 10 43.5 -4.25 0)
           (cons 50 0)
          )
         )
         (entmake
          (list
           (cons 0 "POINT")
           (cons 100 "AcDbEntity")
           (cons 67 0)
           (cons 8 "0")
           (cons 100 "AcDbPoint")
           (list 10 0 -4.25 0)
           (cons 50 0)
          )
         )
         (entmake
          (list
           (cons 0 "POINT")
           (cons 100 "AcDbEntity")
           (cons 67 0)
           (cons 8 "0")
           (cons 100 "AcDbPoint")
           (list 10 0 4.25 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4.25)
           (cons 40 0)
           (cons 41 0)
           (cons 42 0)
           (cons 91 0)
           (list 10 48 -4.25)
           (cons 40 0)
           (cons 41 0)
           (cons 42 0)
           (cons 91 0)
           (list 10 48 4.25)
           (cons 40 0)
           (cons 41 0)
           (cons 42 0)
           (cons 91 0)
           (list 10 0 4.25)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 48 4.25 0)
           (cons 50 0)
          )
         )
         (entmake
          (list
           (cons 0 "POINT")
           (cons 100 "AcDbEntity")
           (cons 67 0)
           (cons 8 "0")
           (cons 100 "AcDbPoint")
           (list 10 48 -4.25 0)
           (cons 50 0)
          )
         )
         (entmake
          (list
           (cons 0 "ATTDEF")
           (cons 100 "AcDbEntity")
           (cons 67 0)
           (cons 8 "0")
           (cons 100 "AcDbText")
           (list 10 0.70341207 1.85914261 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 0.76552931 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -0.32808399 0)
           (cons 40 0.65616798)
           (cons 1 "43.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -1.42169729 0)
           (cons 40 0.65616798)
           (cons 1 "48.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-92D-TRUCK"))
        (progn
         (entmake)
         (entmake
          (list
           (cons 0 "BLOCK")
           (cons 2 "AASHTO-2011-WB-92D-TRUCK")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.5 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.5 -1.66666667 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 21.9 -1.66666667 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 21.9 1.66666667 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.5 1.66666667 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.5 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 19.3 0 0)
           (cons 40 1.14285714)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 20.10812204 -0.80812204 0)
           (list 11 20.10812204 0.80812204 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 16.03333333 -2.34333333)
           (cons 40 0)
           (cons 41 0)
           (cons 42 0)
           (cons 91 0)
           (list 10 16.03333333 -1.82333333)
           (cons 40 0)
           (cons 41 0)
           (cons 42 0)
           (cons 91 0)
           (list 10 16.5 -1.66666667)
           (cons 40 0)
           (cons 41 0)
           (cons 42 0)
           (cons 91 0)
           (list 10 18.9 -1.66666667)
           (cons 40 0)
           (cons 41 0)
           (cons 42 0)
           (cons 91 0)
           (list 10 19.36666667 -1.82333333)
           (cons 40 0)
           (cons 41 0)
           (cons 42 0)
           (cons 91 0)
           (list 10 19.36666667 -2.34333333)
           (cons 40 0)
           (cons 41 0)
           (cons 42 0)
           (cons 91 0)
           (list 10 18.9 -2.5)
           (cons 40 0)
           (cons 41 0)
           (cons 42 0)
           (cons 91 0)
           (list 10 16.5 -2.5)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 16.03333333 -3.84333333)
           (cons 40 0)
           (cons 41 0)
           (cons 42 0)
           (cons 91 0)
           (list 10 16.03333333 -3.32333333)
           (cons 40 0)
           (cons 41 0)
           (cons 42 0)
           (cons 91 0)
           (list 10 16.5 -3.16666667)
           (cons 40 0)
           (cons 41 0)
           (cons 42 0)
           (cons 91 0)
           (list 10 18.9 -3.16666667)
           (cons 40 0)
           (cons 41 0)
           (cons 42 0)
           (cons 91 0)
           (list 10 19.36666667 -3.32333333)
           (cons 40 0)
           (cons 41 0)
           (cons 42 0)
           (cons 91 0)
           (list 10 19.36666667 -3.84333333)
           (cons 40 0)
           (cons 41 0)
           (cons 42 0)
           (cons 91 0)
           (list 10 18.9 -4)
           (cons 40 0)
           (cons 41 0)
           (cons 42 0)
           (cons 91 0)
           (list 10 16.5 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 16.03333333 1.82333333)
           (cons 40 0)
           (cons 41 0)
           (cons 42 0)
           (cons 91 0)
           (list 10 16.03333333 2.34333333)
           (cons 40 0)
           (cons 41 0)
           (cons 42 0)
           (cons 91 0)
           (list 10 16.5 2.5)
           (cons 40 0)
           (cons 41 0)
           (cons 42 0)
           (cons 91 0)
           (list 10 18.9 2.5)
           (cons 40 0)
           (cons 41 0)
           (cons 42 0)
           (cons 91 0)
           (list 10 19.36666667 2.34333333)
           (cons 40 0)
           (cons 41 0)
           (cons 42 0)
           (cons 91 0)
           (list 10 19.36666667 1.82333333)
           (cons 40 0)
           (cons 41 0)
           (cons 42 0)
           (cons 91 0)
           (list 10 18.9 1.66666667)
           (cons 40 0)
           (cons 41 0)
           (cons 42 0)
           (cons 91 0)
           (list 10 16.5 1.66666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 16.03333333 3.32333333)
           (cons 40 0)
           (cons 41 0)
           (cons 42 0)
           (cons 91 0)
           (list 10 16.03333333 3.84333333)
           (cons 40 0)
           (cons 41 0)
           (cons 42 0)
           (cons 91 0)
           (list 10 16.5 4)
           (cons 40 0)
           (cons 41 0)
           (cons 42 0)
           (cons 91 0)
           (list 10 18.9 4)
           (cons 40 0)
           (cons 41 0)
           (cons 42 0)
           (cons 91 0)
           (list 10 19.36666667 3.84333333)
           (cons 40 0)
           (cons 41 0)
           (cons 42 0)
           (cons 91 0)
           (list 10 19.36666667 3.32333333)
           (cons 40 0)
           (cons 41 0)
           (cons 42 0)
           (cons 91 0)
           (list 10 18.9 3.16666667)
           (cons 40 0)
           (cons 41 0)
           (cons 42 0)
           (cons 91 0)
           (list 10 16.5 3.16666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 20.23333333 -2.34333333)
           (cons 40 0)
           (cons 41 0)
           (cons 42 0)
           (cons 91 0)
           (list 10 20.23333333 -1.82333333)
           (cons 40 0)
           (cons 41 0)
           (cons 42 0)
           (cons 91 0)
           (list 10 20.7 -1.66666667)
           (cons 40 0)
           (cons 41 0)
           (cons 42 0)
           (cons 91 0)
           (list 10 23.1 -1.66666667)
           (cons 40 0)
           (cons 41 0)
           (cons 42 0)
           (cons 91 0)
           (list 10 23.56666667 -1.82333333)
           (cons 40 0)
           (cons 41 0)
           (cons 42 0)
           (cons 91 0)
           (list 10 23.56666667 -2.34333333)
           (cons 40 0)
           (cons 41 0)
           (cons 42 0)
           (cons 91 0)
           (list 10 23.1 -2.5)
           (cons 40 0)
           (cons 41 0)
           (cons 42 0)
           (cons 91 0)
           (list 10 20.7 -2.5)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 20.23333333 -3.84333333)
           (cons 40 0)
           (cons 41 0)
           (cons 42 0)
           (cons 91 0)
           (list 10 20.23333333 -3.32333333)
           (cons 40 0)
           (cons 41 0)
           (cons 42 0)
           (cons 91 0)
           (list 10 20.7 -3.16666667)
           (cons 40 0)
           (cons 41 0)
           (cons 42 0)
           (cons 91 0)
           (list 10 23.1 -3.16666667)
           (cons 40 0)
           (cons 41 0)
           (cons 42 0)
           (cons 91 0)
           (list 10 23.56666667 -3.32333333)
           (cons 40 0)
           (cons 41 0)
           (cons 42 0)
           (cons 91 0)
           (list 10 23.56666667 -3.84333333)
           (cons 40 0)
           (cons 41 0)
           (cons 42 0)
           (cons 91 0)
           (list 10 23.1 -4)
           (cons 40 0)
           (cons 41 0)
           (cons 42 0)
           (cons 91 0)
           (list 10 20.7 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 20.23333333 1.82333333)
           (cons 40 0)
           (cons 41 0)
           (cons 42 0)
           (cons 91 0)
           (list 10 20.23333333 2.34333333)
           (cons 40 0)
           (cons 41 0)
           (cons 42 0)
           (cons 91 0)
           (list 10 20.7 2.5)
           (cons 40 0)
           (cons 41 0)
           (cons 42 0)
           (cons 91 0)
           (list 10 23.1 2.5)
           (cons 40 0)
           (cons 41 0)
           (cons 42 0)
           (cons 91 0)
           (list 10 23.56666667 2.34333333)
           (cons 40 0)
           (cons 41 0)
           (cons 42 0)
           (cons 91 0)
           (list 10 23.56666667 1.82333333)
           (cons 40 0)
           (cons 41 0)
           (cons 42 0)
           (cons 91 0)
           (list 10 23.1 1.66666667)
           (cons 40 0)
           (cons 41 0)
           (cons 42 0)
           (cons 91 0)
           (list 10 20.7 1.66666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 20.23333333 3.32333333)
           (cons 40 0)
           (cons 41 0)
           (cons 42 0)
           (cons 91 0)
           (list 10 20.23333333 3.84333333)
           (cons 40 0)
           (cons 41 0)
           (cons 42 0)
           (cons 91 0)
           (list 10 20.7 4)
           (cons 40 0)
           (cons 41 0)
           (cons 42 0)
           (cons 91 0)
           (list 10 23.1 4)
           (cons 40 0)
           (cons 41 0)
           (cons 42 0)
           (cons 91 0)
           (list 10 23.56666667 3.84333333)
           (cons 40 0)
           (cons 41 0)
           (cons 42 0)
           (cons 91 0)
           (list 10 23.56666667 3.32333333)
           (cons 40 0)
           (cons 41 0)
           (cons 42 0)
           (cons 91 0)
           (list 10 23.1 3.16666667)
           (cons 40 0)
           (cons 41 0)
           (cons 42 0)
           (cons 91 0)
           (list 10 20.7 3.16666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4 0)
           (cons 50 0)
          )
         )
         (entmake
          (list
           (cons 0 "POINT")
           (cons 100 "AcDbEntity")
           (cons 67 0)
           (cons 8 "0")
           (cons 100 "AcDbPoint")
           (list 10 2.3 -4 0)
           (cons 50 0)
          )
         )
         (entmake
          (list
           (cons 0 "POINT")
           (cons 100 "AcDbEntity")
           (cons 67 0)
           (cons 8 "0")
           (cons 100 "AcDbPoint")
           (list 10 0 4 0)
           (cons 50 0)
          )
         )
         (entmake
          (list
           (cons 0 "POINT")
           (cons 100 "AcDbEntity")
           (cons 67 0)
           (cons 8 "0")
           (cons 100 "AcDbPoint")
           (list 10 2.3 4 0)
           (cons 50 0)
          )
         )
         (entmake
          (list
           (cons 0 "POINT")
           (cons 100 "AcDbEntity")
           (cons 67 0)
           (cons 8 "0")
           (cons 100 "AcDbPoint")
           (list 10 19.3 0 0)
           (cons 50 0)
          )
         )
         (entmake
          (list
           (cons 0 "POINT")
           (cons 100 "AcDbEntity")
           (cons 67 0)
           (cons 8 "0")
           (cons 100 "AcDbPoint")
           (list 10 19.8 4 0)
           (cons 50 0)
          )
         )
         (entmake
          (list
           (cons 0 "POINT")
           (cons 100 "AcDbEntity")
           (cons 67 0)
           (cons 8 "0")
           (cons 100 "AcDbPoint")
           (list 10 19.8 -4 0)
           (cons 50 0)
          )
         )
         (entmake
          (list
           (cons 0 "POINT")
           (cons 100 "AcDbEntity")
           (cons 67 0)
           (cons 8 "0")
           (cons 100 "AcDbPoint")
           (list 10 2.3 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4)
           (cons 40 0)
           (cons 41 0)
           (cons 42 0)
           (cons 91 0)
           (list 10 21.9 -4)
           (cons 40 0)
           (cons 41 0)
           (cons 42 0)
           (cons 91 0)
           (list 10 21.9 4)
           (cons 40 0)
           (cons 41 0)
           (cons 42 0)
           (cons 91 0)
           (list 10 0 4)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelLeft2")
           (list 10 2.3 -3.16666667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRight2")
           (list 10 2.3 3.16666667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 0.0328084 1.85914261 0)
           (cons 40 0.65616798)
           (cons 1 "2.300")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.0328084 0.76552931 0)
           (cons 40 0.65616798)
           (cons 1 "2.300")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.0328084 -0.32808399 0)
           (cons 40 0.65616798)
           (cons 1 "19.800")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.0328084 -1.42169729 0)
           (cons 40 0.65616798)
           (cons 1 "19.300")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.0328084 -2.51531059 0)
           (cons 40 0.65616798)
           (cons 1 "13.0")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-67D-TRAILER2"))
        (progn
         (entmake)
         (entmake
          (list
           (cons 0 "BLOCK")
           (cons 2 "AASHTO-2011-WB-67D-TRAILER2")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 28.5 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 28.5 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 2.5 0 0)
           (cons 40 0.56666667)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 -2.59333333)
           (cons 40 0)
           (cons 41 0)
           (cons 42 0)
           (cons 91 0)
           (list 10 23.83333333 -2.07333333)
           (cons 40 0)
           (cons 41 0)
           (cons 42 0)
           (cons 91 0)
           (list 10 24.3 -1.91666667)
           (cons 40 0)
           (cons 41 0)
           (cons 42 0)
           (cons 91 0)
           (list 10 26.7 -1.91666667)
           (cons 40 0)
           (cons 41 0)
           (cons 42 0)
           (cons 91 0)
           (list 10 27.16666667 -2.07333333)
           (cons 40 0)
           (cons 41 0)
           (cons 42 0)
           (cons 91 0)
           (list 10 27.16666667 -2.59333333)
           (cons 40 0)
           (cons 41 0)
           (cons 42 0)
           (cons 91 0)
           (list 10 26.7 -2.75)
           (cons 40 0)
           (cons 41 0)
           (cons 42 0)
           (cons 91 0)
           (list 10 24.3 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 -4.09333333)
           (cons 40 0)
           (cons 41 0)
           (cons 42 0)
           (cons 91 0)
           (list 10 23.83333333 -3.57333333)
           (cons 40 0)
           (cons 41 0)
           (cons 42 0)
           (cons 91 0)
           (list 10 24.3 -3.41666667)
           (cons 40 0)
           (cons 41 0)
           (cons 42 0)
           (cons 91 0)
           (list 10 26.7 -3.41666667)
           (cons 40 0)
           (cons 41 0)
           (cons 42 0)
           (cons 91 0)
           (list 10 27.16666667 -3.57333333)
           (cons 40 0)
           (cons 41 0)
           (cons 42 0)
           (cons 91 0)
           (list 10 27.16666667 -4.09333333)
           (cons 40 0)
           (cons 41 0)
           (cons 42 0)
           (cons 91 0)
           (list 10 26.7 -4.25)
           (cons 40 0)
           (cons 41 0)
           (cons 42 0)
           (cons 91 0)
           (list 10 24.3 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 2.07333333)
           (cons 40 0)
           (cons 41 0)
           (cons 42 0)
           (cons 91 0)
           (list 10 23.83333333 2.59333333)
           (cons 40 0)
           (cons 41 0)
           (cons 42 0)
           (cons 91 0)
           (list 10 24.3 2.75)
           (cons 40 0)
           (cons 41 0)
           (cons 42 0)
           (cons 91 0)
           (list 10 26.7 2.75)
           (cons 40 0)
           (cons 41 0)
           (cons 42 0)
           (cons 91 0)
           (list 10 27.16666667 2.59333333)
           (cons 40 0)
           (cons 41 0)
           (cons 42 0)
           (cons 91 0)
           (list 10 27.16666667 2.07333333)
           (cons 40 0)
           (cons 41 0)
           (cons 42 0)
           (cons 91 0)
           (list 10 26.7 1.91666667)
           (cons 40 0)
           (cons 41 0)
           (cons 42 0)
           (cons 91 0)
           (list 10 24.3 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 3.57333333)
           (cons 40 0)
           (cons 41 0)
           (cons 42 0)
           (cons 91 0)
           (list 10 23.83333333 4.09333333)
           (cons 40 0)
           (cons 41 0)
           (cons 42 0)
           (cons 91 0)
           (list 10 24.3 4.25)
           (cons 40 0)
           (cons 41 0)
           (cons 42 0)
           (cons 91 0)
           (list 10 26.7 4.25)
           (cons 40 0)
           (cons 41 0)
           (cons 42 0)
           (cons 91 0)
           (list 10 27.16666667 4.09333333)
           (cons 40 0)
           (cons 41 0)
           (cons 42 0)
           (cons 91 0)
           (list 10 27.16666667 3.57333333)
           (cons 40 0)
           (cons 41 0)
           (cons 42 0)
           (cons 91 0)
           (list 10 26.7 3.41666667)
           (cons 40 0)
           (cons 41 0)
           (cons 42 0)
           (cons 91 0)
           (list 10 24.3 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 2.5 0 0)
           (cons 50 0)
          )
         )
         (entmake
          (list
           (cons 0 "POINT")
           (cons 100 "AcDbEntity")
           (cons 67 0)
           (cons 8 "0")
           (cons 100 "AcDbPoint")
           (list 10 0 -4.25 0)
           (cons 50 0)
          )
         )
         (entmake
          (list
           (cons 0 "POINT")
           (cons 100 "AcDbEntity")
           (cons 67 0)
           (cons 8 "0")
           (cons 100 "AcDbPoint")
           (list 10 0 4.25 0)
           (cons 50 0)
          )
         )
         (entmake
          (list
           (cons 0 "POINT")
           (cons 100 "AcDbEntity")
           (cons 67 0)
           (cons 8 "0")
           (cons 100 "AcDbPoint")
           (list 10 25.5 4.25 0)
           (cons 50 0)
          )
         )
         (entmake
          (list
           (cons 0 "POINT")
           (cons 100 "AcDbEntity")
           (cons 67 0)
           (cons 8 "0")
           (cons 100 "AcDbPoint")
           (list 10 28.5 4.25 0)
           (cons 50 0)
          )
         )
         (entmake
          (list
           (cons 0 "POINT")
           (cons 100 "AcDbEntity")
           (cons 67 0)
           (cons 8 "0")
           (cons 100 "AcDbPoint")
           (list 10 28.5 -4.25 0)
           (cons 50 0)
          )
         )
         (entmake
          (list
           (cons 0 "POINT")
           (cons 100 "AcDbEntity")
           (cons 67 0)
           (cons 8 "0")
           (cons 100 "AcDbPoint")
           (list 10 25.5 -4.25 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4.25)
           (cons 40 0)
           (cons 41 0)
           (cons 42 0)
           (cons 91 0)
           (list 10 28.5 -4.25)
           (cons 40 0)
           (cons 41 0)
           (cons 42 0)
           (cons 91 0)
           (list 10 28.5 4.25)
           (cons 40 0)
           (cons 41 0)
           (cons 42 0)
           (cons 91 0)
           (list 10 0 4.25)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.20341207 1.85914261 0)
           (cons 40 0.65616798)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 0.76552931 0)
           (cons 40 0.65616798)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -0.32808399 0)
           (cons 40 0.65616798)
           (cons 1 "25.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-67D-PUP"))
        (progn
         (entmake)
         (entmake
          (list
           (cons 0 "BLOCK")
           (cons 2 "AASHTO-2011-WB-67D-PUP")
           (cons 70 2)
           (cons 4 "")
           (list 10 0 0 0)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 7 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.56666667)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.33333333 -2.59333333)
           (cons 40 0)
           (cons 41 0)
           (cons 42 0)
           (cons 91 0)
           (list 10 5.33333333 -2.07333333)
           (cons 40 0)
           (cons 41 0)
           (cons 42 0)
           (cons 91 0)
           (list 10 5.8 -1.91666667)
           (cons 40 0)
           (cons 41 0)
           (cons 42 0)
           (cons 91 0)
           (list 10 8.2 -1.91666667)
           (cons 40 0)
           (cons 41 0)
           (cons 42 0)
           (cons 91 0)
           (list 10 8.66666667 -2.07333333)
           (cons 40 0)
           (cons 41 0)
           (cons 42 0)
           (cons 91 0)
           (list 10 8.66666667 -2.59333333)
           (cons 40 0)
           (cons 41 0)
           (cons 42 0)
           (cons 91 0)
           (list 10 8.2 -2.75)
           (cons 40 0)
           (cons 41 0)
           (cons 42 0)
           (cons 91 0)
           (list 10 5.8 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.33333333 -4.09333333)
           (cons 40 0)
           (cons 41 0)
           (cons 42 0)
           (cons 91 0)
           (list 10 5.33333333 -3.57333333)
           (cons 40 0)
           (cons 41 0)
           (cons 42 0)
           (cons 91 0)
           (list 10 5.8 -3.41666667)
           (cons 40 0)
           (cons 41 0)
           (cons 42 0)
           (cons 91 0)
           (list 10 8.2 -3.41666667)
           (cons 40 0)
           (cons 41 0)
           (cons 42 0)
           (cons 91 0)
           (list 10 8.66666667 -3.57333333)
           (cons 40 0)
           (cons 41 0)
           (cons 42 0)
           (cons 91 0)
           (list 10 8.66666667 -4.09333333)
           (cons 40 0)
           (cons 41 0)
           (cons 42 0)
           (cons 91 0)
           (list 10 8.2 -4.25)
           (cons 40 0)
           (cons 41 0)
           (cons 42 0)
           (cons 91 0)
           (list 10 5.8 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.33333333 2.07333333)
           (cons 40 0)
           (cons 41 0)
           (cons 42 0)
           (cons 91 0)
           (list 10 5.33333333 2.59333333)
           (cons 40 0)
           (cons 41 0)
           (cons 42 0)
           (cons 91 0)
           (list 10 5.8 2.75)
           (cons 40 0)
           (cons 41 0)
           (cons 42 0)
           (cons 91 0)
           (list 10 8.2 2.75)
           (cons 40 0)
           (cons 41 0)
           (cons 42 0)
           (cons 91 0)
           (list 10 8.66666667 2.59333333)
           (cons 40 0)
           (cons 41 0)
           (cons 42 0)
           (cons 91 0)
           (list 10 8.66666667 2.07333333)
           (cons 40 0)
           (cons 41 0)
           (cons 42 0)
           (cons 91 0)
           (list 10 8.2 1.91666667)
           (cons 40 0)
           (cons 41 0)
           (cons 42 0)
           (cons 91 0)
           (list 10 5.8 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.33333333 3.57333333)
           (cons 40 0)
           (cons 41 0)
           (cons 42 0)
           (cons 91 0)
           (list 10 5.33333333 4.09333333)
           (cons 40 0)
           (cons 41 0)
           (cons 42 0)
           (cons 91 0)
           (list 10 5.8 4.25)
           (cons 40 0)
           (cons 41 0)
           (cons 42 0)
           (cons 91 0)
           (list 10 8.2 4.25)
           (cons 40 0)
           (cons 41 0)
           (cons 42 0)
           (cons 91 0)
           (list 10 8.66666667 4.09333333)
           (cons 40 0)
           (cons 41 0)
           (cons 42 0)
           (cons 91 0)
           (list 10 8.66666667 3.57333333)
           (cons 40 0)
           (cons 41 0)
           (cons 42 0)
           (cons 91 0)
           (list 10 8.2 3.41666667)
           (cons 40 0)
           (cons 41 0)
           (cons 42 0)
           (cons 91 0)
           (list 10 5.8 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 7 0 0)
           (cons 50 0)
          )
         )
         (entmake
          (list
           (cons 0 "POINT")
           (cons 100 "AcDbEntity")
           (cons 67 0)
           (cons 8 "0")
           (cons 100 "AcDbPoint")
           (list 10 7 -4.25 0)
           (cons 50 0)
          )
         )
         (entmake
          (list
           (cons 0 "POINT")
           (cons 100 "AcDbEntity")
           (cons 67 0)
           (cons 8 "0")
           (cons 100 "AcDbPoint")
           (list 10 7 4.25 0)
           (cons 50 0)
          )
         )
         (entmake
          (list
           (cons 0 "LWPOLYLINE")
           (cons 100 "AcDbEntity")
           (cons 67 0)
           (cons 8 "Defpoints")
           (cons 100 "AcDbPolyline")
           (cons 90 3)
           (cons 70 1)
           (cons 43 0)
           (cons 38 0)
           (cons 39 0)
           (list 10 0 0)
           (cons 40 0)
           (cons 41 0)
           (cons 42 0)
           (cons 91 0)
           (list 10 7 4.25)
           (cons 40 0)
           (cons 41 0)
           (cons 42 0)
           (cons 91 0)
           (list 10 7 -4.25)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 -2.29658793 1.85914261 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 0.76552931 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -0.32808399 0)
           (cons 40 0.65616798)
           (cons 1 "7.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -1.42169729 0)
           (cons 40 0.65616798)
           (cons 1 "7.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-67D-TRAILER1"))
        (progn
         (entmake)
         (entmake
          (list
           (cons 0 "BLOCK")
           (cons 2 "AASHTO-2011-WB-67D-TRAILER1")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 28.5 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 28.5 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 2.5 0 0)
           (cons 40 0.34)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 -2.59333333)
           (cons 40 0)
           (cons 41 0)
           (cons 42 0)
           (cons 91 0)
           (list 10 23.83333333 -2.07333333)
           (cons 40 0)
           (cons 41 0)
           (cons 42 0)
           (cons 91 0)
           (list 10 24.3 -1.91666667)
           (cons 40 0)
           (cons 41 0)
           (cons 42 0)
           (cons 91 0)
           (list 10 26.7 -1.91666667)
           (cons 40 0)
           (cons 41 0)
           (cons 42 0)
           (cons 91 0)
           (list 10 27.16666667 -2.07333333)
           (cons 40 0)
           (cons 41 0)
           (cons 42 0)
           (cons 91 0)
           (list 10 27.16666667 -2.59333333)
           (cons 40 0)
           (cons 41 0)
           (cons 42 0)
           (cons 91 0)
           (list 10 26.7 -2.75)
           (cons 40 0)
           (cons 41 0)
           (cons 42 0)
           (cons 91 0)
           (list 10 24.3 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 -4.09333333)
           (cons 40 0)
           (cons 41 0)
           (cons 42 0)
           (cons 91 0)
           (list 10 23.83333333 -3.57333333)
           (cons 40 0)
           (cons 41 0)
           (cons 42 0)
           (cons 91 0)
           (list 10 24.3 -3.41666667)
           (cons 40 0)
           (cons 41 0)
           (cons 42 0)
           (cons 91 0)
           (list 10 26.7 -3.41666667)
           (cons 40 0)
           (cons 41 0)
           (cons 42 0)
           (cons 91 0)
           (list 10 27.16666667 -3.57333333)
           (cons 40 0)
           (cons 41 0)
           (cons 42 0)
           (cons 91 0)
           (list 10 27.16666667 -4.09333333)
           (cons 40 0)
           (cons 41 0)
           (cons 42 0)
           (cons 91 0)
           (list 10 26.7 -4.25)
           (cons 40 0)
           (cons 41 0)
           (cons 42 0)
           (cons 91 0)
           (list 10 24.3 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 2.07333333)
           (cons 40 0)
           (cons 41 0)
           (cons 42 0)
           (cons 91 0)
           (list 10 23.83333333 2.59333333)
           (cons 40 0)
           (cons 41 0)
           (cons 42 0)
           (cons 91 0)
           (list 10 24.3 2.75)
           (cons 40 0)
           (cons 41 0)
           (cons 42 0)
           (cons 91 0)
           (list 10 26.7 2.75)
           (cons 40 0)
           (cons 41 0)
           (cons 42 0)
           (cons 91 0)
           (list 10 27.16666667 2.59333333)
           (cons 40 0)
           (cons 41 0)
           (cons 42 0)
           (cons 91 0)
           (list 10 27.16666667 2.07333333)
           (cons 40 0)
           (cons 41 0)
           (cons 42 0)
           (cons 91 0)
           (list 10 26.7 1.91666667)
           (cons 40 0)
           (cons 41 0)
           (cons 42 0)
           (cons 91 0)
           (list 10 24.3 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.83333333 3.57333333)
           (cons 40 0)
           (cons 41 0)
           (cons 42 0)
           (cons 91 0)
           (list 10 23.83333333 4.09333333)
           (cons 40 0)
           (cons 41 0)
           (cons 42 0)
           (cons 91 0)
           (list 10 24.3 4.25)
           (cons 40 0)
           (cons 41 0)
           (cons 42 0)
           (cons 91 0)
           (list 10 26.7 4.25)
           (cons 40 0)
           (cons 41 0)
           (cons 42 0)
           (cons 91 0)
           (list 10 27.16666667 4.09333333)
           (cons 40 0)
           (cons 41 0)
           (cons 42 0)
           (cons 91 0)
           (list 10 27.16666667 3.57333333)
           (cons 40 0)
           (cons 41 0)
           (cons 42 0)
           (cons 91 0)
           (list 10 26.7 3.41666667)
           (cons 40 0)
           (cons 41 0)
           (cons 42 0)
           (cons 91 0)
           (list 10 24.3 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 2.5 0 0)
           (cons 50 0)
          )
         )
         (entmake
          (list
           (cons 0 "POINT")
           (cons 100 "AcDbEntity")
           (cons 67 0)
           (cons 8 "0")
           (cons 100 "AcDbPoint")
           (list 10 0 -4.25 0)
           (cons 50 0)
          )
         )
         (entmake
          (list
           (cons 0 "POINT")
           (cons 100 "AcDbEntity")
           (cons 67 0)
           (cons 8 "0")
           (cons 100 "AcDbPoint")
           (list 10 0 4.25 0)
           (cons 50 0)
          )
         )
         (entmake
          (list
           (cons 0 "POINT")
           (cons 100 "AcDbEntity")
           (cons 67 0)
           (cons 8 "0")
           (cons 100 "AcDbPoint")
           (list 10 25.5 4.25 0)
           (cons 50 0)
          )
         )
         (entmake
          (list
           (cons 0 "POINT")
           (cons 100 "AcDbEntity")
           (cons 67 0)
           (cons 8 "0")
           (cons 100 "AcDbPoint")
           (list 10 28.5 4.25 0)
           (cons 50 0)
          )
         )
         (entmake
          (list
           (cons 0 "POINT")
           (cons 100 "AcDbEntity")
           (cons 67 0)
           (cons 8 "0")
           (cons 100 "AcDbPoint")
           (list 10 25.5 -4.25 0)
           (cons 50 0)
          )
         )
         (entmake
          (list
           (cons 0 "POINT")
           (cons 100 "AcDbEntity")
           (cons 67 0)
           (cons 8 "0")
           (cons 100 "AcDbPoint")
           (list 10 28.5 -4.25 0)
           (cons 50 0)
          )
         )
         (entmake
          (list
           (cons 0 "POINT")
           (cons 100 "AcDbEntity")
           (cons 67 0)
           (cons 8 "0")
           (cons 100 "AcDbPoint")
           (list 10 28.5 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4.25)
           (cons 40 0)
           (cons 41 0)
           (cons 42 0)
           (cons 91 0)
           (list 10 28.5 -4.25)
           (cons 40 0)
           (cons 41 0)
           (cons 42 0)
           (cons 91 0)
           (list 10 28.5 4.25)
           (cons 40 0)
           (cons 41 0)
           (cons 42 0)
           (cons 91 0)
           (list 10 0 4.25)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.20341207 1.85914261 0)
           (cons 40 0.65616798)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 0.76552931 0)
           (cons 40 0.65616798)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -0.32808399 0)
           (cons 40 0.65616798)
           (cons 1 "25.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -1.42169729 0)
           (cons 40 0.65616798)
           (cons 1 "28.500")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-67D-TRUCK"))
        (progn
         (entmake)
         (entmake
          (list
           (cons 0 "BLOCK")
           (cons 2 "AASHTO-2011-WB-67D-TRUCK")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.5 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.5 -1.66666667 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 13.3 -1.66666667 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 13.3 1.66666667 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.5 1.66666667 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.5 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 13.3 0 0)
           (cons 40 1.14285714)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 14.10812204 -0.80812204 0)
           (list 11 14.10812204 0.80812204 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.63333333 -2.34333333)
           (cons 40 0)
           (cons 41 0)
           (cons 42 0)
           (cons 91 0)
           (list 10 11.63333333 -1.82333333)
           (cons 40 0)
           (cons 41 0)
           (cons 42 0)
           (cons 91 0)
           (list 10 12.1 -1.66666667)
           (cons 40 0)
           (cons 41 0)
           (cons 42 0)
           (cons 91 0)
           (list 10 14.5 -1.66666667)
           (cons 40 0)
           (cons 41 0)
           (cons 42 0)
           (cons 91 0)
           (list 10 14.96666667 -1.82333333)
           (cons 40 0)
           (cons 41 0)
           (cons 42 0)
           (cons 91 0)
           (list 10 14.96666667 -2.34333333)
           (cons 40 0)
           (cons 41 0)
           (cons 42 0)
           (cons 91 0)
           (list 10 14.5 -2.5)
           (cons 40 0)
           (cons 41 0)
           (cons 42 0)
           (cons 91 0)
           (list 10 12.1 -2.5)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.63333333 -3.84333333)
           (cons 40 0)
           (cons 41 0)
           (cons 42 0)
           (cons 91 0)
           (list 10 11.63333333 -3.32333333)
           (cons 40 0)
           (cons 41 0)
           (cons 42 0)
           (cons 91 0)
           (list 10 12.1 -3.16666667)
           (cons 40 0)
           (cons 41 0)
           (cons 42 0)
           (cons 91 0)
           (list 10 14.5 -3.16666667)
           (cons 40 0)
           (cons 41 0)
           (cons 42 0)
           (cons 91 0)
           (list 10 14.96666667 -3.32333333)
           (cons 40 0)
           (cons 41 0)
           (cons 42 0)
           (cons 91 0)
           (list 10 14.96666667 -3.84333333)
           (cons 40 0)
           (cons 41 0)
           (cons 42 0)
           (cons 91 0)
           (list 10 14.5 -4)
           (cons 40 0)
           (cons 41 0)
           (cons 42 0)
           (cons 91 0)
           (list 10 12.1 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.63333333 1.82333333)
           (cons 40 0)
           (cons 41 0)
           (cons 42 0)
           (cons 91 0)
           (list 10 11.63333333 2.34333333)
           (cons 40 0)
           (cons 41 0)
           (cons 42 0)
           (cons 91 0)
           (list 10 12.1 2.5)
           (cons 40 0)
           (cons 41 0)
           (cons 42 0)
           (cons 91 0)
           (list 10 14.5 2.5)
           (cons 40 0)
           (cons 41 0)
           (cons 42 0)
           (cons 91 0)
           (list 10 14.96666667 2.34333333)
           (cons 40 0)
           (cons 41 0)
           (cons 42 0)
           (cons 91 0)
           (list 10 14.96666667 1.82333333)
           (cons 40 0)
           (cons 41 0)
           (cons 42 0)
           (cons 91 0)
           (list 10 14.5 1.66666667)
           (cons 40 0)
           (cons 41 0)
           (cons 42 0)
           (cons 91 0)
           (list 10 12.1 1.66666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.63333333 3.32333333)
           (cons 40 0)
           (cons 41 0)
           (cons 42 0)
           (cons 91 0)
           (list 10 11.63333333 3.84333333)
           (cons 40 0)
           (cons 41 0)
           (cons 42 0)
           (cons 91 0)
           (list 10 12.1 4)
           (cons 40 0)
           (cons 41 0)
           (cons 42 0)
           (cons 91 0)
           (list 10 14.5 4)
           (cons 40 0)
           (cons 41 0)
           (cons 42 0)
           (cons 91 0)
           (list 10 14.96666667 3.84333333)
           (cons 40 0)
           (cons 41 0)
           (cons 42 0)
           (cons 91 0)
           (list 10 14.96666667 3.32333333)
           (cons 40 0)
           (cons 41 0)
           (cons 42 0)
           (cons 91 0)
           (list 10 14.5 3.16666667)
           (cons 40 0)
           (cons 41 0)
           (cons 42 0)
           (cons 91 0)
           (list 10 12.1 3.16666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 2.3 0 0)
           (cons 50 0)
          )
         )
         (entmake
          (list
           (cons 0 "POINT")
           (cons 100 "AcDbEntity")
           (cons 67 0)
           (cons 8 "0")
           (cons 100 "AcDbPoint")
           (list 10 13.3 0 0)
           (cons 50 0)
          )
         )
         (entmake
          (list
           (cons 0 "POINT")
           (cons 100 "AcDbEntity")
           (cons 67 0)
           (cons 8 "0")
           (cons 100 "AcDbPoint")
           (list 10 2.3 -4 0)
           (cons 50 0)
          )
         )
         (entmake
          (list
           (cons 0 "POINT")
           (cons 100 "AcDbEntity")
           (cons 67 0)
           (cons 8 "0")
           (cons 100 "AcDbPoint")
           (list 10 13.3 -4 0)
           (cons 50 0)
          )
         )
         (entmake
          (list
           (cons 0 "POINT")
           (cons 100 "AcDbEntity")
           (cons 67 0)
           (cons 8 "0")
           (cons 100 "AcDbPoint")
           (list 10 13.3 4 0)
           (cons 50 0)
          )
         )
         (entmake
          (list
           (cons 0 "POINT")
           (cons 100 "AcDbEntity")
           (cons 67 0)
           (cons 8 "0")
           (cons 100 "AcDbPoint")
           (list 10 2.3 4 0)
           (cons 50 0)
          )
         )
         (entmake
          (list
           (cons 0 "POINT")
           (cons 100 "AcDbEntity")
           (cons 67 0)
           (cons 8 "0")
           (cons 100 "AcDbPoint")
           (list 10 0 4 0)
           (cons 50 0)
          )
         )
         (entmake
          (list
           (cons 0 "POINT")
           (cons 100 "AcDbEntity")
           (cons 67 0)
           (cons 8 "0")
           (cons 100 "AcDbPoint")
           (list 10 0 -4 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4)
           (cons 40 0)
           (cons 41 0)
           (cons 42 0)
           (cons 91 0)
           (list 10 13.3 -4)
           (cons 40 0)
           (cons 41 0)
           (cons 42 0)
           (cons 91 0)
           (list 10 13.3 4)
           (cons 40 0)
           (cons 41 0)
           (cons 42 0)
           (cons 91 0)
           (list 10 0 4)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelRight2")
           (list 10 2.3 3.16666667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeft2")
           (list 10 2.3 -3.16666667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 0.0328084 1.85914261 0)
           (cons 40 0.65616798)
           (cons 1 "2.300")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.0328084 0.76552931 0)
           (cons 40 0.65616798)
           (cons 1 "2.300")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.0328084 -0.32808399 0)
           (cons 40 0.65616798)
           (cons 1 "13.300")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.0328084 -1.42169729 0)
           (cons 40 0.65616798)
           (cons 1 "13.300")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.0328084 -2.51531059 0)
           (cons 40 0.65616798)
           (cons 1 "27.3")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-62-TRAILER"))
        (progn
         (entmake)
         (entmake
          (list
           (cons 0 "BLOCK")
           (cons 2 "AASHTO-2011-WB-62-TRAILER")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 48 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 48 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 2.5 0 0)
           (cons 40 0.34)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 39.84868766 -2.42766667)
           (cons 40 0)
           (cons 41 0)
           (cons 42 0)
           (cons 91 0)
           (list 10 39.84868766 -1.85566667)
           (cons 40 0)
           (cons 41 0)
           (cons 42 0)
           (cons 91 0)
           (list 10 40.31068766 -1.68333333)
           (cons 40 0)
           (cons 41 0)
           (cons 42 0)
           (cons 91 0)
           (list 10 42.68668766 -1.68333333)
           (cons 40 0)
           (cons 41 0)
           (cons 42 0)
           (cons 91 0)
           (list 10 43.14868766 -1.85566667)
           (cons 40 0)
           (cons 41 0)
           (cons 42 0)
           (cons 91 0)
           (list 10 43.14868766 -2.42766667)
           (cons 40 0)
           (cons 41 0)
           (cons 42 0)
           (cons 91 0)
           (list 10 42.68668766 -2.6)
           (cons 40 0)
           (cons 41 0)
           (cons 42 0)
           (cons 91 0)
           (list 10 40.31068766 -2.6)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 39.84868766 -4.07766667)
           (cons 40 0)
           (cons 41 0)
           (cons 42 0)
           (cons 91 0)
           (list 10 39.84868766 -3.50566667)
           (cons 40 0)
           (cons 41 0)
           (cons 42 0)
           (cons 91 0)
           (list 10 40.31068766 -3.33333333)
           (cons 40 0)
           (cons 41 0)
           (cons 42 0)
           (cons 91 0)
           (list 10 42.68668766 -3.33333333)
           (cons 40 0)
           (cons 41 0)
           (cons 42 0)
           (cons 91 0)
           (list 10 43.14868766 -3.50566667)
           (cons 40 0)
           (cons 41 0)
           (cons 42 0)
           (cons 91 0)
           (list 10 43.14868766 -4.07766667)
           (cons 40 0)
           (cons 41 0)
           (cons 42 0)
           (cons 91 0)
           (list 10 42.68668766 -4.25)
           (cons 40 0)
           (cons 41 0)
           (cons 42 0)
           (cons 91 0)
           (list 10 40.31068766 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 39.84868766 3.50566667)
           (cons 40 0)
           (cons 41 0)
           (cons 42 0)
           (cons 91 0)
           (list 10 39.84868766 4.07766667)
           (cons 40 0)
           (cons 41 0)
           (cons 42 0)
           (cons 91 0)
           (list 10 40.31068766 4.25)
           (cons 40 0)
           (cons 41 0)
           (cons 42 0)
           (cons 91 0)
           (list 10 42.68668766 4.25)
           (cons 40 0)
           (cons 41 0)
           (cons 42 0)
           (cons 91 0)
           (list 10 43.14868766 4.07766667)
           (cons 40 0)
           (cons 41 0)
           (cons 42 0)
           (cons 91 0)
           (list 10 43.14868766 3.50566667)
           (cons 40 0)
           (cons 41 0)
           (cons 42 0)
           (cons 91 0)
           (list 10 42.68668766 3.33333333)
           (cons 40 0)
           (cons 41 0)
           (cons 42 0)
           (cons 91 0)
           (list 10 40.31068766 3.33333333)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 43.85131234 -2.42766667)
           (cons 40 0)
           (cons 41 0)
           (cons 42 0)
           (cons 91 0)
           (list 10 43.85131234 -1.85566667)
           (cons 40 0)
           (cons 41 0)
           (cons 42 0)
           (cons 91 0)
           (list 10 44.31331234 -1.68333333)
           (cons 40 0)
           (cons 41 0)
           (cons 42 0)
           (cons 91 0)
           (list 10 46.68931234 -1.68333333)
           (cons 40 0)
           (cons 41 0)
           (cons 42 0)
           (cons 91 0)
           (list 10 47.15131234 -1.85566667)
           (cons 40 0)
           (cons 41 0)
           (cons 42 0)
           (cons 91 0)
           (list 10 47.15131234 -2.42766667)
           (cons 40 0)
           (cons 41 0)
           (cons 42 0)
           (cons 91 0)
           (list 10 46.68931234 -2.6)
           (cons 40 0)
           (cons 41 0)
           (cons 42 0)
           (cons 91 0)
           (list 10 44.31331234 -2.6)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 43.85131234 -4.07766667)
           (cons 40 0)
           (cons 41 0)
           (cons 42 0)
           (cons 91 0)
           (list 10 43.85131234 -3.50566667)
           (cons 40 0)
           (cons 41 0)
           (cons 42 0)
           (cons 91 0)
           (list 10 44.31331234 -3.33333333)
           (cons 40 0)
           (cons 41 0)
           (cons 42 0)
           (cons 91 0)
           (list 10 46.68931234 -3.33333333)
           (cons 40 0)
           (cons 41 0)
           (cons 42 0)
           (cons 91 0)
           (list 10 47.15131234 -3.50566667)
           (cons 40 0)
           (cons 41 0)
           (cons 42 0)
           (cons 91 0)
           (list 10 47.15131234 -4.07766667)
           (cons 40 0)
           (cons 41 0)
           (cons 42 0)
           (cons 91 0)
           (list 10 46.68931234 -4.25)
           (cons 40 0)
           (cons 41 0)
           (cons 42 0)
           (cons 91 0)
           (list 10 44.31331234 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 43.85131234 3.50566667)
           (cons 40 0)
           (cons 41 0)
           (cons 42 0)
           (cons 91 0)
           (list 10 43.85131234 4.07766667)
           (cons 40 0)
           (cons 41 0)
           (cons 42 0)
           (cons 91 0)
           (list 10 44.31331234 4.25)
           (cons 40 0)
           (cons 41 0)
           (cons 42 0)
           (cons 91 0)
           (list 10 46.68931234 4.25)
           (cons 40 0)
           (cons 41 0)
           (cons 42 0)
           (cons 91 0)
           (list 10 47.15131234 4.07766667)
           (cons 40 0)
           (cons 41 0)
           (cons 42 0)
           (cons 91 0)
           (list 10 47.15131234 3.50566667)
           (cons 40 0)
           (cons 41 0)
           (cons 42 0)
           (cons 91 0)
           (list 10 46.68931234 3.33333333)
           (cons 40 0)
           (cons 41 0)
           (cons 42 0)
           (cons 91 0)
           (list 10 44.31331234 3.33333333)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 2.5 0 0)
           (cons 50 0)
          )
         )
         (entmake
          (list
           (cons 0 "POINT")
           (cons 100 "AcDbEntity")
           (cons 67 0)
           (cons 8 "0")
           (cons 100 "AcDbPoint")
           (list 10 0 -4.25 0)
           (cons 50 0)
          )
         )
         (entmake
          (list
           (cons 0 "POINT")
           (cons 100 "AcDbEntity")
           (cons 67 0)
           (cons 8 "0")
           (cons 100 "AcDbPoint")
           (list 10 48 -4.25 0)
           (cons 50 0)
          )
         )
         (entmake
          (list
           (cons 0 "POINT")
           (cons 100 "AcDbEntity")
           (cons 67 0)
           (cons 8 "0")
           (cons 100 "AcDbPoint")
           (list 10 48 4.25 0)
           (cons 50 0)
          )
         )
         (entmake
          (list
           (cons 0 "POINT")
           (cons 100 "AcDbEntity")
           (cons 67 0)
           (cons 8 "0")
           (cons 100 "AcDbPoint")
           (list 10 0 4.25 0)
           (cons 50 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 39.84868766 2.42766667)
           (cons 40 0)
           (cons 41 0)
           (cons 42 0)
           (cons 91 0)
           (list 10 39.84868766 1.85566667)
           (cons 40 0)
           (cons 41 0)
           (cons 42 0)
           (cons 91 0)
           (list 10 40.31068766 1.68333333)
           (cons 40 0)
           (cons 41 0)
           (cons 42 0)
           (cons 91 0)
           (list 10 42.68668766 1.68333333)
           (cons 40 0)
           (cons 41 0)
           (cons 42 0)
           (cons 91 0)
           (list 10 43.14868766 1.85566667)
           (cons 40 0)
           (cons 41 0)
           (cons 42 0)
           (cons 91 0)
           (list 10 43.14868766 2.42766667)
           (cons 40 0)
           (cons 41 0)
           (cons 42 0)
           (cons 91 0)
           (list 10 42.68668766 2.6)
           (cons 40 0)
           (cons 41 0)
           (cons 42 0)
           (cons 91 0)
           (list 10 40.31068766 2.6)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 43.85131234 2.42766667)
           (cons 40 0)
           (cons 41 0)
           (cons 42 0)
           (cons 91 0)
           (list 10 43.85131234 1.85566667)
           (cons 40 0)
           (cons 41 0)
           (cons 42 0)
           (cons 91 0)
           (list 10 44.31331234 1.68333333)
           (cons 40 0)
           (cons 41 0)
           (cons 42 0)
           (cons 91 0)
           (list 10 46.68931234 1.68333333)
           (cons 40 0)
           (cons 41 0)
           (cons 42 0)
           (cons 91 0)
           (list 10 47.15131234 1.85566667)
           (cons 40 0)
           (cons 41 0)
           (cons 42 0)
           (cons 91 0)
           (list 10 47.15131234 2.42766667)
           (cons 40 0)
           (cons 41 0)
           (cons 42 0)
           (cons 91 0)
           (list 10 46.68931234 2.6)
           (cons 40 0)
           (cons 41 0)
           (cons 42 0)
           (cons 91 0)
           (list 10 44.31331234 2.6)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 43.5 -4.25 0)
           (cons 50 0)
          )
         )
         (entmake
          (list
           (cons 0 "POINT")
           (cons 100 "AcDbEntity")
           (cons 67 0)
           (cons 8 "0")
           (cons 100 "AcDbPoint")
           (list 10 43.5 4.25 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4.25)
           (cons 40 0)
           (cons 41 0)
           (cons 42 0)
           (cons 91 0)
           (list 10 48 -4.25)
           (cons 40 0)
           (cons 41 0)
           (cons 42 0)
           (cons 91 0)
           (list 10 48 4.25)
           (cons 40 0)
           (cons 41 0)
           (cons 42 0)
           (cons 91 0)
           (list 10 0 4.25)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.20341207 1.85914261 0)
           (cons 40 0.65616798)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 0.76552931 0)
           (cons 40 0.65616798)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -0.32808399 0)
           (cons 40 0.65616798)
           (cons 1 "43.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-62-TRUCK"))
        (progn
         (entmake)
         (entmake
          (list
           (cons 0 "BLOCK")
           (cons 2 "AASHTO-2011-WB-62-TRUCK")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15 -1.43333333 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 25.6 -1.43333333 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 25.6 1.43333333 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15 1.43333333 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 23.5 0 0)
           (cons 40 1.14285714)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 24.30812204 -0.80812204 0)
           (list 11 24.30812204 0.80812204 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 19.56666667 -2.17766667)
           (cons 40 0)
           (cons 41 0)
           (cons 42 0)
           (cons 91 0)
           (list 10 19.56666667 -1.60566667)
           (cons 40 0)
           (cons 41 0)
           (cons 42 0)
           (cons 91 0)
           (list 10 20.08 -1.43333333)
           (cons 40 0)
           (cons 41 0)
           (cons 42 0)
           (cons 91 0)
           (list 10 22.72 -1.43333333)
           (cons 40 0)
           (cons 41 0)
           (cons 42 0)
           (cons 91 0)
           (list 10 23.23333333 -1.60566667)
           (cons 40 0)
           (cons 41 0)
           (cons 42 0)
           (cons 91 0)
           (list 10 23.23333333 -2.17766667)
           (cons 40 0)
           (cons 41 0)
           (cons 42 0)
           (cons 91 0)
           (list 10 22.72 -2.35)
           (cons 40 0)
           (cons 41 0)
           (cons 42 0)
           (cons 91 0)
           (list 10 20.08 -2.35)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 19.56666667 -3.82766667)
           (cons 40 0)
           (cons 41 0)
           (cons 42 0)
           (cons 91 0)
           (list 10 19.56666667 -3.25566667)
           (cons 40 0)
           (cons 41 0)
           (cons 42 0)
           (cons 91 0)
           (list 10 20.08 -3.08333333)
           (cons 40 0)
           (cons 41 0)
           (cons 42 0)
           (cons 91 0)
           (list 10 22.72 -3.08333333)
           (cons 40 0)
           (cons 41 0)
           (cons 42 0)
           (cons 91 0)
           (list 10 23.23333333 -3.25566667)
           (cons 40 0)
           (cons 41 0)
           (cons 42 0)
           (cons 91 0)
           (list 10 23.23333333 -3.82766667)
           (cons 40 0)
           (cons 41 0)
           (cons 42 0)
           (cons 91 0)
           (list 10 22.72 -4)
           (cons 40 0)
           (cons 41 0)
           (cons 42 0)
           (cons 91 0)
           (list 10 20.08 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 19.56666667 1.60566667)
           (cons 40 0)
           (cons 41 0)
           (cons 42 0)
           (cons 91 0)
           (list 10 19.56666667 2.17766667)
           (cons 40 0)
           (cons 41 0)
           (cons 42 0)
           (cons 91 0)
           (list 10 20.08 2.35)
           (cons 40 0)
           (cons 41 0)
           (cons 42 0)
           (cons 91 0)
           (list 10 22.72 2.35)
           (cons 40 0)
           (cons 41 0)
           (cons 42 0)
           (cons 91 0)
           (list 10 23.23333333 2.17766667)
           (cons 40 0)
           (cons 41 0)
           (cons 42 0)
           (cons 91 0)
           (list 10 23.23333333 1.60566667)
           (cons 40 0)
           (cons 41 0)
           (cons 42 0)
           (cons 91 0)
           (list 10 22.72 1.43333333)
           (cons 40 0)
           (cons 41 0)
           (cons 42 0)
           (cons 91 0)
           (list 10 20.08 1.43333333)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 19.56666667 3.25566667)
           (cons 40 0)
           (cons 41 0)
           (cons 42 0)
           (cons 91 0)
           (list 10 19.56666667 3.82766667)
           (cons 40 0)
           (cons 41 0)
           (cons 42 0)
           (cons 91 0)
           (list 10 20.08 4)
           (cons 40 0)
           (cons 41 0)
           (cons 42 0)
           (cons 91 0)
           (list 10 22.72 4)
           (cons 40 0)
           (cons 41 0)
           (cons 42 0)
           (cons 91 0)
           (list 10 23.23333333 3.82766667)
           (cons 40 0)
           (cons 41 0)
           (cons 42 0)
           (cons 91 0)
           (list 10 23.23333333 3.25566667)
           (cons 40 0)
           (cons 41 0)
           (cons 42 0)
           (cons 91 0)
           (list 10 22.72 3.08333333)
           (cons 40 0)
           (cons 41 0)
           (cons 42 0)
           (cons 91 0)
           (list 10 20.08 3.08333333)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.76666667 -2.17766667)
           (cons 40 0)
           (cons 41 0)
           (cons 42 0)
           (cons 91 0)
           (list 10 23.76666667 -1.60566667)
           (cons 40 0)
           (cons 41 0)
           (cons 42 0)
           (cons 91 0)
           (list 10 24.28 -1.43333333)
           (cons 40 0)
           (cons 41 0)
           (cons 42 0)
           (cons 91 0)
           (list 10 26.92 -1.43333333)
           (cons 40 0)
           (cons 41 0)
           (cons 42 0)
           (cons 91 0)
           (list 10 27.43333333 -1.60566667)
           (cons 40 0)
           (cons 41 0)
           (cons 42 0)
           (cons 91 0)
           (list 10 27.43333333 -2.17766667)
           (cons 40 0)
           (cons 41 0)
           (cons 42 0)
           (cons 91 0)
           (list 10 26.92 -2.35)
           (cons 40 0)
           (cons 41 0)
           (cons 42 0)
           (cons 91 0)
           (list 10 24.28 -2.35)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.76666667 -3.82766667)
           (cons 40 0)
           (cons 41 0)
           (cons 42 0)
           (cons 91 0)
           (list 10 23.76666667 -3.25566667)
           (cons 40 0)
           (cons 41 0)
           (cons 42 0)
           (cons 91 0)
           (list 10 24.28 -3.08333333)
           (cons 40 0)
           (cons 41 0)
           (cons 42 0)
           (cons 91 0)
           (list 10 26.92 -3.08333333)
           (cons 40 0)
           (cons 41 0)
           (cons 42 0)
           (cons 91 0)
           (list 10 27.43333333 -3.25566667)
           (cons 40 0)
           (cons 41 0)
           (cons 42 0)
           (cons 91 0)
           (list 10 27.43333333 -3.82766667)
           (cons 40 0)
           (cons 41 0)
           (cons 42 0)
           (cons 91 0)
           (list 10 26.92 -4)
           (cons 40 0)
           (cons 41 0)
           (cons 42 0)
           (cons 91 0)
           (list 10 24.28 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.76666667 1.60566667)
           (cons 40 0)
           (cons 41 0)
           (cons 42 0)
           (cons 91 0)
           (list 10 23.76666667 2.17766667)
           (cons 40 0)
           (cons 41 0)
           (cons 42 0)
           (cons 91 0)
           (list 10 24.28 2.35)
           (cons 40 0)
           (cons 41 0)
           (cons 42 0)
           (cons 91 0)
           (list 10 26.92 2.35)
           (cons 40 0)
           (cons 41 0)
           (cons 42 0)
           (cons 91 0)
           (list 10 27.43333333 2.17766667)
           (cons 40 0)
           (cons 41 0)
           (cons 42 0)
           (cons 91 0)
           (list 10 27.43333333 1.60566667)
           (cons 40 0)
           (cons 41 0)
           (cons 42 0)
           (cons 91 0)
           (list 10 26.92 1.43333333)
           (cons 40 0)
           (cons 41 0)
           (cons 42 0)
           (cons 91 0)
           (list 10 24.28 1.43333333)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 23.76666667 3.25566667)
           (cons 40 0)
           (cons 41 0)
           (cons 42 0)
           (cons 91 0)
           (list 10 23.76666667 3.82766667)
           (cons 40 0)
           (cons 41 0)
           (cons 42 0)
           (cons 91 0)
           (list 10 24.28 4)
           (cons 40 0)
           (cons 41 0)
           (cons 42 0)
           (cons 91 0)
           (list 10 26.92 4)
           (cons 40 0)
           (cons 41 0)
           (cons 42 0)
           (cons 91 0)
           (list 10 27.43333333 3.82766667)
           (cons 40 0)
           (cons 41 0)
           (cons 42 0)
           (cons 91 0)
           (list 10 27.43333333 3.25566667)
           (cons 40 0)
           (cons 41 0)
           (cons 42 0)
           (cons 91 0)
           (list 10 26.92 3.08333333)
           (cons 40 0)
           (cons 41 0)
           (cons 42 0)
           (cons 91 0)
           (list 10 24.28 3.08333333)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4 0)
           (cons 50 0)
          )
         )
         (entmake
          (list
           (cons 0 "POINT")
           (cons 100 "AcDbEntity")
           (cons 67 0)
           (cons 8 "0")
           (cons 100 "AcDbPoint")
           (list 10 4 -4 0)
           (cons 50 0)
          )
         )
         (entmake
          (list
           (cons 0 "POINT")
           (cons 100 "AcDbEntity")
           (cons 67 0)
           (cons 8 "0")
           (cons 100 "AcDbPoint")
           (list 10 23.5 -4 0)
           (cons 50 0)
          )
         )
         (entmake
          (list
           (cons 0 "POINT")
           (cons 100 "AcDbEntity")
           (cons 67 0)
           (cons 8 "0")
           (cons 100 "AcDbPoint")
           (list 10 23.5 4 0)
           (cons 50 0)
          )
         )
         (entmake
          (list
           (cons 0 "POINT")
           (cons 100 "AcDbEntity")
           (cons 67 0)
           (cons 8 "0")
           (cons 100 "AcDbPoint")
           (list 10 4 0 0)
           (cons 50 0)
          )
         )
         (entmake
          (list
           (cons 0 "POINT")
           (cons 100 "AcDbEntity")
           (cons 67 0)
           (cons 8 "0")
           (cons 100 "AcDbPoint")
           (list 10 4 4 0)
           (cons 50 0)
          )
         )
         (entmake
          (list
           (cons 0 "POINT")
           (cons 100 "AcDbEntity")
           (cons 67 0)
           (cons 8 "0")
           (cons 100 "AcDbPoint")
           (list 10 0 4 0)
           (cons 50 0)
          )
         )
         (entmake
          (list
           (cons 0 "POINT")
           (cons 100 "AcDbEntity")
           (cons 67 0)
           (cons 8 "0")
           (cons 100 "AcDbPoint")
           (list 10 23.5 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4)
           (cons 40 0)
           (cons 41 0)
           (cons 42 0)
           (cons 91 0)
           (list 10 25.6 -4)
           (cons 40 0)
           (cons 41 0)
           (cons 42 0)
           (cons 91 0)
           (list 10 25.6 4)
           (cons 40 0)
           (cons 41 0)
           (cons 42 0)
           (cons 91 0)
           (list 10 0 4)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelLeft1")
           (list 10 4 -3.08333333 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRight1")
           (list 10 4 3.08333333 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 1.70341207 1.85914261 0)
           (cons 40 0.65616798)
           (cons 1 "4.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 0.76552931 0)
           (cons 40 0.65616798)
           (cons 1 "4.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -0.32808399 0)
           (cons 40 0.65616798)
           (cons 1 "23.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -1.42169729 0)
           (cons 40 0.65616798)
           (cons 1 "23.500")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -2.51531059 0)
           (cons 40 0.65616798)
           (cons 1 "28.4")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-40-TRAILER"))
        (progn
         (entmake)
         (entmake
          (list
           (cons 0 "BLOCK")
           (cons 2 "AASHTO-2011-WB-40-TRAILER")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 33 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 33 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 3 0 0)
           (cons 40 0.32)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 24.86509186 -2.17766667)
           (cons 40 0)
           (cons 41 0)
           (cons 42 0)
           (cons 91 0)
           (list 10 24.86509186 -1.60566667)
           (cons 40 0)
           (cons 41 0)
           (cons 42 0)
           (cons 91 0)
           (list 10 25.32709186 -1.43333333)
           (cons 40 0)
           (cons 41 0)
           (cons 42 0)
           (cons 91 0)
           (list 10 27.70309186 -1.43333333)
           (cons 40 0)
           (cons 41 0)
           (cons 42 0)
           (cons 91 0)
           (list 10 28.16509186 -1.60566667)
           (cons 40 0)
           (cons 41 0)
           (cons 42 0)
           (cons 91 0)
           (list 10 28.16509186 -2.17766667)
           (cons 40 0)
           (cons 41 0)
           (cons 42 0)
           (cons 91 0)
           (list 10 27.70309186 -2.35)
           (cons 40 0)
           (cons 41 0)
           (cons 42 0)
           (cons 91 0)
           (list 10 25.32709186 -2.35)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 24.86509186 -3.82766667)
           (cons 40 0)
           (cons 41 0)
           (cons 42 0)
           (cons 91 0)
           (list 10 24.86509186 -3.25566667)
           (cons 40 0)
           (cons 41 0)
           (cons 42 0)
           (cons 91 0)
           (list 10 25.32709186 -3.08333333)
           (cons 40 0)
           (cons 41 0)
           (cons 42 0)
           (cons 91 0)
           (list 10 27.70309186 -3.08333333)
           (cons 40 0)
           (cons 41 0)
           (cons 42 0)
           (cons 91 0)
           (list 10 28.16509186 -3.25566667)
           (cons 40 0)
           (cons 41 0)
           (cons 42 0)
           (cons 91 0)
           (list 10 28.16509186 -3.82766667)
           (cons 40 0)
           (cons 41 0)
           (cons 42 0)
           (cons 91 0)
           (list 10 27.70309186 -4)
           (cons 40 0)
           (cons 41 0)
           (cons 42 0)
           (cons 91 0)
           (list 10 25.32709186 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 24.86509186 1.60566667)
           (cons 40 0)
           (cons 41 0)
           (cons 42 0)
           (cons 91 0)
           (list 10 24.86509186 2.17766667)
           (cons 40 0)
           (cons 41 0)
           (cons 42 0)
           (cons 91 0)
           (list 10 25.32709186 2.35)
           (cons 40 0)
           (cons 41 0)
           (cons 42 0)
           (cons 91 0)
           (list 10 27.70309186 2.35)
           (cons 40 0)
           (cons 41 0)
           (cons 42 0)
           (cons 91 0)
           (list 10 28.16509186 2.17766667)
           (cons 40 0)
           (cons 41 0)
           (cons 42 0)
           (cons 91 0)
           (list 10 28.16509186 1.60566667)
           (cons 40 0)
           (cons 41 0)
           (cons 42 0)
           (cons 91 0)
           (list 10 27.70309186 1.43333333)
           (cons 40 0)
           (cons 41 0)
           (cons 42 0)
           (cons 91 0)
           (list 10 25.32709186 1.43333333)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 24.86509186 3.25566667)
           (cons 40 0)
           (cons 41 0)
           (cons 42 0)
           (cons 91 0)
           (list 10 24.86509186 3.82766667)
           (cons 40 0)
           (cons 41 0)
           (cons 42 0)
           (cons 91 0)
           (list 10 25.32709186 4)
           (cons 40 0)
           (cons 41 0)
           (cons 42 0)
           (cons 91 0)
           (list 10 27.70309186 4)
           (cons 40 0)
           (cons 41 0)
           (cons 42 0)
           (cons 91 0)
           (list 10 28.16509186 3.82766667)
           (cons 40 0)
           (cons 41 0)
           (cons 42 0)
           (cons 91 0)
           (list 10 28.16509186 3.25566667)
           (cons 40 0)
           (cons 41 0)
           (cons 42 0)
           (cons 91 0)
           (list 10 27.70309186 3.08333333)
           (cons 40 0)
           (cons 41 0)
           (cons 42 0)
           (cons 91 0)
           (list 10 25.32709186 3.08333333)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 28.83490814 -2.17766667)
           (cons 40 0)
           (cons 41 0)
           (cons 42 0)
           (cons 91 0)
           (list 10 28.83490814 -1.60566667)
           (cons 40 0)
           (cons 41 0)
           (cons 42 0)
           (cons 91 0)
           (list 10 29.29690814 -1.43333333)
           (cons 40 0)
           (cons 41 0)
           (cons 42 0)
           (cons 91 0)
           (list 10 31.67290814 -1.43333333)
           (cons 40 0)
           (cons 41 0)
           (cons 42 0)
           (cons 91 0)
           (list 10 32.13490814 -1.60566667)
           (cons 40 0)
           (cons 41 0)
           (cons 42 0)
           (cons 91 0)
           (list 10 32.13490814 -2.17766667)
           (cons 40 0)
           (cons 41 0)
           (cons 42 0)
           (cons 91 0)
           (list 10 31.67290814 -2.35)
           (cons 40 0)
           (cons 41 0)
           (cons 42 0)
           (cons 91 0)
           (list 10 29.29690814 -2.35)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 28.83490814 -3.82766667)
           (cons 40 0)
           (cons 41 0)
           (cons 42 0)
           (cons 91 0)
           (list 10 28.83490814 -3.25566667)
           (cons 40 0)
           (cons 41 0)
           (cons 42 0)
           (cons 91 0)
           (list 10 29.29690814 -3.08333333)
           (cons 40 0)
           (cons 41 0)
           (cons 42 0)
           (cons 91 0)
           (list 10 31.67290814 -3.08333333)
           (cons 40 0)
           (cons 41 0)
           (cons 42 0)
           (cons 91 0)
           (list 10 32.13490814 -3.25566667)
           (cons 40 0)
           (cons 41 0)
           (cons 42 0)
           (cons 91 0)
           (list 10 32.13490814 -3.82766667)
           (cons 40 0)
           (cons 41 0)
           (cons 42 0)
           (cons 91 0)
           (list 10 31.67290814 -4)
           (cons 40 0)
           (cons 41 0)
           (cons 42 0)
           (cons 91 0)
           (list 10 29.29690814 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 28.83490814 1.60566667)
           (cons 40 0)
           (cons 41 0)
           (cons 42 0)
           (cons 91 0)
           (list 10 28.83490814 2.17766667)
           (cons 40 0)
           (cons 41 0)
           (cons 42 0)
           (cons 91 0)
           (list 10 29.29690814 2.35)
           (cons 40 0)
           (cons 41 0)
           (cons 42 0)
           (cons 91 0)
           (list 10 31.67290814 2.35)
           (cons 40 0)
           (cons 41 0)
           (cons 42 0)
           (cons 91 0)
           (list 10 32.13490814 2.17766667)
           (cons 40 0)
           (cons 41 0)
           (cons 42 0)
           (cons 91 0)
           (list 10 32.13490814 1.60566667)
           (cons 40 0)
           (cons 41 0)
           (cons 42 0)
           (cons 91 0)
           (list 10 31.67290814 1.43333333)
           (cons 40 0)
           (cons 41 0)
           (cons 42 0)
           (cons 91 0)
           (list 10 29.29690814 1.43333333)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 28.83490814 3.25566667)
           (cons 40 0)
           (cons 41 0)
           (cons 42 0)
           (cons 91 0)
           (list 10 28.83490814 3.82766667)
           (cons 40 0)
           (cons 41 0)
           (cons 42 0)
           (cons 91 0)
           (list 10 29.29690814 4)
           (cons 40 0)
           (cons 41 0)
           (cons 42 0)
           (cons 91 0)
           (list 10 31.67290814 4)
           (cons 40 0)
           (cons 41 0)
           (cons 42 0)
           (cons 91 0)
           (list 10 32.13490814 3.82766667)
           (cons 40 0)
           (cons 41 0)
           (cons 42 0)
           (cons 91 0)
           (list 10 32.13490814 3.25566667)
           (cons 40 0)
           (cons 41 0)
           (cons 42 0)
           (cons 91 0)
           (list 10 31.67290814 3.08333333)
           (cons 40 0)
           (cons 41 0)
           (cons 42 0)
           (cons 91 0)
           (list 10 29.29690814 3.08333333)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4 0)
           (cons 50 0)
          )
         )
         (entmake
          (list
           (cons 0 "POINT")
           (cons 100 "AcDbEntity")
           (cons 67 0)
           (cons 8 "0")
           (cons 100 "AcDbPoint")
           (list 10 0 4 0)
           (cons 50 0)
          )
         )
         (entmake
          (list
           (cons 0 "POINT")
           (cons 100 "AcDbEntity")
           (cons 67 0)
           (cons 8 "0")
           (cons 100 "AcDbPoint")
           (list 10 3 0 0)
           (cons 50 0)
          )
         )
         (entmake
          (list
           (cons 0 "POINT")
           (cons 100 "AcDbEntity")
           (cons 67 0)
           (cons 8 "0")
           (cons 100 "AcDbPoint")
           (list 10 33 -4 0)
           (cons 50 0)
          )
         )
         (entmake
          (list
           (cons 0 "POINT")
           (cons 100 "AcDbEntity")
           (cons 67 0)
           (cons 8 "0")
           (cons 100 "AcDbPoint")
           (list 10 33 4 0)
           (cons 50 0)
          )
         )
         (entmake
          (list
           (cons 0 "POINT")
           (cons 100 "AcDbEntity")
           (cons 67 0)
           (cons 8 "0")
           (cons 100 "AcDbPoint")
           (list 10 28.5 -4 0)
           (cons 50 0)
          )
         )
         (entmake
          (list
           (cons 0 "POINT")
           (cons 100 "AcDbEntity")
           (cons 67 0)
           (cons 8 "0")
           (cons 100 "AcDbPoint")
           (list 10 28.5 4 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4)
           (cons 40 0)
           (cons 41 0)
           (cons 42 0)
           (cons 91 0)
           (list 10 33 -4)
           (cons 40 0)
           (cons 41 0)
           (cons 42 0)
           (cons 91 0)
           (list 10 33 4)
           (cons 40 0)
           (cons 41 0)
           (cons 42 0)
           (cons 91 0)
           (list 10 0 4)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.70341207 1.85914261 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 0.76552931 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -0.32808399 0)
           (cons 40 0.65616798)
           (cons 1 "28.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-WB-40-TRUCK"))
        (progn
         (entmake)
         (entmake
          (list
           (cons 0 "BLOCK")
           (cons 2 "AASHTO-2011-WB-40-TRUCK")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.5 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.5 -1.43333333 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15.5 -1.43333333 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15.5 1.43333333 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.5 1.43333333 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.5 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 15.5 0 0)
           (cons 40 1.14285714)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 16.30812204 -0.80812204 0)
           (list 11 16.30812204 0.80812204 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.66666667 -2.17766667)
           (cons 40 0)
           (cons 41 0)
           (cons 42 0)
           (cons 91 0)
           (list 10 13.66666667 -1.60566667)
           (cons 40 0)
           (cons 41 0)
           (cons 42 0)
           (cons 91 0)
           (list 10 14.18 -1.43333333)
           (cons 40 0)
           (cons 41 0)
           (cons 42 0)
           (cons 91 0)
           (list 10 16.82 -1.43333333)
           (cons 40 0)
           (cons 41 0)
           (cons 42 0)
           (cons 91 0)
           (list 10 17.33333333 -1.60566667)
           (cons 40 0)
           (cons 41 0)
           (cons 42 0)
           (cons 91 0)
           (list 10 17.33333333 -2.17766667)
           (cons 40 0)
           (cons 41 0)
           (cons 42 0)
           (cons 91 0)
           (list 10 16.82 -2.35)
           (cons 40 0)
           (cons 41 0)
           (cons 42 0)
           (cons 91 0)
           (list 10 14.18 -2.35)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.66666667 -3.82766667)
           (cons 40 0)
           (cons 41 0)
           (cons 42 0)
           (cons 91 0)
           (list 10 13.66666667 -3.25566667)
           (cons 40 0)
           (cons 41 0)
           (cons 42 0)
           (cons 91 0)
           (list 10 14.18 -3.08333333)
           (cons 40 0)
           (cons 41 0)
           (cons 42 0)
           (cons 91 0)
           (list 10 16.82 -3.08333333)
           (cons 40 0)
           (cons 41 0)
           (cons 42 0)
           (cons 91 0)
           (list 10 17.33333333 -3.25566667)
           (cons 40 0)
           (cons 41 0)
           (cons 42 0)
           (cons 91 0)
           (list 10 17.33333333 -3.82766667)
           (cons 40 0)
           (cons 41 0)
           (cons 42 0)
           (cons 91 0)
           (list 10 16.82 -4)
           (cons 40 0)
           (cons 41 0)
           (cons 42 0)
           (cons 91 0)
           (list 10 14.18 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.66666667 1.60566667)
           (cons 40 0)
           (cons 41 0)
           (cons 42 0)
           (cons 91 0)
           (list 10 13.66666667 2.17766667)
           (cons 40 0)
           (cons 41 0)
           (cons 42 0)
           (cons 91 0)
           (list 10 14.18 2.35)
           (cons 40 0)
           (cons 41 0)
           (cons 42 0)
           (cons 91 0)
           (list 10 16.82 2.35)
           (cons 40 0)
           (cons 41 0)
           (cons 42 0)
           (cons 91 0)
           (list 10 17.33333333 2.17766667)
           (cons 40 0)
           (cons 41 0)
           (cons 42 0)
           (cons 91 0)
           (list 10 17.33333333 1.60566667)
           (cons 40 0)
           (cons 41 0)
           (cons 42 0)
           (cons 91 0)
           (list 10 16.82 1.43333333)
           (cons 40 0)
           (cons 41 0)
           (cons 42 0)
           (cons 91 0)
           (list 10 14.18 1.43333333)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.66666667 3.25566667)
           (cons 40 0)
           (cons 41 0)
           (cons 42 0)
           (cons 91 0)
           (list 10 13.66666667 3.82766667)
           (cons 40 0)
           (cons 41 0)
           (cons 42 0)
           (cons 91 0)
           (list 10 14.18 4)
           (cons 40 0)
           (cons 41 0)
           (cons 42 0)
           (cons 91 0)
           (list 10 16.82 4)
           (cons 40 0)
           (cons 41 0)
           (cons 42 0)
           (cons 91 0)
           (list 10 17.33333333 3.82766667)
           (cons 40 0)
           (cons 41 0)
           (cons 42 0)
           (cons 91 0)
           (list 10 17.33333333 3.25566667)
           (cons 40 0)
           (cons 41 0)
           (cons 42 0)
           (cons 91 0)
           (list 10 16.82 3.08333333)
           (cons 40 0)
           (cons 41 0)
           (cons 42 0)
           (cons 91 0)
           (list 10 14.18 3.08333333)
           (cons 40 0)
           (cons 41 0)
           (cons 42 0)
           (cons 91 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4)
           (cons 40 0)
           (cons 41 0)
           (cons 42 0)
           (cons 91 0)
           (list 10 15.5 -4)
           (cons 40 0)
           (cons 41 0)
           (cons 42 0)
           (cons 91 0)
           (list 10 15.5 4)
           (cons 40 0)
           (cons 41 0)
           (cons 42 0)
           (cons 91 0)
           (list 10 0 4)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 3 -4 0)
           (cons 50 0)
          )
         )
         (entmake
          (list
           (cons 0 "POINT")
           (cons 100 "AcDbEntity")
           (cons 67 0)
           (cons 8 "0")
           (cons 100 "AcDbPoint")
           (list 10 15.5 -4 0)
           (cons 50 0)
          )
         )
         (entmake
          (list
           (cons 0 "POINT")
           (cons 100 "AcDbEntity")
           (cons 67 0)
           (cons 8 "0")
           (cons 100 "AcDbPoint")
           (list 10 15.5 4 0)
           (cons 50 0)
          )
         )
         (entmake
          (list
           (cons 0 "POINT")
           (cons 100 "AcDbEntity")
           (cons 67 0)
           (cons 8 "0")
           (cons 100 "AcDbPoint")
           (list 10 15.5 0 0)
           (cons 50 0)
          )
         )
         (entmake
          (list
           (cons 0 "POINT")
           (cons 100 "AcDbEntity")
           (cons 67 0)
           (cons 8 "0")
           (cons 100 "AcDbPoint")
           (list 10 3 4 0)
           (cons 50 0)
          )
         )
         (entmake
          (list
           (cons 0 "POINT")
           (cons 100 "AcDbEntity")
           (cons 67 0)
           (cons 8 "0")
           (cons 100 "AcDbPoint")
           (list 10 0 4 0)
           (cons 50 0)
          )
         )
         (entmake
          (list
           (cons 0 "POINT")
           (cons 100 "AcDbEntity")
           (cons 67 0)
           (cons 8 "0")
           (cons 100 "AcDbPoint")
           (list 10 0 -4 0)
           (cons 50 0)
          )
         )
         (entmake
          (list
           (cons 0 "POINT")
           (cons 100 "AcDbEntity")
           (cons 67 0)
           (cons 8 "0")
           (cons 100 "AcDbPoint")
           (list 10 3 0 0)
           (cons 50 0)
          )
         )
         (entmake
          (list
           (cons 0 "INSERT")
           (cons 100 "AcDbEntity")
           (cons 67 0)
           (cons 8 "0")
           (cons 100 "AcDbBlockReference")
           (cons 2 "WheelLeft1")
           (list 10 3 -3.08333333 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRight1")
           (list 10 3 3.08333333 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 0.70341207 1.85914261 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 0.76552931 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -0.32808399 0)
           (cons 40 0.65616798)
           (cons 1 "15.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -1.42169729 0)
           (cons 40 0.65616798)
           (cons 1 "15.500")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -2.51531059 0)
           (cons 40 0.65616798)
           (cons 1 "20.3")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-SU-40"))
        (progn
         (entmake)
         (entmake
          (list
           (cons 0 "BLOCK")
           (cons 2 "AASHTO-2011-SU-40")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 39.5 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 39.5 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 25.13333333 -2.34333333)
           (cons 40 0)
           (cons 41 0)
           (cons 42 0)
           (cons 91 0)
           (list 10 25.13333333 -1.82333333)
           (cons 40 0)
           (cons 41 0)
           (cons 42 0)
           (cons 91 0)
           (list 10 25.6 -1.66666667)
           (cons 40 0)
           (cons 41 0)
           (cons 42 0)
           (cons 91 0)
           (list 10 28 -1.66666667)
           (cons 40 0)
           (cons 41 0)
           (cons 42 0)
           (cons 91 0)
           (list 10 28.46666667 -1.82333333)
           (cons 40 0)
           (cons 41 0)
           (cons 42 0)
           (cons 91 0)
           (list 10 28.46666667 -2.34333333)
           (cons 40 0)
           (cons 41 0)
           (cons 42 0)
           (cons 91 0)
           (list 10 28 -2.5)
           (cons 40 0)
           (cons 41 0)
           (cons 42 0)
           (cons 91 0)
           (list 10 25.6 -2.5)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 25.13333333 -3.84333333)
           (cons 40 0)
           (cons 41 0)
           (cons 42 0)
           (cons 91 0)
           (list 10 25.13333333 -3.32333333)
           (cons 40 0)
           (cons 41 0)
           (cons 42 0)
           (cons 91 0)
           (list 10 25.6 -3.16666667)
           (cons 40 0)
           (cons 41 0)
           (cons 42 0)
           (cons 91 0)
           (list 10 28 -3.16666667)
           (cons 40 0)
           (cons 41 0)
           (cons 42 0)
           (cons 91 0)
           (list 10 28.46666667 -3.32333333)
           (cons 40 0)
           (cons 41 0)
           (cons 42 0)
           (cons 91 0)
           (list 10 28.46666667 -3.84333333)
           (cons 40 0)
           (cons 41 0)
           (cons 42 0)
           (cons 91 0)
           (list 10 28 -4)
           (cons 40 0)
           (cons 41 0)
           (cons 42 0)
           (cons 91 0)
           (list 10 25.6 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 25.13333333 1.82333333)
           (cons 40 0)
           (cons 41 0)
           (cons 42 0)
           (cons 91 0)
           (list 10 25.13333333 2.34333333)
           (cons 40 0)
           (cons 41 0)
           (cons 42 0)
           (cons 91 0)
           (list 10 25.6 2.5)
           (cons 40 0)
           (cons 41 0)
           (cons 42 0)
           (cons 91 0)
           (list 10 28 2.5)
           (cons 40 0)
           (cons 41 0)
           (cons 42 0)
           (cons 91 0)
           (list 10 28.46666667 2.34333333)
           (cons 40 0)
           (cons 41 0)
           (cons 42 0)
           (cons 91 0)
           (list 10 28.46666667 1.82333333)
           (cons 40 0)
           (cons 41 0)
           (cons 42 0)
           (cons 91 0)
           (list 10 28 1.66666667)
           (cons 40 0)
           (cons 41 0)
           (cons 42 0)
           (cons 91 0)
           (list 10 25.6 1.66666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 25.13333333 3.32333333)
           (cons 40 0)
           (cons 41 0)
           (cons 42 0)
           (cons 91 0)
           (list 10 25.13333333 3.84333333)
           (cons 40 0)
           (cons 41 0)
           (cons 42 0)
           (cons 91 0)
           (list 10 25.6 4)
           (cons 40 0)
           (cons 41 0)
           (cons 42 0)
           (cons 91 0)
           (list 10 28 4)
           (cons 40 0)
           (cons 41 0)
           (cons 42 0)
           (cons 91 0)
           (list 10 28.46666667 3.84333333)
           (cons 40 0)
           (cons 41 0)
           (cons 42 0)
           (cons 91 0)
           (list 10 28.46666667 3.32333333)
           (cons 40 0)
           (cons 41 0)
           (cons 42 0)
           (cons 91 0)
           (list 10 28 3.16666667)
           (cons 40 0)
           (cons 41 0)
           (cons 42 0)
           (cons 91 0)
           (list 10 25.6 3.16666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 29.53333333 -2.34333333)
           (cons 40 0)
           (cons 41 0)
           (cons 42 0)
           (cons 91 0)
           (list 10 29.53333333 -1.82333333)
           (cons 40 0)
           (cons 41 0)
           (cons 42 0)
           (cons 91 0)
           (list 10 30 -1.66666667)
           (cons 40 0)
           (cons 41 0)
           (cons 42 0)
           (cons 91 0)
           (list 10 32.4 -1.66666667)
           (cons 40 0)
           (cons 41 0)
           (cons 42 0)
           (cons 91 0)
           (list 10 32.86666667 -1.82333333)
           (cons 40 0)
           (cons 41 0)
           (cons 42 0)
           (cons 91 0)
           (list 10 32.86666667 -2.34333333)
           (cons 40 0)
           (cons 41 0)
           (cons 42 0)
           (cons 91 0)
           (list 10 32.4 -2.5)
           (cons 40 0)
           (cons 41 0)
           (cons 42 0)
           (cons 91 0)
           (list 10 30 -2.5)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 29.53333333 -3.84333333)
           (cons 40 0)
           (cons 41 0)
           (cons 42 0)
           (cons 91 0)
           (list 10 29.53333333 -3.32333333)
           (cons 40 0)
           (cons 41 0)
           (cons 42 0)
           (cons 91 0)
           (list 10 30 -3.16666667)
           (cons 40 0)
           (cons 41 0)
           (cons 42 0)
           (cons 91 0)
           (list 10 32.4 -3.16666667)
           (cons 40 0)
           (cons 41 0)
           (cons 42 0)
           (cons 91 0)
           (list 10 32.86666667 -3.32333333)
           (cons 40 0)
           (cons 41 0)
           (cons 42 0)
           (cons 91 0)
           (list 10 32.86666667 -3.84333333)
           (cons 40 0)
           (cons 41 0)
           (cons 42 0)
           (cons 91 0)
           (list 10 32.4 -4)
           (cons 40 0)
           (cons 41 0)
           (cons 42 0)
           (cons 91 0)
           (list 10 30 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 29.53333333 1.82333333)
           (cons 40 0)
           (cons 41 0)
           (cons 42 0)
           (cons 91 0)
           (list 10 29.53333333 2.34333333)
           (cons 40 0)
           (cons 41 0)
           (cons 42 0)
           (cons 91 0)
           (list 10 30 2.5)
           (cons 40 0)
           (cons 41 0)
           (cons 42 0)
           (cons 91 0)
           (list 10 32.4 2.5)
           (cons 40 0)
           (cons 41 0)
           (cons 42 0)
           (cons 91 0)
           (list 10 32.86666667 2.34333333)
           (cons 40 0)
           (cons 41 0)
           (cons 42 0)
           (cons 91 0)
           (list 10 32.86666667 1.82333333)
           (cons 40 0)
           (cons 41 0)
           (cons 42 0)
           (cons 91 0)
           (list 10 32.4 1.66666667)
           (cons 40 0)
           (cons 41 0)
           (cons 42 0)
           (cons 91 0)
           (list 10 30 1.66666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 29.53333333 3.32333333)
           (cons 40 0)
           (cons 41 0)
           (cons 42 0)
           (cons 91 0)
           (list 10 29.53333333 3.84333333)
           (cons 40 0)
           (cons 41 0)
           (cons 42 0)
           (cons 91 0)
           (list 10 30 4)
           (cons 40 0)
           (cons 41 0)
           (cons 42 0)
           (cons 91 0)
           (list 10 32.4 4)
           (cons 40 0)
           (cons 41 0)
           (cons 42 0)
           (cons 91 0)
           (list 10 32.86666667 3.84333333)
           (cons 40 0)
           (cons 41 0)
           (cons 42 0)
           (cons 91 0)
           (list 10 32.86666667 3.32333333)
           (cons 40 0)
           (cons 41 0)
           (cons 42 0)
           (cons 91 0)
           (list 10 32.4 3.16666667)
           (cons 40 0)
           (cons 41 0)
           (cons 42 0)
           (cons 91 0)
           (list 10 30 3.16666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4 0)
           (cons 50 0)
          )
         )
         (entmake
          (list
           (cons 0 "POINT")
           (cons 100 "AcDbEntity")
           (cons 67 0)
           (cons 8 "0")
           (cons 100 "AcDbPoint")
           (list 10 0 4 0)
           (cons 50 0)
          )
         )
         (entmake
          (list
           (cons 0 "POINT")
           (cons 100 "AcDbEntity")
           (cons 67 0)
           (cons 8 "0")
           (cons 100 "AcDbPoint")
           (list 10 4 4 0)
           (cons 50 0)
          )
         )
         (entmake
          (list
           (cons 0 "POINT")
           (cons 100 "AcDbEntity")
           (cons 67 0)
           (cons 8 "0")
           (cons 100 "AcDbPoint")
           (list 10 29 4 0)
           (cons 50 0)
          )
         )
         (entmake
          (list
           (cons 0 "POINT")
           (cons 100 "AcDbEntity")
           (cons 67 0)
           (cons 8 "0")
           (cons 100 "AcDbPoint")
           (list 10 39.5 4 0)
           (cons 50 0)
          )
         )
         (entmake
          (list
           (cons 0 "POINT")
           (cons 100 "AcDbEntity")
           (cons 67 0)
           (cons 8 "0")
           (cons 100 "AcDbPoint")
           (list 10 39.5 -4 0)
           (cons 50 0)
          )
         )
         (entmake
          (list
           (cons 0 "POINT")
           (cons 100 "AcDbEntity")
           (cons 67 0)
           (cons 8 "0")
           (cons 100 "AcDbPoint")
           (list 10 29 -4 0)
           (cons 50 0)
          )
         )
         (entmake
          (list
           (cons 0 "POINT")
           (cons 100 "AcDbEntity")
           (cons 67 0)
           (cons 8 "0")
           (cons 100 "AcDbPoint")
           (list 10 4 -4 0)
           (cons 50 0)
          )
         )
         (entmake
          (list
           (cons 0 "POINT")
           (cons 100 "AcDbEntity")
           (cons 67 0)
           (cons 8 "0")
           (cons 100 "AcDbPoint")
           (list 10 4 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4)
           (cons 40 0)
           (cons 41 0)
           (cons 42 0)
           (cons 91 0)
           (list 10 39.5 -4)
           (cons 40 0)
           (cons 41 0)
           (cons 42 0)
           (cons 91 0)
           (list 10 39.5 4)
           (cons 40 0)
           (cons 41 0)
           (cons 42 0)
           (cons 91 0)
           (list 10 0 4)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelRight2")
           (list 10 4 3.16666667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeft2")
           (list 10 4 -3.16666667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 1.70341207 1.85914261 0)
           (cons 40 0.65616798)
           (cons 1 "4.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 0.76552931 0)
           (cons 40 0.65616798)
           (cons 1 "4.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -0.32808399 0)
           (cons 40 0.65616798)
           (cons 1 "29.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -2.51531059 0)
           (cons 40 0.65616798)
           (cons 1 "31.8")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-SU-30"))
        (progn
         (entmake)
         (entmake
          (list
           (cons 0 "BLOCK")
           (cons 2 "AASHTO-2011-SU-30")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 30 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 30 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 22.33333333 -2.34333333)
           (cons 40 0)
           (cons 41 0)
           (cons 42 0)
           (cons 91 0)
           (list 10 22.33333333 -1.82333333)
           (cons 40 0)
           (cons 41 0)
           (cons 42 0)
           (cons 91 0)
           (list 10 22.8 -1.66666667)
           (cons 40 0)
           (cons 41 0)
           (cons 42 0)
           (cons 91 0)
           (list 10 25.2 -1.66666667)
           (cons 40 0)
           (cons 41 0)
           (cons 42 0)
           (cons 91 0)
           (list 10 25.66666667 -1.82333333)
           (cons 40 0)
           (cons 41 0)
           (cons 42 0)
           (cons 91 0)
           (list 10 25.66666667 -2.34333333)
           (cons 40 0)
           (cons 41 0)
           (cons 42 0)
           (cons 91 0)
           (list 10 25.2 -2.5)
           (cons 40 0)
           (cons 41 0)
           (cons 42 0)
           (cons 91 0)
           (list 10 22.8 -2.5)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 22.33333333 -3.84333333)
           (cons 40 0)
           (cons 41 0)
           (cons 42 0)
           (cons 91 0)
           (list 10 22.33333333 -3.32333333)
           (cons 40 0)
           (cons 41 0)
           (cons 42 0)
           (cons 91 0)
           (list 10 22.8 -3.16666667)
           (cons 40 0)
           (cons 41 0)
           (cons 42 0)
           (cons 91 0)
           (list 10 25.2 -3.16666667)
           (cons 40 0)
           (cons 41 0)
           (cons 42 0)
           (cons 91 0)
           (list 10 25.66666667 -3.32333333)
           (cons 40 0)
           (cons 41 0)
           (cons 42 0)
           (cons 91 0)
           (list 10 25.66666667 -3.84333333)
           (cons 40 0)
           (cons 41 0)
           (cons 42 0)
           (cons 91 0)
           (list 10 25.2 -4)
           (cons 40 0)
           (cons 41 0)
           (cons 42 0)
           (cons 91 0)
           (list 10 22.8 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 22.33333333 1.82333333)
           (cons 40 0)
           (cons 41 0)
           (cons 42 0)
           (cons 91 0)
           (list 10 22.33333333 2.34333333)
           (cons 40 0)
           (cons 41 0)
           (cons 42 0)
           (cons 91 0)
           (list 10 22.8 2.5)
           (cons 40 0)
           (cons 41 0)
           (cons 42 0)
           (cons 91 0)
           (list 10 25.2 2.5)
           (cons 40 0)
           (cons 41 0)
           (cons 42 0)
           (cons 91 0)
           (list 10 25.66666667 2.34333333)
           (cons 40 0)
           (cons 41 0)
           (cons 42 0)
           (cons 91 0)
           (list 10 25.66666667 1.82333333)
           (cons 40 0)
           (cons 41 0)
           (cons 42 0)
           (cons 91 0)
           (list 10 25.2 1.66666667)
           (cons 40 0)
           (cons 41 0)
           (cons 42 0)
           (cons 91 0)
           (list 10 22.8 1.66666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 22.33333333 3.32333333)
           (cons 40 0)
           (cons 41 0)
           (cons 42 0)
           (cons 91 0)
           (list 10 22.33333333 3.84333333)
           (cons 40 0)
           (cons 41 0)
           (cons 42 0)
           (cons 91 0)
           (list 10 22.8 4)
           (cons 40 0)
           (cons 41 0)
           (cons 42 0)
           (cons 91 0)
           (list 10 25.2 4)
           (cons 40 0)
           (cons 41 0)
           (cons 42 0)
           (cons 91 0)
           (list 10 25.66666667 3.84333333)
           (cons 40 0)
           (cons 41 0)
           (cons 42 0)
           (cons 91 0)
           (list 10 25.66666667 3.32333333)
           (cons 40 0)
           (cons 41 0)
           (cons 42 0)
           (cons 91 0)
           (list 10 25.2 3.16666667)
           (cons 40 0)
           (cons 41 0)
           (cons 42 0)
           (cons 91 0)
           (list 10 22.8 3.16666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 4 0 0)
           (cons 50 0)
          )
         )
         (entmake
          (list
           (cons 0 "POINT")
           (cons 100 "AcDbEntity")
           (cons 67 0)
           (cons 8 "0")
           (cons 100 "AcDbPoint")
           (list 10 0 -4 0)
           (cons 50 0)
          )
         )
         (entmake
          (list
           (cons 0 "POINT")
           (cons 100 "AcDbEntity")
           (cons 67 0)
           (cons 8 "0")
           (cons 100 "AcDbPoint")
           (list 10 4 -4 0)
           (cons 50 0)
          )
         )
         (entmake
          (list
           (cons 0 "POINT")
           (cons 100 "AcDbEntity")
           (cons 67 0)
           (cons 8 "0")
           (cons 100 "AcDbPoint")
           (list 10 24 -4 0)
           (cons 50 0)
          )
         )
         (entmake
          (list
           (cons 0 "POINT")
           (cons 100 "AcDbEntity")
           (cons 67 0)
           (cons 8 "0")
           (cons 100 "AcDbPoint")
           (list 10 30 -4 0)
           (cons 50 0)
          )
         )
         (entmake
          (list
           (cons 0 "POINT")
           (cons 100 "AcDbEntity")
           (cons 67 0)
           (cons 8 "0")
           (cons 100 "AcDbPoint")
           (list 10 30 4 0)
           (cons 50 0)
          )
         )
         (entmake
          (list
           (cons 0 "POINT")
           (cons 100 "AcDbEntity")
           (cons 67 0)
           (cons 8 "0")
           (cons 100 "AcDbPoint")
           (list 10 24 4 0)
           (cons 50 0)
          )
         )
         (entmake
          (list
           (cons 0 "POINT")
           (cons 100 "AcDbEntity")
           (cons 67 0)
           (cons 8 "0")
           (cons 100 "AcDbPoint")
           (list 10 4 4 0)
           (cons 50 0)
          )
         )
         (entmake
          (list
           (cons 0 "POINT")
           (cons 100 "AcDbEntity")
           (cons 67 0)
           (cons 8 "0")
           (cons 100 "AcDbPoint")
           (list 10 0 4 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4)
           (cons 40 0)
           (cons 41 0)
           (cons 42 0)
           (cons 91 0)
           (list 10 30 -4)
           (cons 40 0)
           (cons 41 0)
           (cons 42 0)
           (cons 91 0)
           (list 10 30 4)
           (cons 40 0)
           (cons 41 0)
           (cons 42 0)
           (cons 91 0)
           (list 10 0 4)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelRight2")
           (list 10 4 3.16666667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeft2")
           (list 10 4 -3.16666667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 1.70341207 1.85914261 0)
           (cons 40 0.65616798)
           (cons 1 "4.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 0.76552931 0)
           (cons 40 0.65616798)
           (cons 1 "4.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -0.32808399 0)
           (cons 40 0.65616798)
           (cons 1 "24.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -2.51531059 0)
           (cons 40 0.65616798)
           (cons 1 "31.8")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-S-BUS-40"))
        (progn
         (entmake)
         (entmake
          (list
           (cons 0 "BLOCK")
           (cons 2 "AASHTO-2011-S-BUS-40")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 39.99343832 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 39.99343832 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 25.33333333 -3.84333333)
           (cons 40 0)
           (cons 41 0)
           (cons 42 0)
           (cons 91 0)
           (list 10 25.33333333 -3.32333333)
           (cons 40 0)
           (cons 41 0)
           (cons 42 0)
           (cons 91 0)
           (list 10 25.8 -3.16666667)
           (cons 40 0)
           (cons 41 0)
           (cons 42 0)
           (cons 91 0)
           (list 10 28.2 -3.16666667)
           (cons 40 0)
           (cons 41 0)
           (cons 42 0)
           (cons 91 0)
           (list 10 28.66666667 -3.32333333)
           (cons 40 0)
           (cons 41 0)
           (cons 42 0)
           (cons 91 0)
           (list 10 28.66666667 -3.84333333)
           (cons 40 0)
           (cons 41 0)
           (cons 42 0)
           (cons 91 0)
           (list 10 28.2 -4)
           (cons 40 0)
           (cons 41 0)
           (cons 42 0)
           (cons 91 0)
           (list 10 25.8 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 25.33333333 3.32333333)
           (cons 40 0)
           (cons 41 0)
           (cons 42 0)
           (cons 91 0)
           (list 10 25.33333333 3.84333333)
           (cons 40 0)
           (cons 41 0)
           (cons 42 0)
           (cons 91 0)
           (list 10 25.8 4)
           (cons 40 0)
           (cons 41 0)
           (cons 42 0)
           (cons 91 0)
           (list 10 28.2 4)
           (cons 40 0)
           (cons 41 0)
           (cons 42 0)
           (cons 91 0)
           (list 10 28.66666667 3.84333333)
           (cons 40 0)
           (cons 41 0)
           (cons 42 0)
           (cons 91 0)
           (list 10 28.66666667 3.32333333)
           (cons 40 0)
           (cons 41 0)
           (cons 42 0)
           (cons 91 0)
           (list 10 28.2 3.16666667)
           (cons 40 0)
           (cons 41 0)
           (cons 42 0)
           (cons 91 0)
           (list 10 25.8 3.16666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4 0)
           (cons 50 0)
          )
         )
         (entmake
          (list
           (cons 0 "POINT")
           (cons 100 "AcDbEntity")
           (cons 67 0)
           (cons 8 "0")
           (cons 100 "AcDbPoint")
           (list 10 7 -4 0)
           (cons 50 0)
          )
         )
         (entmake
          (list
           (cons 0 "POINT")
           (cons 100 "AcDbEntity")
           (cons 67 0)
           (cons 8 "0")
           (cons 100 "AcDbPoint")
           (list 10 27 -4 0)
           (cons 50 0)
          )
         )
         (entmake
          (list
           (cons 0 "POINT")
           (cons 100 "AcDbEntity")
           (cons 67 0)
           (cons 8 "0")
           (cons 100 "AcDbPoint")
           (list 10 39.99343832 -4 0)
           (cons 50 0)
          )
         )
         (entmake
          (list
           (cons 0 "POINT")
           (cons 100 "AcDbEntity")
           (cons 67 0)
           (cons 8 "0")
           (cons 100 "AcDbPoint")
           (list 10 39.99343832 4 0)
           (cons 50 0)
          )
         )
         (entmake
          (list
           (cons 0 "POINT")
           (cons 100 "AcDbEntity")
           (cons 67 0)
           (cons 8 "0")
           (cons 100 "AcDbPoint")
           (list 10 27 4 0)
           (cons 50 0)
          )
         )
         (entmake
          (list
           (cons 0 "POINT")
           (cons 100 "AcDbEntity")
           (cons 67 0)
           (cons 8 "0")
           (cons 100 "AcDbPoint")
           (list 10 7 4 0)
           (cons 50 0)
          )
         )
         (entmake
          (list
           (cons 0 "POINT")
           (cons 100 "AcDbEntity")
           (cons 67 0)
           (cons 8 "0")
           (cons 100 "AcDbPoint")
           (list 10 0 4 0)
           (cons 50 0)
          )
         )
         (entmake
          (list
           (cons 0 "POINT")
           (cons 100 "AcDbEntity")
           (cons 67 0)
           (cons 8 "0")
           (cons 100 "AcDbPoint")
           (list 10 7 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4)
           (cons 40 0)
           (cons 41 0)
           (cons 42 0)
           (cons 91 0)
           (list 10 39.99343832 -4)
           (cons 40 0)
           (cons 41 0)
           (cons 42 0)
           (cons 91 0)
           (list 10 39.99343832 4)
           (cons 40 0)
           (cons 41 0)
           (cons 42 0)
           (cons 91 0)
           (list 10 0 4)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelRight2")
           (list 10 7 3.16666667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeft2")
           (list 10 7 -3.16666667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 4.70341207 1.85914261 0)
           (cons 40 0.65616798)
           (cons 1 "7.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 4.70341207 0.76552931 0)
           (cons 40 0.65616798)
           (cons 1 "7.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 4.70341207 -0.32808399 0)
           (cons 40 0.65616798)
           (cons 1 "27.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 4.70341207 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 4.70341207 -2.51531059 0)
           (cons 40 0.65616798)
           (cons 1 "34.4")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-S-BUS-36"))
        (progn
         (entmake)
         (entmake
          (list
           (cons 0 "BLOCK")
           (cons 2 "AASHTO-2011-S-BUS-36")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -4)
           (cons 40 0)
           (cons 41 0)
           (cons 42 0)
           (cons 91 0)
           (list 10 35.8 -4)
           (cons 40 0)
           (cons 41 0)
           (cons 42 0)
           (cons 91 0)
           (list 10 35.8 4)
           (cons 40 0)
           (cons 41 0)
           (cons 42 0)
           (cons 91 0)
           (list 10 0 4)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 35.8 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 35.8 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 22.13333333 -2.34333333)
           (cons 40 0)
           (cons 41 0)
           (cons 42 0)
           (cons 91 0)
           (list 10 22.13333333 -1.82333333)
           (cons 40 0)
           (cons 41 0)
           (cons 42 0)
           (cons 91 0)
           (list 10 22.6 -1.66666667)
           (cons 40 0)
           (cons 41 0)
           (cons 42 0)
           (cons 91 0)
           (list 10 25 -1.66666667)
           (cons 40 0)
           (cons 41 0)
           (cons 42 0)
           (cons 91 0)
           (list 10 25.46666667 -1.82333333)
           (cons 40 0)
           (cons 41 0)
           (cons 42 0)
           (cons 91 0)
           (list 10 25.46666667 -2.34333333)
           (cons 40 0)
           (cons 41 0)
           (cons 42 0)
           (cons 91 0)
           (list 10 25 -2.5)
           (cons 40 0)
           (cons 41 0)
           (cons 42 0)
           (cons 91 0)
           (list 10 22.6 -2.5)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 22.13333333 -3.84333333)
           (cons 40 0)
           (cons 41 0)
           (cons 42 0)
           (cons 91 0)
           (list 10 22.13333333 -3.32333333)
           (cons 40 0)
           (cons 41 0)
           (cons 42 0)
           (cons 91 0)
           (list 10 22.6 -3.16666667)
           (cons 40 0)
           (cons 41 0)
           (cons 42 0)
           (cons 91 0)
           (list 10 25 -3.16666667)
           (cons 40 0)
           (cons 41 0)
           (cons 42 0)
           (cons 91 0)
           (list 10 25.46666667 -3.32333333)
           (cons 40 0)
           (cons 41 0)
           (cons 42 0)
           (cons 91 0)
           (list 10 25.46666667 -3.84333333)
           (cons 40 0)
           (cons 41 0)
           (cons 42 0)
           (cons 91 0)
           (list 10 25 -4)
           (cons 40 0)
           (cons 41 0)
           (cons 42 0)
           (cons 91 0)
           (list 10 22.6 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 22.13333333 1.82333333)
           (cons 40 0)
           (cons 41 0)
           (cons 42 0)
           (cons 91 0)
           (list 10 22.13333333 2.34333333)
           (cons 40 0)
           (cons 41 0)
           (cons 42 0)
           (cons 91 0)
           (list 10 22.6 2.5)
           (cons 40 0)
           (cons 41 0)
           (cons 42 0)
           (cons 91 0)
           (list 10 25 2.5)
           (cons 40 0)
           (cons 41 0)
           (cons 42 0)
           (cons 91 0)
           (list 10 25.46666667 2.34333333)
           (cons 40 0)
           (cons 41 0)
           (cons 42 0)
           (cons 91 0)
           (list 10 25.46666667 1.82333333)
           (cons 40 0)
           (cons 41 0)
           (cons 42 0)
           (cons 91 0)
           (list 10 25 1.66666667)
           (cons 40 0)
           (cons 41 0)
           (cons 42 0)
           (cons 91 0)
           (list 10 22.6 1.66666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 22.13333333 3.32333333)
           (cons 40 0)
           (cons 41 0)
           (cons 42 0)
           (cons 91 0)
           (list 10 22.13333333 3.84333333)
           (cons 40 0)
           (cons 41 0)
           (cons 42 0)
           (cons 91 0)
           (list 10 22.6 4)
           (cons 40 0)
           (cons 41 0)
           (cons 42 0)
           (cons 91 0)
           (list 10 25 4)
           (cons 40 0)
           (cons 41 0)
           (cons 42 0)
           (cons 91 0)
           (list 10 25.46666667 3.84333333)
           (cons 40 0)
           (cons 41 0)
           (cons 42 0)
           (cons 91 0)
           (list 10 25.46666667 3.32333333)
           (cons 40 0)
           (cons 41 0)
           (cons 42 0)
           (cons 91 0)
           (list 10 25 3.16666667)
           (cons 40 0)
           (cons 41 0)
           (cons 42 0)
           (cons 91 0)
           (list 10 22.6 3.16666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4 0)
           (cons 50 0)
          )
         )
         (entmake
          (list
           (cons 0 "POINT")
           (cons 100 "AcDbEntity")
           (cons 67 0)
           (cons 8 "0")
           (cons 100 "AcDbPoint")
           (list 10 0 4 0)
           (cons 50 0)
          )
         )
         (entmake
          (list
           (cons 0 "POINT")
           (cons 100 "AcDbEntity")
           (cons 67 0)
           (cons 8 "0")
           (cons 100 "AcDbPoint")
           (list 10 35.8 4 0)
           (cons 50 0)
          )
         )
         (entmake
          (list
           (cons 0 "POINT")
           (cons 100 "AcDbEntity")
           (cons 67 0)
           (cons 8 "0")
           (cons 100 "AcDbPoint")
           (list 10 35.8 -4 0)
           (cons 50 0)
          )
         )
         (entmake
          (list
           (cons 0 "POINT")
           (cons 100 "AcDbEntity")
           (cons 67 0)
           (cons 8 "0")
           (cons 100 "AcDbPoint")
           (list 10 23.8 -4 0)
           (cons 50 0)
          )
         )
         (entmake
          (list
           (cons 0 "POINT")
           (cons 100 "AcDbEntity")
           (cons 67 0)
           (cons 8 "0")
           (cons 100 "AcDbPoint")
           (list 10 23.8 4 0)
           (cons 50 0)
          )
         )
         (entmake
          (list
           (cons 0 "POINT")
           (cons 100 "AcDbEntity")
           (cons 67 0)
           (cons 8 "0")
           (cons 100 "AcDbPoint")
           (list 10 2.5 0 0)
           (cons 50 0)
          )
         )
         (entmake
          (list
           (cons 0 "POINT")
           (cons 100 "AcDbEntity")
           (cons 67 0)
           (cons 8 "0")
           (cons 100 "AcDbPoint")
           (list 10 2.5 -4 0)
           (cons 50 0)
          )
         )
         (entmake
          (list
           (cons 0 "POINT")
           (cons 100 "AcDbEntity")
           (cons 67 0)
           (cons 8 "0")
           (cons 100 "AcDbPoint")
           (list 10 2.5 4 0)
           (cons 50 0)
          )
         )
         (entmake
          (list
           (cons 0 "INSERT")
           (cons 100 "AcDbEntity")
           (cons 67 0)
           (cons 8 "0")
           (cons 100 "AcDbBlockReference")
           (cons 2 "WheelRight2")
           (list 10 2.5 3.16666667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeft2")
           (list 10 2.5 -3.16666667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 0.20341207 1.85914261 0)
           (cons 40 0.65616798)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 0.76552931 0)
           (cons 40 0.65616798)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -0.32808399 0)
           (cons 40 0.65616798)
           (cons 1 "23.800")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.20341207 -2.51531059 0)
           (cons 40 0.65616798)
           (cons 1 "37.6")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-T"))
        (progn
         (entmake)
         (entmake
          (list
           (cons 0 "BLOCK")
           (cons 2 "AASHTO-2011-T")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 5)
           (cons 70 129)
           (cons 43 0)
           (cons 38 0)
           (cons 39 0)
           (list 10 0 0)
           (cons 40 0)
           (cons 41 0)
           (cons 42 0)
           (cons 91 0)
           (list 10 3 4)
           (cons 40 0)
           (cons 41 0)
           (cons 42 0)
           (cons 91 0)
           (list 10 29.7 4)
           (cons 40 0)
           (cons 41 0)
           (cons 42 0)
           (cons 91 0)
           (list 10 29.7 -4)
           (cons 40 0)
           (cons 41 0)
           (cons 42 0)
           (cons 91 0)
           (list 10 3 -4)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 29.7 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 29.7 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 3 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.53333333)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.46666667 -3.90208333)
           (cons 40 0)
           (cons 41 0)
           (cons 42 0)
           (cons 91 0)
           (list 10 14.46666667 -3.57708333)
           (cons 40 0)
           (cons 41 0)
           (cons 42 0)
           (cons 91 0)
           (list 10 14.78866667 -3.47916667)
           (cons 40 0)
           (cons 41 0)
           (cons 42 0)
           (cons 91 0)
           (list 10 16.44466667 -3.47916667)
           (cons 40 0)
           (cons 41 0)
           (cons 42 0)
           (cons 91 0)
           (list 10 16.76666667 -3.57708333)
           (cons 40 0)
           (cons 41 0)
           (cons 42 0)
           (cons 91 0)
           (list 10 16.76666667 -3.90208333)
           (cons 40 0)
           (cons 41 0)
           (cons 42 0)
           (cons 91 0)
           (list 10 16.44466667 -4)
           (cons 40 0)
           (cons 41 0)
           (cons 42 0)
           (cons 91 0)
           (list 10 14.78866667 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.46666667 3.57708333)
           (cons 40 0)
           (cons 41 0)
           (cons 42 0)
           (cons 91 0)
           (list 10 14.46666667 3.90208333)
           (cons 40 0)
           (cons 41 0)
           (cons 42 0)
           (cons 91 0)
           (list 10 14.78866667 4)
           (cons 40 0)
           (cons 41 0)
           (cons 42 0)
           (cons 91 0)
           (list 10 16.44466667 4)
           (cons 40 0)
           (cons 41 0)
           (cons 42 0)
           (cons 91 0)
           (list 10 16.76666667 3.90208333)
           (cons 40 0)
           (cons 41 0)
           (cons 42 0)
           (cons 91 0)
           (list 10 16.76666667 3.57708333)
           (cons 40 0)
           (cons 41 0)
           (cons 42 0)
           (cons 91 0)
           (list 10 16.44466667 3.47916667)
           (cons 40 0)
           (cons 41 0)
           (cons 42 0)
           (cons 91 0)
           (list 10 14.78866667 3.47916667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 18.63333333 -3.90208333)
           (cons 40 0)
           (cons 41 0)
           (cons 42 0)
           (cons 91 0)
           (list 10 18.63333333 -3.57708333)
           (cons 40 0)
           (cons 41 0)
           (cons 42 0)
           (cons 91 0)
           (list 10 18.95533333 -3.47916667)
           (cons 40 0)
           (cons 41 0)
           (cons 42 0)
           (cons 91 0)
           (list 10 20.61133333 -3.47916667)
           (cons 40 0)
           (cons 41 0)
           (cons 42 0)
           (cons 91 0)
           (list 10 20.93333333 -3.57708333)
           (cons 40 0)
           (cons 41 0)
           (cons 42 0)
           (cons 91 0)
           (list 10 20.93333333 -3.90208333)
           (cons 40 0)
           (cons 41 0)
           (cons 42 0)
           (cons 91 0)
           (list 10 20.61133333 -4)
           (cons 40 0)
           (cons 41 0)
           (cons 42 0)
           (cons 91 0)
           (list 10 18.95533333 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 18.63333333 3.57708333)
           (cons 40 0)
           (cons 41 0)
           (cons 42 0)
           (cons 91 0)
           (list 10 18.63333333 3.90208333)
           (cons 40 0)
           (cons 41 0)
           (cons 42 0)
           (cons 91 0)
           (list 10 18.95533333 4)
           (cons 40 0)
           (cons 41 0)
           (cons 42 0)
           (cons 91 0)
           (list 10 20.61133333 4)
           (cons 40 0)
           (cons 41 0)
           (cons 42 0)
           (cons 91 0)
           (list 10 20.93333333 3.90208333)
           (cons 40 0)
           (cons 41 0)
           (cons 42 0)
           (cons 91 0)
           (list 10 20.93333333 3.57708333)
           (cons 40 0)
           (cons 41 0)
           (cons 42 0)
           (cons 91 0)
           (list 10 20.61133333 3.47916667)
           (cons 40 0)
           (cons 41 0)
           (cons 42 0)
           (cons 91 0)
           (list 10 18.95533333 3.47916667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 3 -4 0)
           (cons 50 0)
          )
         )
         (entmake
          (list
           (cons 0 "POINT")
           (cons 100 "AcDbEntity")
           (cons 67 0)
           (cons 8 "0")
           (cons 100 "AcDbPoint")
           (list 10 3 4 0)
           (cons 50 0)
          )
         )
         (entmake
          (list
           (cons 0 "POINT")
           (cons 100 "AcDbEntity")
           (cons 67 0)
           (cons 8 "0")
           (cons 100 "AcDbPoint")
           (list 10 29.7 4 0)
           (cons 50 0)
          )
         )
         (entmake
          (list
           (cons 0 "POINT")
           (cons 100 "AcDbEntity")
           (cons 67 0)
           (cons 8 "0")
           (cons 100 "AcDbPoint")
           (list 10 29.7 -4 0)
           (cons 50 0)
          )
         )
         (entmake
          (list
           (cons 0 "POINT")
           (cons 100 "AcDbEntity")
           (cons 67 0)
           (cons 8 "0")
           (cons 100 "AcDbPoint")
           (list 10 17.7 -4 0)
           (cons 50 0)
          )
         )
         (entmake
          (list
           (cons 0 "POINT")
           (cons 100 "AcDbEntity")
           (cons 67 0)
           (cons 8 "0")
           (cons 100 "AcDbPoint")
           (list 10 17.7 4 0)
           (cons 50 0)
          )
         )
         (entmake
          (list
           (cons 0 "ATTDEF")
           (cons 100 "AcDbEntity")
           (cons 67 0)
           (cons 8 "0")
           (cons 100 "AcDbText")
           (list 10 -2.29658793 1.85914261 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 0.76552931 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -0.32808399 0)
           (cons 40 0.65616798)
           (cons 1 "17.700")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-MH"))
        (progn
         (entmake)
         (entmake
          (list
           (cons 0 "BLOCK")
           (cons 2 "AASHTO-2011-MH")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 -4)
           (cons 40 0)
           (cons 41 0)
           (cons 42 0)
           (cons 91 0)
           (list 10 30 -4)
           (cons 40 0)
           (cons 41 0)
           (cons 42 0)
           (cons 91 0)
           (list 10 30 4)
           (cons 40 0)
           (cons 41 0)
           (cons 42 0)
           (cons 91 0)
           (list 10 0 4)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 30 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 30 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 22.33333333 -3.84333333)
           (cons 40 0)
           (cons 41 0)
           (cons 42 0)
           (cons 91 0)
           (list 10 22.33333333 -3.32333333)
           (cons 40 0)
           (cons 41 0)
           (cons 42 0)
           (cons 91 0)
           (list 10 22.8 -3.16666667)
           (cons 40 0)
           (cons 41 0)
           (cons 42 0)
           (cons 91 0)
           (list 10 25.2 -3.16666667)
           (cons 40 0)
           (cons 41 0)
           (cons 42 0)
           (cons 91 0)
           (list 10 25.66666667 -3.32333333)
           (cons 40 0)
           (cons 41 0)
           (cons 42 0)
           (cons 91 0)
           (list 10 25.66666667 -3.84333333)
           (cons 40 0)
           (cons 41 0)
           (cons 42 0)
           (cons 91 0)
           (list 10 25.2 -4)
           (cons 40 0)
           (cons 41 0)
           (cons 42 0)
           (cons 91 0)
           (list 10 22.8 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 22.33333333 3.32333333)
           (cons 40 0)
           (cons 41 0)
           (cons 42 0)
           (cons 91 0)
           (list 10 22.33333333 3.84333333)
           (cons 40 0)
           (cons 41 0)
           (cons 42 0)
           (cons 91 0)
           (list 10 22.8 4)
           (cons 40 0)
           (cons 41 0)
           (cons 42 0)
           (cons 91 0)
           (list 10 25.2 4)
           (cons 40 0)
           (cons 41 0)
           (cons 42 0)
           (cons 91 0)
           (list 10 25.66666667 3.84333333)
           (cons 40 0)
           (cons 41 0)
           (cons 42 0)
           (cons 91 0)
           (list 10 25.66666667 3.32333333)
           (cons 40 0)
           (cons 41 0)
           (cons 42 0)
           (cons 91 0)
           (list 10 25.2 3.16666667)
           (cons 40 0)
           (cons 41 0)
           (cons 42 0)
           (cons 91 0)
           (list 10 22.8 3.16666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4 0)
           (cons 50 0)
          )
         )
         (entmake
          (list
           (cons 0 "POINT")
           (cons 100 "AcDbEntity")
           (cons 67 0)
           (cons 8 "0")
           (cons 100 "AcDbPoint")
           (list 10 4 -4 0)
           (cons 50 0)
          )
         )
         (entmake
          (list
           (cons 0 "POINT")
           (cons 100 "AcDbEntity")
           (cons 67 0)
           (cons 8 "0")
           (cons 100 "AcDbPoint")
           (list 10 24 -4 0)
           (cons 50 0)
          )
         )
         (entmake
          (list
           (cons 0 "POINT")
           (cons 100 "AcDbEntity")
           (cons 67 0)
           (cons 8 "0")
           (cons 100 "AcDbPoint")
           (list 10 30 -4 0)
           (cons 50 0)
          )
         )
         (entmake
          (list
           (cons 0 "POINT")
           (cons 100 "AcDbEntity")
           (cons 67 0)
           (cons 8 "0")
           (cons 100 "AcDbPoint")
           (list 10 30 4 0)
           (cons 50 0)
          )
         )
         (entmake
          (list
           (cons 0 "POINT")
           (cons 100 "AcDbEntity")
           (cons 67 0)
           (cons 8 "0")
           (cons 100 "AcDbPoint")
           (list 10 24 4 0)
           (cons 50 0)
          )
         )
         (entmake
          (list
           (cons 0 "POINT")
           (cons 100 "AcDbEntity")
           (cons 67 0)
           (cons 8 "0")
           (cons 100 "AcDbPoint")
           (list 10 4 4 0)
           (cons 50 0)
          )
         )
         (entmake
          (list
           (cons 0 "POINT")
           (cons 100 "AcDbEntity")
           (cons 67 0)
           (cons 8 "0")
           (cons 100 "AcDbPoint")
           (list 10 0 4 0)
           (cons 50 0)
          )
         )
         (entmake
          (list
           (cons 0 "POINT")
           (cons 100 "AcDbEntity")
           (cons 67 0)
           (cons 8 "0")
           (cons 100 "AcDbPoint")
           (list 10 4 0 0)
           (cons 50 0)
          )
         )
         (entmake
          (list
           (cons 0 "POINT")
           (cons 100 "AcDbEntity")
           (cons 67 0)
           (cons 8 "0")
           (cons 100 "AcDbPoint")
           (list 10 29.98687664 0 0)
           (cons 50 0)
          )
         )
         (entmake
          (list
           (cons 0 "INSERT")
           (cons 100 "AcDbEntity")
           (cons 67 0)
           (cons 8 "0")
           (cons 100 "AcDbBlockReference")
           (cons 2 "WheelRight2")
           (list 10 4.0049 3.16666667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeft2")
           (list 10 4.0049 -3.16666667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 1.70341207 1.85914261 0)
           (cons 40 0.65616798)
           (cons 1 "4.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 0.76552931 0)
           (cons 40 0.65616798)
           (cons 1 "4.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -0.32808399 0)
           (cons 40 0.65616798)
           (cons 1 "24.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -1.42169729 0)
           (cons 40 0.65616798)
           (cons 1 "30.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -2.51531059 0)
           (cons 40 0.65616798)
           (cons 1 "25.8")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-B"))
        (progn
         (entmake)
         (entmake
          (list
           (cons 0 "BLOCK")
           (cons 2 "AASHTO-2011-B")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 5)
           (cons 70 129)
           (cons 43 0)
           (cons 38 0)
           (cons 39 0)
           (list 10 0 0)
           (cons 40 0)
           (cons 41 0)
           (cons 42 0)
           (cons 91 0)
           (list 10 3 4)
           (cons 40 0)
           (cons 41 0)
           (cons 42 0)
           (cons 91 0)
           (list 10 23 4)
           (cons 40 0)
           (cons 41 0)
           (cons 42 0)
           (cons 91 0)
           (list 10 23 -4)
           (cons 40 0)
           (cons 41 0)
           (cons 42 0)
           (cons 91 0)
           (list 10 3 -4)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 23 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 23 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 3 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.53333333)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.95833333 -3.90208333)
           (cons 40 0)
           (cons 41 0)
           (cons 42 0)
           (cons 91 0)
           (list 10 13.95833333 -3.57708333)
           (cons 40 0)
           (cons 41 0)
           (cons 42 0)
           (cons 91 0)
           (list 10 14.25 -3.47916667)
           (cons 40 0)
           (cons 41 0)
           (cons 42 0)
           (cons 91 0)
           (list 10 15.75 -3.47916667)
           (cons 40 0)
           (cons 41 0)
           (cons 42 0)
           (cons 91 0)
           (list 10 16.04166667 -3.57708333)
           (cons 40 0)
           (cons 41 0)
           (cons 42 0)
           (cons 91 0)
           (list 10 16.04166667 -3.90208333)
           (cons 40 0)
           (cons 41 0)
           (cons 42 0)
           (cons 91 0)
           (list 10 15.75 -4)
           (cons 40 0)
           (cons 41 0)
           (cons 42 0)
           (cons 91 0)
           (list 10 14.25 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.95833333 3.57708333)
           (cons 40 0)
           (cons 41 0)
           (cons 42 0)
           (cons 91 0)
           (list 10 13.95833333 3.90208333)
           (cons 40 0)
           (cons 41 0)
           (cons 42 0)
           (cons 91 0)
           (list 10 14.25 4)
           (cons 40 0)
           (cons 41 0)
           (cons 42 0)
           (cons 91 0)
           (list 10 15.75 4)
           (cons 40 0)
           (cons 41 0)
           (cons 42 0)
           (cons 91 0)
           (list 10 16.04166667 3.90208333)
           (cons 40 0)
           (cons 41 0)
           (cons 42 0)
           (cons 91 0)
           (list 10 16.04166667 3.57708333)
           (cons 40 0)
           (cons 41 0)
           (cons 42 0)
           (cons 91 0)
           (list 10 15.75 3.47916667)
           (cons 40 0)
           (cons 41 0)
           (cons 42 0)
           (cons 91 0)
           (list 10 14.25 3.47916667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 3 -4 0)
           (cons 50 0)
          )
         )
         (entmake
          (list
           (cons 0 "POINT")
           (cons 100 "AcDbEntity")
           (cons 67 0)
           (cons 8 "0")
           (cons 100 "AcDbPoint")
           (list 10 15 -4 0)
           (cons 50 0)
          )
         )
         (entmake
          (list
           (cons 0 "POINT")
           (cons 100 "AcDbEntity")
           (cons 67 0)
           (cons 8 "0")
           (cons 100 "AcDbPoint")
           (list 10 15 4 0)
           (cons 50 0)
          )
         )
         (entmake
          (list
           (cons 0 "POINT")
           (cons 100 "AcDbEntity")
           (cons 67 0)
           (cons 8 "0")
           (cons 100 "AcDbPoint")
           (list 10 23 4 0)
           (cons 50 0)
          )
         )
         (entmake
          (list
           (cons 0 "POINT")
           (cons 100 "AcDbEntity")
           (cons 67 0)
           (cons 8 "0")
           (cons 100 "AcDbPoint")
           (list 10 23 -4 0)
           (cons 50 0)
          )
         )
         (entmake
          (list
           (cons 0 "POINT")
           (cons 100 "AcDbEntity")
           (cons 67 0)
           (cons 8 "0")
           (cons 100 "AcDbPoint")
           (list 10 3 4 0)
           (cons 50 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "ATTDEF")
           (cons 100 "AcDbEntity")
           (cons 67 0)
           (cons 8 "0")
           (cons 100 "AcDbText")
           (list 10 -2.29658793 1.85914261 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 0.76552931 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -0.32808399 0)
           (cons 40 0.65616798)
           (cons 1 "15.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-MH"))
        (progn
         (entmake)
         (entmake
          (list
           (cons 0 "BLOCK")
           (cons 2 "AASHTO-2011-MH")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 -4)
           (cons 40 0)
           (cons 41 0)
           (cons 42 0)
           (cons 91 0)
           (list 10 30 -4)
           (cons 40 0)
           (cons 41 0)
           (cons 42 0)
           (cons 91 0)
           (list 10 30 4)
           (cons 40 0)
           (cons 41 0)
           (cons 42 0)
           (cons 91 0)
           (list 10 0 4)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 30 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 30 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 22.33333333 -3.84333333)
           (cons 40 0)
           (cons 41 0)
           (cons 42 0)
           (cons 91 0)
           (list 10 22.33333333 -3.32333333)
           (cons 40 0)
           (cons 41 0)
           (cons 42 0)
           (cons 91 0)
           (list 10 22.8 -3.16666667)
           (cons 40 0)
           (cons 41 0)
           (cons 42 0)
           (cons 91 0)
           (list 10 25.2 -3.16666667)
           (cons 40 0)
           (cons 41 0)
           (cons 42 0)
           (cons 91 0)
           (list 10 25.66666667 -3.32333333)
           (cons 40 0)
           (cons 41 0)
           (cons 42 0)
           (cons 91 0)
           (list 10 25.66666667 -3.84333333)
           (cons 40 0)
           (cons 41 0)
           (cons 42 0)
           (cons 91 0)
           (list 10 25.2 -4)
           (cons 40 0)
           (cons 41 0)
           (cons 42 0)
           (cons 91 0)
           (list 10 22.8 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 22.33333333 3.32333333)
           (cons 40 0)
           (cons 41 0)
           (cons 42 0)
           (cons 91 0)
           (list 10 22.33333333 3.84333333)
           (cons 40 0)
           (cons 41 0)
           (cons 42 0)
           (cons 91 0)
           (list 10 22.8 4)
           (cons 40 0)
           (cons 41 0)
           (cons 42 0)
           (cons 91 0)
           (list 10 25.2 4)
           (cons 40 0)
           (cons 41 0)
           (cons 42 0)
           (cons 91 0)
           (list 10 25.66666667 3.84333333)
           (cons 40 0)
           (cons 41 0)
           (cons 42 0)
           (cons 91 0)
           (list 10 25.66666667 3.32333333)
           (cons 40 0)
           (cons 41 0)
           (cons 42 0)
           (cons 91 0)
           (list 10 25.2 3.16666667)
           (cons 40 0)
           (cons 41 0)
           (cons 42 0)
           (cons 91 0)
           (list 10 22.8 3.16666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4 0)
           (cons 50 0)
          )
         )
         (entmake
          (list
           (cons 0 "POINT")
           (cons 100 "AcDbEntity")
           (cons 67 0)
           (cons 8 "0")
           (cons 100 "AcDbPoint")
           (list 10 4 -4 0)
           (cons 50 0)
          )
         )
         (entmake
          (list
           (cons 0 "POINT")
           (cons 100 "AcDbEntity")
           (cons 67 0)
           (cons 8 "0")
           (cons 100 "AcDbPoint")
           (list 10 24 -4 0)
           (cons 50 0)
          )
         )
         (entmake
          (list
           (cons 0 "POINT")
           (cons 100 "AcDbEntity")
           (cons 67 0)
           (cons 8 "0")
           (cons 100 "AcDbPoint")
           (list 10 30 -4 0)
           (cons 50 0)
          )
         )
         (entmake
          (list
           (cons 0 "POINT")
           (cons 100 "AcDbEntity")
           (cons 67 0)
           (cons 8 "0")
           (cons 100 "AcDbPoint")
           (list 10 30 4 0)
           (cons 50 0)
          )
         )
         (entmake
          (list
           (cons 0 "POINT")
           (cons 100 "AcDbEntity")
           (cons 67 0)
           (cons 8 "0")
           (cons 100 "AcDbPoint")
           (list 10 24 4 0)
           (cons 50 0)
          )
         )
         (entmake
          (list
           (cons 0 "POINT")
           (cons 100 "AcDbEntity")
           (cons 67 0)
           (cons 8 "0")
           (cons 100 "AcDbPoint")
           (list 10 4 4 0)
           (cons 50 0)
          )
         )
         (entmake
          (list
           (cons 0 "POINT")
           (cons 100 "AcDbEntity")
           (cons 67 0)
           (cons 8 "0")
           (cons 100 "AcDbPoint")
           (list 10 0 4 0)
           (cons 50 0)
          )
         )
         (entmake
          (list
           (cons 0 "POINT")
           (cons 100 "AcDbEntity")
           (cons 67 0)
           (cons 8 "0")
           (cons 100 "AcDbPoint")
           (list 10 4 0 0)
           (cons 50 0)
          )
         )
         (entmake
          (list
           (cons 0 "POINT")
           (cons 100 "AcDbEntity")
           (cons 67 0)
           (cons 8 "0")
           (cons 100 "AcDbPoint")
           (list 10 29.98687664 0 0)
           (cons 50 0)
          )
         )
         (entmake
          (list
           (cons 0 "INSERT")
           (cons 100 "AcDbEntity")
           (cons 67 0)
           (cons 8 "0")
           (cons 100 "AcDbBlockReference")
           (cons 2 "WheelRight2")
           (list 10 4.0049 3.16666667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeft2")
           (list 10 4.0049 -3.16666667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 1.70341207 1.85914261 0)
           (cons 40 0.65616798)
           (cons 1 "4.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 0.76552931 0)
           (cons 40 0.65616798)
           (cons 1 "4.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -0.32808399 0)
           (cons 40 0.65616798)
           (cons 1 "24.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -1.42169729 0)
           (cons 40 0.65616798)
           (cons 1 "30.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -2.51531059 0)
           (cons 40 0.65616798)
           (cons 1 "25.8")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-MH"))
        (progn
         (entmake)
         (entmake
          (list
           (cons 0 "BLOCK")
           (cons 2 "AASHTO-2011-MH")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 -4)
           (cons 40 0)
           (cons 41 0)
           (cons 42 0)
           (cons 91 0)
           (list 10 30 -4)
           (cons 40 0)
           (cons 41 0)
           (cons 42 0)
           (cons 91 0)
           (list 10 30 4)
           (cons 40 0)
           (cons 41 0)
           (cons 42 0)
           (cons 91 0)
           (list 10 0 4)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 30 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 30 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 22.33333333 -3.84333333)
           (cons 40 0)
           (cons 41 0)
           (cons 42 0)
           (cons 91 0)
           (list 10 22.33333333 -3.32333333)
           (cons 40 0)
           (cons 41 0)
           (cons 42 0)
           (cons 91 0)
           (list 10 22.8 -3.16666667)
           (cons 40 0)
           (cons 41 0)
           (cons 42 0)
           (cons 91 0)
           (list 10 25.2 -3.16666667)
           (cons 40 0)
           (cons 41 0)
           (cons 42 0)
           (cons 91 0)
           (list 10 25.66666667 -3.32333333)
           (cons 40 0)
           (cons 41 0)
           (cons 42 0)
           (cons 91 0)
           (list 10 25.66666667 -3.84333333)
           (cons 40 0)
           (cons 41 0)
           (cons 42 0)
           (cons 91 0)
           (list 10 25.2 -4)
           (cons 40 0)
           (cons 41 0)
           (cons 42 0)
           (cons 91 0)
           (list 10 22.8 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 22.33333333 3.32333333)
           (cons 40 0)
           (cons 41 0)
           (cons 42 0)
           (cons 91 0)
           (list 10 22.33333333 3.84333333)
           (cons 40 0)
           (cons 41 0)
           (cons 42 0)
           (cons 91 0)
           (list 10 22.8 4)
           (cons 40 0)
           (cons 41 0)
           (cons 42 0)
           (cons 91 0)
           (list 10 25.2 4)
           (cons 40 0)
           (cons 41 0)
           (cons 42 0)
           (cons 91 0)
           (list 10 25.66666667 3.84333333)
           (cons 40 0)
           (cons 41 0)
           (cons 42 0)
           (cons 91 0)
           (list 10 25.66666667 3.32333333)
           (cons 40 0)
           (cons 41 0)
           (cons 42 0)
           (cons 91 0)
           (list 10 25.2 3.16666667)
           (cons 40 0)
           (cons 41 0)
           (cons 42 0)
           (cons 91 0)
           (list 10 22.8 3.16666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4 0)
           (cons 50 0)
          )
         )
         (entmake
          (list
           (cons 0 "POINT")
           (cons 100 "AcDbEntity")
           (cons 67 0)
           (cons 8 "0")
           (cons 100 "AcDbPoint")
           (list 10 4 -4 0)
           (cons 50 0)
          )
         )
         (entmake
          (list
           (cons 0 "POINT")
           (cons 100 "AcDbEntity")
           (cons 67 0)
           (cons 8 "0")
           (cons 100 "AcDbPoint")
           (list 10 24 -4 0)
           (cons 50 0)
          )
         )
         (entmake
          (list
           (cons 0 "POINT")
           (cons 100 "AcDbEntity")
           (cons 67 0)
           (cons 8 "0")
           (cons 100 "AcDbPoint")
           (list 10 30 -4 0)
           (cons 50 0)
          )
         )
         (entmake
          (list
           (cons 0 "POINT")
           (cons 100 "AcDbEntity")
           (cons 67 0)
           (cons 8 "0")
           (cons 100 "AcDbPoint")
           (list 10 30 4 0)
           (cons 50 0)
          )
         )
         (entmake
          (list
           (cons 0 "POINT")
           (cons 100 "AcDbEntity")
           (cons 67 0)
           (cons 8 "0")
           (cons 100 "AcDbPoint")
           (list 10 24 4 0)
           (cons 50 0)
          )
         )
         (entmake
          (list
           (cons 0 "POINT")
           (cons 100 "AcDbEntity")
           (cons 67 0)
           (cons 8 "0")
           (cons 100 "AcDbPoint")
           (list 10 4 4 0)
           (cons 50 0)
          )
         )
         (entmake
          (list
           (cons 0 "POINT")
           (cons 100 "AcDbEntity")
           (cons 67 0)
           (cons 8 "0")
           (cons 100 "AcDbPoint")
           (list 10 0 4 0)
           (cons 50 0)
          )
         )
         (entmake
          (list
           (cons 0 "POINT")
           (cons 100 "AcDbEntity")
           (cons 67 0)
           (cons 8 "0")
           (cons 100 "AcDbPoint")
           (list 10 4 0 0)
           (cons 50 0)
          )
         )
         (entmake
          (list
           (cons 0 "POINT")
           (cons 100 "AcDbEntity")
           (cons 67 0)
           (cons 8 "0")
           (cons 100 "AcDbPoint")
           (list 10 29.98687664 0 0)
           (cons 50 0)
          )
         )
         (entmake
          (list
           (cons 0 "INSERT")
           (cons 100 "AcDbEntity")
           (cons 67 0)
           (cons 8 "0")
           (cons 100 "AcDbBlockReference")
           (cons 2 "WheelRight2")
           (list 10 4.0049 3.16666667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeft2")
           (list 10 4.0049 -3.16666667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 1.70341207 1.85914261 0)
           (cons 40 0.65616798)
           (cons 1 "4.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 0.76552931 0)
           (cons 40 0.65616798)
           (cons 1 "4.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -0.32808399 0)
           (cons 40 0.65616798)
           (cons 1 "24.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -1.42169729 0)
           (cons 40 0.65616798)
           (cons 1 "30.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.70341207 -2.51531059 0)
           (cons 40 0.65616798)
           (cons 1 "25.8")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-T"))
        (progn
         (entmake)
         (entmake
          (list
           (cons 0 "BLOCK")
           (cons 2 "AASHTO-2011-T")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 5)
           (cons 70 129)
           (cons 43 0)
           (cons 38 0)
           (cons 39 0)
           (list 10 0 0)
           (cons 40 0)
           (cons 41 0)
           (cons 42 0)
           (cons 91 0)
           (list 10 3 4)
           (cons 40 0)
           (cons 41 0)
           (cons 42 0)
           (cons 91 0)
           (list 10 29.7 4)
           (cons 40 0)
           (cons 41 0)
           (cons 42 0)
           (cons 91 0)
           (list 10 29.7 -4)
           (cons 40 0)
           (cons 41 0)
           (cons 42 0)
           (cons 91 0)
           (list 10 3 -4)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 29.7 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 29.7 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 3 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.53333333)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.46666667 -3.90208333)
           (cons 40 0)
           (cons 41 0)
           (cons 42 0)
           (cons 91 0)
           (list 10 14.46666667 -3.57708333)
           (cons 40 0)
           (cons 41 0)
           (cons 42 0)
           (cons 91 0)
           (list 10 14.78866667 -3.47916667)
           (cons 40 0)
           (cons 41 0)
           (cons 42 0)
           (cons 91 0)
           (list 10 16.44466667 -3.47916667)
           (cons 40 0)
           (cons 41 0)
           (cons 42 0)
           (cons 91 0)
           (list 10 16.76666667 -3.57708333)
           (cons 40 0)
           (cons 41 0)
           (cons 42 0)
           (cons 91 0)
           (list 10 16.76666667 -3.90208333)
           (cons 40 0)
           (cons 41 0)
           (cons 42 0)
           (cons 91 0)
           (list 10 16.44466667 -4)
           (cons 40 0)
           (cons 41 0)
           (cons 42 0)
           (cons 91 0)
           (list 10 14.78866667 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.46666667 3.57708333)
           (cons 40 0)
           (cons 41 0)
           (cons 42 0)
           (cons 91 0)
           (list 10 14.46666667 3.90208333)
           (cons 40 0)
           (cons 41 0)
           (cons 42 0)
           (cons 91 0)
           (list 10 14.78866667 4)
           (cons 40 0)
           (cons 41 0)
           (cons 42 0)
           (cons 91 0)
           (list 10 16.44466667 4)
           (cons 40 0)
           (cons 41 0)
           (cons 42 0)
           (cons 91 0)
           (list 10 16.76666667 3.90208333)
           (cons 40 0)
           (cons 41 0)
           (cons 42 0)
           (cons 91 0)
           (list 10 16.76666667 3.57708333)
           (cons 40 0)
           (cons 41 0)
           (cons 42 0)
           (cons 91 0)
           (list 10 16.44466667 3.47916667)
           (cons 40 0)
           (cons 41 0)
           (cons 42 0)
           (cons 91 0)
           (list 10 14.78866667 3.47916667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 18.63333333 -3.90208333)
           (cons 40 0)
           (cons 41 0)
           (cons 42 0)
           (cons 91 0)
           (list 10 18.63333333 -3.57708333)
           (cons 40 0)
           (cons 41 0)
           (cons 42 0)
           (cons 91 0)
           (list 10 18.95533333 -3.47916667)
           (cons 40 0)
           (cons 41 0)
           (cons 42 0)
           (cons 91 0)
           (list 10 20.61133333 -3.47916667)
           (cons 40 0)
           (cons 41 0)
           (cons 42 0)
           (cons 91 0)
           (list 10 20.93333333 -3.57708333)
           (cons 40 0)
           (cons 41 0)
           (cons 42 0)
           (cons 91 0)
           (list 10 20.93333333 -3.90208333)
           (cons 40 0)
           (cons 41 0)
           (cons 42 0)
           (cons 91 0)
           (list 10 20.61133333 -4)
           (cons 40 0)
           (cons 41 0)
           (cons 42 0)
           (cons 91 0)
           (list 10 18.95533333 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 18.63333333 3.57708333)
           (cons 40 0)
           (cons 41 0)
           (cons 42 0)
           (cons 91 0)
           (list 10 18.63333333 3.90208333)
           (cons 40 0)
           (cons 41 0)
           (cons 42 0)
           (cons 91 0)
           (list 10 18.95533333 4)
           (cons 40 0)
           (cons 41 0)
           (cons 42 0)
           (cons 91 0)
           (list 10 20.61133333 4)
           (cons 40 0)
           (cons 41 0)
           (cons 42 0)
           (cons 91 0)
           (list 10 20.93333333 3.90208333)
           (cons 40 0)
           (cons 41 0)
           (cons 42 0)
           (cons 91 0)
           (list 10 20.93333333 3.57708333)
           (cons 40 0)
           (cons 41 0)
           (cons 42 0)
           (cons 91 0)
           (list 10 20.61133333 3.47916667)
           (cons 40 0)
           (cons 41 0)
           (cons 42 0)
           (cons 91 0)
           (list 10 18.95533333 3.47916667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 3 -4 0)
           (cons 50 0)
          )
         )
         (entmake
          (list
           (cons 0 "POINT")
           (cons 100 "AcDbEntity")
           (cons 67 0)
           (cons 8 "0")
           (cons 100 "AcDbPoint")
           (list 10 3 4 0)
           (cons 50 0)
          )
         )
         (entmake
          (list
           (cons 0 "POINT")
           (cons 100 "AcDbEntity")
           (cons 67 0)
           (cons 8 "0")
           (cons 100 "AcDbPoint")
           (list 10 29.7 4 0)
           (cons 50 0)
          )
         )
         (entmake
          (list
           (cons 0 "POINT")
           (cons 100 "AcDbEntity")
           (cons 67 0)
           (cons 8 "0")
           (cons 100 "AcDbPoint")
           (list 10 29.7 -4 0)
           (cons 50 0)
          )
         )
         (entmake
          (list
           (cons 0 "POINT")
           (cons 100 "AcDbEntity")
           (cons 67 0)
           (cons 8 "0")
           (cons 100 "AcDbPoint")
           (list 10 17.7 -4 0)
           (cons 50 0)
          )
         )
         (entmake
          (list
           (cons 0 "POINT")
           (cons 100 "AcDbEntity")
           (cons 67 0)
           (cons 8 "0")
           (cons 100 "AcDbPoint")
           (list 10 17.7 4 0)
           (cons 50 0)
          )
         )
         (entmake
          (list
           (cons 0 "ATTDEF")
           (cons 100 "AcDbEntity")
           (cons 67 0)
           (cons 8 "0")
           (cons 100 "AcDbText")
           (list 10 -2.29658793 1.85914261 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 0.76552931 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -0.32808399 0)
           (cons 40 0.65616798)
           (cons 1 "17.700")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-P"))
        (progn
         (entmake)
         (entmake
          (list
           (cons 0 "BLOCK")
           (cons 2 "AASHTO-2011-P")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 -3.5)
           (cons 40 0)
           (cons 41 0)
           (cons 42 0)
           (cons 91 0)
           (list 10 19 -3.5)
           (cons 40 0)
           (cons 41 0)
           (cons 42 0)
           (cons 91 0)
           (list 10 19 3.5)
           (cons 40 0)
           (cons 41 0)
           (cons 42 0)
           (cons 91 0)
           (list 10 0 3.5)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -3.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 19 -3.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 19 3.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 3.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -3.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -3.5 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.95833333 -2.90208333)
           (cons 40 0)
           (cons 41 0)
           (cons 42 0)
           (cons 91 0)
           (list 10 12.95833333 -2.57708333)
           (cons 40 0)
           (cons 41 0)
           (cons 42 0)
           (cons 91 0)
           (list 10 13.25 -2.47916667)
           (cons 40 0)
           (cons 41 0)
           (cons 42 0)
           (cons 91 0)
           (list 10 14.75 -2.47916667)
           (cons 40 0)
           (cons 41 0)
           (cons 42 0)
           (cons 91 0)
           (list 10 15.04166667 -2.57708333)
           (cons 40 0)
           (cons 41 0)
           (cons 42 0)
           (cons 91 0)
           (list 10 15.04166667 -2.90208333)
           (cons 40 0)
           (cons 41 0)
           (cons 42 0)
           (cons 91 0)
           (list 10 14.75 -3)
           (cons 40 0)
           (cons 41 0)
           (cons 42 0)
           (cons 91 0)
           (list 10 13.25 -3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.95833333 2.57708333)
           (cons 40 0)
           (cons 41 0)
           (cons 42 0)
           (cons 91 0)
           (list 10 12.95833333 2.90208333)
           (cons 40 0)
           (cons 41 0)
           (cons 42 0)
           (cons 91 0)
           (list 10 13.25 3)
           (cons 40 0)
           (cons 41 0)
           (cons 42 0)
           (cons 91 0)
           (list 10 14.75 3)
           (cons 40 0)
           (cons 41 0)
           (cons 42 0)
           (cons 91 0)
           (list 10 15.04166667 2.90208333)
           (cons 40 0)
           (cons 41 0)
           (cons 42 0)
           (cons 91 0)
           (list 10 15.04166667 2.57708333)
           (cons 40 0)
           (cons 41 0)
           (cons 42 0)
           (cons 91 0)
           (list 10 14.75 2.47916667)
           (cons 40 0)
           (cons 41 0)
           (cons 42 0)
           (cons 91 0)
           (list 10 13.25 2.47916667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 3 0 0)
           (cons 50 0)
          )
         )
         (entmake
          (list
           (cons 0 "POINT")
           (cons 100 "AcDbEntity")
           (cons 67 0)
           (cons 8 "0")
           (cons 100 "AcDbPoint")
           (list 10 3 3 0)
           (cons 50 0)
          )
         )
         (entmake
          (list
           (cons 0 "POINT")
           (cons 100 "AcDbEntity")
           (cons 67 0)
           (cons 8 "0")
           (cons 100 "AcDbPoint")
           (list 10 3 -3 0)
           (cons 50 0)
          )
         )
         (entmake
          (list
           (cons 0 "POINT")
           (cons 100 "AcDbEntity")
           (cons 67 0)
           (cons 8 "0")
           (cons 100 "AcDbPoint")
           (list 10 0 3.5 0)
           (cons 50 0)
          )
         )
         (entmake
          (list
           (cons 0 "POINT")
           (cons 100 "AcDbEntity")
           (cons 67 0)
           (cons 8 "0")
           (cons 100 "AcDbPoint")
           (list 10 0 -3.5 0)
           (cons 50 0)
          )
         )
         (entmake
          (list
           (cons 0 "POINT")
           (cons 100 "AcDbEntity")
           (cons 67 0)
           (cons 8 "0")
           (cons 100 "AcDbPoint")
           (list 10 14 -3 0)
           (cons 50 0)
          )
         )
         (entmake
          (list
           (cons 0 "POINT")
           (cons 100 "AcDbEntity")
           (cons 67 0)
           (cons 8 "0")
           (cons 100 "AcDbPoint")
           (list 10 14 3 0)
           (cons 50 0)
          )
         )
         (entmake
          (list
           (cons 0 "POINT")
           (cons 100 "AcDbEntity")
           (cons 67 0)
           (cons 8 "0")
           (cons 100 "AcDbPoint")
           (list 10 19 3.5 0)
           (cons 50 0)
          )
         )
         (entmake
          (list
           (cons 0 "POINT")
           (cons 100 "AcDbEntity")
           (cons 67 0)
           (cons 8 "0")
           (cons 100 "AcDbPoint")
           (list 10 19 -3.5 0)
           (cons 50 0)
          )
         )
         (entmake
          (list
           (cons 0 "POINT")
           (cons 100 "AcDbEntity")
           (cons 67 0)
           (cons 8 "0")
           (cons 100 "AcDbPoint")
           (list 10 19 0 0)
           (cons 50 0)
          )
         )
         (entmake
          (list
           (cons 0 "INSERT")
           (cons 100 "AcDbEntity")
           (cons 67 0)
           (cons 8 "0")
           (cons 100 "AcDbBlockReference")
           (cons 2 "WheelLeft4")
           (list 10 3 -2.47916667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRight4")
           (list 10 3 2.47916667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 0.70341207 1.85914261 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 0.76552931 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -0.32808399 0)
           (cons 40 0.65616798)
           (cons 1 "14.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -1.42169729 0)
           (cons 40 0.65616798)
           (cons 1 "19.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -2.51531059 0)
           (cons 40 0.65616798)
           (cons 1 "31.6")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-B"))
        (progn
         (entmake)
         (entmake
          (list
           (cons 0 "BLOCK")
           (cons 2 "AASHTO-2011-B")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 5)
           (cons 70 129)
           (cons 43 0)
           (cons 38 0)
           (cons 39 0)
           (list 10 0 0)
           (cons 40 0)
           (cons 41 0)
           (cons 42 0)
           (cons 91 0)
           (list 10 3 4)
           (cons 40 0)
           (cons 41 0)
           (cons 42 0)
           (cons 91 0)
           (list 10 23 4)
           (cons 40 0)
           (cons 41 0)
           (cons 42 0)
           (cons 91 0)
           (list 10 23 -4)
           (cons 40 0)
           (cons 41 0)
           (cons 42 0)
           (cons 91 0)
           (list 10 3 -4)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 23 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 23 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -4 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -4 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 3 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.53333333)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.95833333 -3.90208333)
           (cons 40 0)
           (cons 41 0)
           (cons 42 0)
           (cons 91 0)
           (list 10 13.95833333 -3.57708333)
           (cons 40 0)
           (cons 41 0)
           (cons 42 0)
           (cons 91 0)
           (list 10 14.25 -3.47916667)
           (cons 40 0)
           (cons 41 0)
           (cons 42 0)
           (cons 91 0)
           (list 10 15.75 -3.47916667)
           (cons 40 0)
           (cons 41 0)
           (cons 42 0)
           (cons 91 0)
           (list 10 16.04166667 -3.57708333)
           (cons 40 0)
           (cons 41 0)
           (cons 42 0)
           (cons 91 0)
           (list 10 16.04166667 -3.90208333)
           (cons 40 0)
           (cons 41 0)
           (cons 42 0)
           (cons 91 0)
           (list 10 15.75 -4)
           (cons 40 0)
           (cons 41 0)
           (cons 42 0)
           (cons 91 0)
           (list 10 14.25 -4)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.95833333 3.57708333)
           (cons 40 0)
           (cons 41 0)
           (cons 42 0)
           (cons 91 0)
           (list 10 13.95833333 3.90208333)
           (cons 40 0)
           (cons 41 0)
           (cons 42 0)
           (cons 91 0)
           (list 10 14.25 4)
           (cons 40 0)
           (cons 41 0)
           (cons 42 0)
           (cons 91 0)
           (list 10 15.75 4)
           (cons 40 0)
           (cons 41 0)
           (cons 42 0)
           (cons 91 0)
           (list 10 16.04166667 3.90208333)
           (cons 40 0)
           (cons 41 0)
           (cons 42 0)
           (cons 91 0)
           (list 10 16.04166667 3.57708333)
           (cons 40 0)
           (cons 41 0)
           (cons 42 0)
           (cons 91 0)
           (list 10 15.75 3.47916667)
           (cons 40 0)
           (cons 41 0)
           (cons 42 0)
           (cons 91 0)
           (list 10 14.25 3.47916667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 3 -4 0)
           (cons 50 0)
          )
         )
         (entmake
          (list
           (cons 0 "POINT")
           (cons 100 "AcDbEntity")
           (cons 67 0)
           (cons 8 "0")
           (cons 100 "AcDbPoint")
           (list 10 15 -4 0)
           (cons 50 0)
          )
         )
         (entmake
          (list
           (cons 0 "POINT")
           (cons 100 "AcDbEntity")
           (cons 67 0)
           (cons 8 "0")
           (cons 100 "AcDbPoint")
           (list 10 15 4 0)
           (cons 50 0)
          )
         )
         (entmake
          (list
           (cons 0 "POINT")
           (cons 100 "AcDbEntity")
           (cons 67 0)
           (cons 8 "0")
           (cons 100 "AcDbPoint")
           (list 10 23 4 0)
           (cons 50 0)
          )
         )
         (entmake
          (list
           (cons 0 "POINT")
           (cons 100 "AcDbEntity")
           (cons 67 0)
           (cons 8 "0")
           (cons 100 "AcDbPoint")
           (list 10 23 -4 0)
           (cons 50 0)
          )
         )
         (entmake
          (list
           (cons 0 "POINT")
           (cons 100 "AcDbEntity")
           (cons 67 0)
           (cons 8 "0")
           (cons 100 "AcDbPoint")
           (list 10 3 4 0)
           (cons 50 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "ATTDEF")
           (cons 100 "AcDbEntity")
           (cons 67 0)
           (cons 8 "0")
           (cons 100 "AcDbText")
           (list 10 -2.29658793 1.85914261 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 0.76552931 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -0.32808399 0)
           (cons 40 0.65616798)
           (cons 1 "15.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-P"))
        (progn
         (entmake)
         (entmake
          (list
           (cons 0 "BLOCK")
           (cons 2 "AASHTO-2011-P")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 -3.5)
           (cons 40 0)
           (cons 41 0)
           (cons 42 0)
           (cons 91 0)
           (list 10 19 -3.5)
           (cons 40 0)
           (cons 41 0)
           (cons 42 0)
           (cons 91 0)
           (list 10 19 3.5)
           (cons 40 0)
           (cons 41 0)
           (cons 42 0)
           (cons 91 0)
           (list 10 0 3.5)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -3.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 19 -3.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 19 3.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 3.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -3.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -3.5 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.95833333 -2.90208333)
           (cons 40 0)
           (cons 41 0)
           (cons 42 0)
           (cons 91 0)
           (list 10 12.95833333 -2.57708333)
           (cons 40 0)
           (cons 41 0)
           (cons 42 0)
           (cons 91 0)
           (list 10 13.25 -2.47916667)
           (cons 40 0)
           (cons 41 0)
           (cons 42 0)
           (cons 91 0)
           (list 10 14.75 -2.47916667)
           (cons 40 0)
           (cons 41 0)
           (cons 42 0)
           (cons 91 0)
           (list 10 15.04166667 -2.57708333)
           (cons 40 0)
           (cons 41 0)
           (cons 42 0)
           (cons 91 0)
           (list 10 15.04166667 -2.90208333)
           (cons 40 0)
           (cons 41 0)
           (cons 42 0)
           (cons 91 0)
           (list 10 14.75 -3)
           (cons 40 0)
           (cons 41 0)
           (cons 42 0)
           (cons 91 0)
           (list 10 13.25 -3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.95833333 2.57708333)
           (cons 40 0)
           (cons 41 0)
           (cons 42 0)
           (cons 91 0)
           (list 10 12.95833333 2.90208333)
           (cons 40 0)
           (cons 41 0)
           (cons 42 0)
           (cons 91 0)
           (list 10 13.25 3)
           (cons 40 0)
           (cons 41 0)
           (cons 42 0)
           (cons 91 0)
           (list 10 14.75 3)
           (cons 40 0)
           (cons 41 0)
           (cons 42 0)
           (cons 91 0)
           (list 10 15.04166667 2.90208333)
           (cons 40 0)
           (cons 41 0)
           (cons 42 0)
           (cons 91 0)
           (list 10 15.04166667 2.57708333)
           (cons 40 0)
           (cons 41 0)
           (cons 42 0)
           (cons 91 0)
           (list 10 14.75 2.47916667)
           (cons 40 0)
           (cons 41 0)
           (cons 42 0)
           (cons 91 0)
           (list 10 13.25 2.47916667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 3 0 0)
           (cons 50 0)
          )
         )
         (entmake
          (list
           (cons 0 "POINT")
           (cons 100 "AcDbEntity")
           (cons 67 0)
           (cons 8 "0")
           (cons 100 "AcDbPoint")
           (list 10 3 3 0)
           (cons 50 0)
          )
         )
         (entmake
          (list
           (cons 0 "POINT")
           (cons 100 "AcDbEntity")
           (cons 67 0)
           (cons 8 "0")
           (cons 100 "AcDbPoint")
           (list 10 3 -3 0)
           (cons 50 0)
          )
         )
         (entmake
          (list
           (cons 0 "POINT")
           (cons 100 "AcDbEntity")
           (cons 67 0)
           (cons 8 "0")
           (cons 100 "AcDbPoint")
           (list 10 0 3.5 0)
           (cons 50 0)
          )
         )
         (entmake
          (list
           (cons 0 "POINT")
           (cons 100 "AcDbEntity")
           (cons 67 0)
           (cons 8 "0")
           (cons 100 "AcDbPoint")
           (list 10 0 -3.5 0)
           (cons 50 0)
          )
         )
         (entmake
          (list
           (cons 0 "POINT")
           (cons 100 "AcDbEntity")
           (cons 67 0)
           (cons 8 "0")
           (cons 100 "AcDbPoint")
           (list 10 14 -3 0)
           (cons 50 0)
          )
         )
         (entmake
          (list
           (cons 0 "POINT")
           (cons 100 "AcDbEntity")
           (cons 67 0)
           (cons 8 "0")
           (cons 100 "AcDbPoint")
           (list 10 14 3 0)
           (cons 50 0)
          )
         )
         (entmake
          (list
           (cons 0 "POINT")
           (cons 100 "AcDbEntity")
           (cons 67 0)
           (cons 8 "0")
           (cons 100 "AcDbPoint")
           (list 10 19 3.5 0)
           (cons 50 0)
          )
         )
         (entmake
          (list
           (cons 0 "POINT")
           (cons 100 "AcDbEntity")
           (cons 67 0)
           (cons 8 "0")
           (cons 100 "AcDbPoint")
           (list 10 19 -3.5 0)
           (cons 50 0)
          )
         )
         (entmake
          (list
           (cons 0 "POINT")
           (cons 100 "AcDbEntity")
           (cons 67 0)
           (cons 8 "0")
           (cons 100 "AcDbPoint")
           (list 10 19 0 0)
           (cons 50 0)
          )
         )
         (entmake
          (list
           (cons 0 "INSERT")
           (cons 100 "AcDbEntity")
           (cons 67 0)
           (cons 8 "0")
           (cons 100 "AcDbBlockReference")
           (cons 2 "WheelLeft4")
           (list 10 3 -2.47916667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRight4")
           (list 10 3 2.47916667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 0.70341207 1.85914261 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 0.76552931 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -0.32808399 0)
           (cons 40 0.65616798)
           (cons 1 "14.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -1.42169729 0)
           (cons 40 0.65616798)
           (cons 1 "19.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -2.51531059 0)
           (cons 40 0.65616798)
           (cons 1 "31.6")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-P"))
        (progn
         (entmake)
         (entmake
          (list
           (cons 0 "BLOCK")
           (cons 2 "AASHTO-2011-P")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 -3.5)
           (cons 40 0)
           (cons 41 0)
           (cons 42 0)
           (cons 91 0)
           (list 10 19 -3.5)
           (cons 40 0)
           (cons 41 0)
           (cons 42 0)
           (cons 91 0)
           (list 10 19 3.5)
           (cons 40 0)
           (cons 41 0)
           (cons 42 0)
           (cons 91 0)
           (list 10 0 3.5)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -3.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 19 -3.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 19 3.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 3.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -3.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -3.5 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.95833333 -2.90208333)
           (cons 40 0)
           (cons 41 0)
           (cons 42 0)
           (cons 91 0)
           (list 10 12.95833333 -2.57708333)
           (cons 40 0)
           (cons 41 0)
           (cons 42 0)
           (cons 91 0)
           (list 10 13.25 -2.47916667)
           (cons 40 0)
           (cons 41 0)
           (cons 42 0)
           (cons 91 0)
           (list 10 14.75 -2.47916667)
           (cons 40 0)
           (cons 41 0)
           (cons 42 0)
           (cons 91 0)
           (list 10 15.04166667 -2.57708333)
           (cons 40 0)
           (cons 41 0)
           (cons 42 0)
           (cons 91 0)
           (list 10 15.04166667 -2.90208333)
           (cons 40 0)
           (cons 41 0)
           (cons 42 0)
           (cons 91 0)
           (list 10 14.75 -3)
           (cons 40 0)
           (cons 41 0)
           (cons 42 0)
           (cons 91 0)
           (list 10 13.25 -3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.95833333 2.57708333)
           (cons 40 0)
           (cons 41 0)
           (cons 42 0)
           (cons 91 0)
           (list 10 12.95833333 2.90208333)
           (cons 40 0)
           (cons 41 0)
           (cons 42 0)
           (cons 91 0)
           (list 10 13.25 3)
           (cons 40 0)
           (cons 41 0)
           (cons 42 0)
           (cons 91 0)
           (list 10 14.75 3)
           (cons 40 0)
           (cons 41 0)
           (cons 42 0)
           (cons 91 0)
           (list 10 15.04166667 2.90208333)
           (cons 40 0)
           (cons 41 0)
           (cons 42 0)
           (cons 91 0)
           (list 10 15.04166667 2.57708333)
           (cons 40 0)
           (cons 41 0)
           (cons 42 0)
           (cons 91 0)
           (list 10 14.75 2.47916667)
           (cons 40 0)
           (cons 41 0)
           (cons 42 0)
           (cons 91 0)
           (list 10 13.25 2.47916667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 3 0 0)
           (cons 50 0)
          )
         )
         (entmake
          (list
           (cons 0 "POINT")
           (cons 100 "AcDbEntity")
           (cons 67 0)
           (cons 8 "0")
           (cons 100 "AcDbPoint")
           (list 10 3 3 0)
           (cons 50 0)
          )
         )
         (entmake
          (list
           (cons 0 "POINT")
           (cons 100 "AcDbEntity")
           (cons 67 0)
           (cons 8 "0")
           (cons 100 "AcDbPoint")
           (list 10 3 -3 0)
           (cons 50 0)
          )
         )
         (entmake
          (list
           (cons 0 "POINT")
           (cons 100 "AcDbEntity")
           (cons 67 0)
           (cons 8 "0")
           (cons 100 "AcDbPoint")
           (list 10 0 3.5 0)
           (cons 50 0)
          )
         )
         (entmake
          (list
           (cons 0 "POINT")
           (cons 100 "AcDbEntity")
           (cons 67 0)
           (cons 8 "0")
           (cons 100 "AcDbPoint")
           (list 10 0 -3.5 0)
           (cons 50 0)
          )
         )
         (entmake
          (list
           (cons 0 "POINT")
           (cons 100 "AcDbEntity")
           (cons 67 0)
           (cons 8 "0")
           (cons 100 "AcDbPoint")
           (list 10 14 -3 0)
           (cons 50 0)
          )
         )
         (entmake
          (list
           (cons 0 "POINT")
           (cons 100 "AcDbEntity")
           (cons 67 0)
           (cons 8 "0")
           (cons 100 "AcDbPoint")
           (list 10 14 3 0)
           (cons 50 0)
          )
         )
         (entmake
          (list
           (cons 0 "POINT")
           (cons 100 "AcDbEntity")
           (cons 67 0)
           (cons 8 "0")
           (cons 100 "AcDbPoint")
           (list 10 19 3.5 0)
           (cons 50 0)
          )
         )
         (entmake
          (list
           (cons 0 "POINT")
           (cons 100 "AcDbEntity")
           (cons 67 0)
           (cons 8 "0")
           (cons 100 "AcDbPoint")
           (list 10 19 -3.5 0)
           (cons 50 0)
          )
         )
         (entmake
          (list
           (cons 0 "POINT")
           (cons 100 "AcDbEntity")
           (cons 67 0)
           (cons 8 "0")
           (cons 100 "AcDbPoint")
           (list 10 19 0 0)
           (cons 50 0)
          )
         )
         (entmake
          (list
           (cons 0 "INSERT")
           (cons 100 "AcDbEntity")
           (cons 67 0)
           (cons 8 "0")
           (cons 100 "AcDbBlockReference")
           (cons 2 "WheelLeft4")
           (list 10 3 -2.47916667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRight4")
           (list 10 3 2.47916667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 0.70341207 1.85914261 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 0.76552931 0)
           (cons 40 0.65616798)
           (cons 1 "3.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -0.32808399 0)
           (cons 40 0.65616798)
           (cons 1 "14.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -1.42169729 0)
           (cons 40 0.65616798)
           (cons 1 "19.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.70341207 -2.51531059 0)
           (cons 40 0.65616798)
           (cons 1 "31.6")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-CITY-BUS"))
        (progn
         (entmake)
         (entmake
          (list
           (cons 0 "BLOCK")
           (cons 2 "AASHTO-2011-CITY-BUS")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 -4.25)
           (cons 40 0)
           (cons 41 0)
           (cons 42 0)
           (cons 91 0)
           (list 10 40 -4.25)
           (cons 40 0)
           (cons 41 0)
           (cons 42 0)
           (cons 91 0)
           (list 10 40 4.25)
           (cons 40 0)
           (cons 41 0)
           (cons 42 0)
           (cons 91 0)
           (list 10 0 4.25)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 40 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 40 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 30.33333333 -4.09333333)
           (cons 40 0)
           (cons 41 0)
           (cons 42 0)
           (cons 91 0)
           (list 10 30.33333333 -3.57333333)
           (cons 40 0)
           (cons 41 0)
           (cons 42 0)
           (cons 91 0)
           (list 10 30.8 -3.41666667)
           (cons 40 0)
           (cons 41 0)
           (cons 42 0)
           (cons 91 0)
           (list 10 33.2 -3.41666667)
           (cons 40 0)
           (cons 41 0)
           (cons 42 0)
           (cons 91 0)
           (list 10 33.66666667 -3.57333333)
           (cons 40 0)
           (cons 41 0)
           (cons 42 0)
           (cons 91 0)
           (list 10 33.66666667 -4.09333333)
           (cons 40 0)
           (cons 41 0)
           (cons 42 0)
           (cons 91 0)
           (list 10 33.2 -4.25)
           (cons 40 0)
           (cons 41 0)
           (cons 42 0)
           (cons 91 0)
           (list 10 30.8 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 30.33333333 3.57333333)
           (cons 40 0)
           (cons 41 0)
           (cons 42 0)
           (cons 91 0)
           (list 10 30.33333333 4.09333333)
           (cons 40 0)
           (cons 41 0)
           (cons 42 0)
           (cons 91 0)
           (list 10 30.8 4.25)
           (cons 40 0)
           (cons 41 0)
           (cons 42 0)
           (cons 91 0)
           (list 10 33.2 4.25)
           (cons 40 0)
           (cons 41 0)
           (cons 42 0)
           (cons 91 0)
           (list 10 33.66666667 4.09333333)
           (cons 40 0)
           (cons 41 0)
           (cons 42 0)
           (cons 91 0)
           (list 10 33.66666667 3.57333333)
           (cons 40 0)
           (cons 41 0)
           (cons 42 0)
           (cons 91 0)
           (list 10 33.2 3.41666667)
           (cons 40 0)
           (cons 41 0)
           (cons 42 0)
           (cons 91 0)
           (list 10 30.8 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4.25 0)
           (cons 50 0)
          )
         )
         (entmake
          (list
           (cons 0 "POINT")
           (cons 100 "AcDbEntity")
           (cons 67 0)
           (cons 8 "0")
           (cons 100 "AcDbPoint")
           (list 10 40 -4.25 0)
           (cons 50 0)
          )
         )
         (entmake
          (list
           (cons 0 "POINT")
           (cons 100 "AcDbEntity")
           (cons 67 0)
           (cons 8 "0")
           (cons 100 "AcDbPoint")
           (list 10 0 4.25 0)
           (cons 50 0)
          )
         )
         (entmake
          (list
           (cons 0 "POINT")
           (cons 100 "AcDbEntity")
           (cons 67 0)
           (cons 8 "0")
           (cons 100 "AcDbPoint")
           (list 10 40 4.25 0)
           (cons 50 0)
          )
         )
         (entmake
          (list
           (cons 0 "POINT")
           (cons 100 "AcDbEntity")
           (cons 67 0)
           (cons 8 "0")
           (cons 100 "AcDbPoint")
           (list 10 7 4.25 0)
           (cons 50 0)
          )
         )
         (entmake
          (list
           (cons 0 "POINT")
           (cons 100 "AcDbEntity")
           (cons 67 0)
           (cons 8 "0")
           (cons 100 "AcDbPoint")
           (list 10 32 4.25 0)
           (cons 50 0)
          )
         )
         (entmake
          (list
           (cons 0 "POINT")
           (cons 100 "AcDbEntity")
           (cons 67 0)
           (cons 8 "0")
           (cons 100 "AcDbPoint")
           (list 10 32 -4.25 0)
           (cons 50 0)
          )
         )
         (entmake
          (list
           (cons 0 "POINT")
           (cons 100 "AcDbEntity")
           (cons 67 0)
           (cons 8 "0")
           (cons 100 "AcDbPoint")
           (list 10 7 -4.25 0)
           (cons 50 0)
          )
         )
         (entmake
          (list
           (cons 0 "POINT")
           (cons 100 "AcDbEntity")
           (cons 67 0)
           (cons 8 "0")
           (cons 100 "AcDbPoint")
           (list 10 7 0 0)
           (cons 50 0)
          )
         )
         (entmake
          (list
           (cons 0 "INSERT")
           (cons 100 "AcDbEntity")
           (cons 67 0)
           (cons 8 "0")
           (cons 100 "AcDbBlockReference")
           (cons 2 "WheelLeft2")
           (list 10 7 -3.41666667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRight2")
           (list 10 7 3.41666667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 4.70341207 1.85914261 0)
           (cons 40 0.65616798)
           (cons 1 "7.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 4.70341207 0.76552931 0)
           (cons 40 0.65616798)
           (cons 1 "7.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 4.70341207 -0.32808399 0)
           (cons 40 0.65616798)
           (cons 1 "32.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 4.70341207 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 4.70341207 -2.51531059 0)
           (cons 40 0.65616798)
           (cons 1 "41.4")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-BUS-45"))
        (progn
         (entmake)
         (entmake
          (list
           (cons 0 "BLOCK")
           (cons 2 "AASHTO-2011-BUS-45")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 -4.25)
           (cons 40 0)
           (cons 41 0)
           (cons 42 0)
           (cons 91 0)
           (list 10 45.5 -4.25)
           (cons 40 0)
           (cons 41 0)
           (cons 42 0)
           (cons 91 0)
           (list 10 45.5 4.25)
           (cons 40 0)
           (cons 41 0)
           (cons 42 0)
           (cons 91 0)
           (list 10 0 4.25)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 45.5 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 45.5 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 30.83333333 -4.09333333)
           (cons 40 0)
           (cons 41 0)
           (cons 42 0)
           (cons 91 0)
           (list 10 30.83333333 -3.57333333)
           (cons 40 0)
           (cons 41 0)
           (cons 42 0)
           (cons 91 0)
           (list 10 31.3 -3.41666667)
           (cons 40 0)
           (cons 41 0)
           (cons 42 0)
           (cons 91 0)
           (list 10 33.7 -3.41666667)
           (cons 40 0)
           (cons 41 0)
           (cons 42 0)
           (cons 91 0)
           (list 10 34.16666667 -3.57333333)
           (cons 40 0)
           (cons 41 0)
           (cons 42 0)
           (cons 91 0)
           (list 10 34.16666667 -4.09333333)
           (cons 40 0)
           (cons 41 0)
           (cons 42 0)
           (cons 91 0)
           (list 10 33.7 -4.25)
           (cons 40 0)
           (cons 41 0)
           (cons 42 0)
           (cons 91 0)
           (list 10 31.3 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 30.83333333 3.57333333)
           (cons 40 0)
           (cons 41 0)
           (cons 42 0)
           (cons 91 0)
           (list 10 30.83333333 4.09333333)
           (cons 40 0)
           (cons 41 0)
           (cons 42 0)
           (cons 91 0)
           (list 10 31.3 4.25)
           (cons 40 0)
           (cons 41 0)
           (cons 42 0)
           (cons 91 0)
           (list 10 33.7 4.25)
           (cons 40 0)
           (cons 41 0)
           (cons 42 0)
           (cons 91 0)
           (list 10 34.16666667 4.09333333)
           (cons 40 0)
           (cons 41 0)
           (cons 42 0)
           (cons 91 0)
           (list 10 34.16666667 3.57333333)
           (cons 40 0)
           (cons 41 0)
           (cons 42 0)
           (cons 91 0)
           (list 10 33.7 3.41666667)
           (cons 40 0)
           (cons 41 0)
           (cons 42 0)
           (cons 91 0)
           (list 10 31.3 3.41666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 34.83333333 -4.09333333)
           (cons 40 0)
           (cons 41 0)
           (cons 42 0)
           (cons 91 0)
           (list 10 34.83333333 -3.57333333)
           (cons 40 0)
           (cons 41 0)
           (cons 42 0)
           (cons 91 0)
           (list 10 35.3 -3.41666667)
           (cons 40 0)
           (cons 41 0)
           (cons 42 0)
           (cons 91 0)
           (list 10 37.7 -3.41666667)
           (cons 40 0)
           (cons 41 0)
           (cons 42 0)
           (cons 91 0)
           (list 10 38.16666667 -3.57333333)
           (cons 40 0)
           (cons 41 0)
           (cons 42 0)
           (cons 91 0)
           (list 10 38.16666667 -4.09333333)
           (cons 40 0)
           (cons 41 0)
           (cons 42 0)
           (cons 91 0)
           (list 10 37.7 -4.25)
           (cons 40 0)
           (cons 41 0)
           (cons 42 0)
           (cons 91 0)
           (list 10 35.3 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 34.83333333 3.57333333)
           (cons 40 0)
           (cons 41 0)
           (cons 42 0)
           (cons 91 0)
           (list 10 34.83333333 4.09333333)
           (cons 40 0)
           (cons 41 0)
           (cons 42 0)
           (cons 91 0)
           (list 10 35.3 4.25)
           (cons 40 0)
           (cons 41 0)
           (cons 42 0)
           (cons 91 0)
           (list 10 37.7 4.25)
           (cons 40 0)
           (cons 41 0)
           (cons 42 0)
           (cons 91 0)
           (list 10 38.16666667 4.09333333)
           (cons 40 0)
           (cons 41 0)
           (cons 42 0)
           (cons 91 0)
           (list 10 38.16666667 3.57333333)
           (cons 40 0)
           (cons 41 0)
           (cons 42 0)
           (cons 91 0)
           (list 10 37.7 3.41666667)
           (cons 40 0)
           (cons 41 0)
           (cons 42 0)
           (cons 91 0)
           (list 10 35.3 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4.25 0)
           (cons 50 0)
          )
         )
         (entmake
          (list
           (cons 0 "POINT")
           (cons 100 "AcDbEntity")
           (cons 67 0)
           (cons 8 "0")
           (cons 100 "AcDbPoint")
           (list 10 0 4.25 0)
           (cons 50 0)
          )
         )
         (entmake
          (list
           (cons 0 "POINT")
           (cons 100 "AcDbEntity")
           (cons 67 0)
           (cons 8 "0")
           (cons 100 "AcDbPoint")
           (list 10 6.2 4.25 0)
           (cons 50 0)
          )
         )
         (entmake
          (list
           (cons 0 "POINT")
           (cons 100 "AcDbEntity")
           (cons 67 0)
           (cons 8 "0")
           (cons 100 "AcDbPoint")
           (list 10 6.2 -4.25 0)
           (cons 50 0)
          )
         )
         (entmake
          (list
           (cons 0 "POINT")
           (cons 100 "AcDbEntity")
           (cons 67 0)
           (cons 8 "0")
           (cons 100 "AcDbPoint")
           (list 10 45.5 4.25 0)
           (cons 50 0)
          )
         )
         (entmake
          (list
           (cons 0 "POINT")
           (cons 100 "AcDbEntity")
           (cons 67 0)
           (cons 8 "0")
           (cons 100 "AcDbPoint")
           (list 10 45.5 -4.25 0)
           (cons 50 0)
          )
         )
         (entmake
          (list
           (cons 0 "POINT")
           (cons 100 "AcDbEntity")
           (cons 67 0)
           (cons 8 "0")
           (cons 100 "AcDbPoint")
           (list 10 6.2 0 0)
           (cons 50 0)
          )
         )
         (entmake
          (list
           (cons 0 "POINT")
           (cons 100 "AcDbEntity")
           (cons 67 0)
           (cons 8 "0")
           (cons 100 "AcDbPoint")
           (list 10 34.5 -4.25 0)
           (cons 50 0)
          )
         )
         (entmake
          (list
           (cons 0 "POINT")
           (cons 100 "AcDbEntity")
           (cons 67 0)
           (cons 8 "0")
           (cons 100 "AcDbPoint")
           (list 10 34.5 4.25 0)
           (cons 50 0)
          )
         )
         (entmake
          (list
           (cons 0 "INSERT")
           (cons 100 "AcDbEntity")
           (cons 67 0)
           (cons 8 "0")
           (cons 100 "AcDbBlockReference")
           (cons 2 "WheelRight2")
           (list 10 6.2 3.41666667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeft2")
           (list 10 6.2 -3.41666667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 3.90341207 1.85914261 0)
           (cons 40 0.65616798)
           (cons 1 "6.200")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 3.90341207 0.76552931 0)
           (cons 40 0.65616798)
           (cons 1 "6.200")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 3.90341207 -0.32808399 0)
           (cons 40 0.65616798)
           (cons 1 "34.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 3.90341207 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 3.90341207 -2.51531059 0)
           (cons 40 0.65616798)
           (cons 1 "45.2")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-BUS-40"))
        (progn
         (entmake)
         (entmake
          (list
           (cons 0 "BLOCK")
           (cons 2 "AASHTO-2011-BUS-40")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 -4.25)
           (cons 40 0)
           (cons 41 0)
           (cons 42 0)
           (cons 91 0)
           (list 10 40.5 -4.25)
           (cons 40 0)
           (cons 41 0)
           (cons 42 0)
           (cons 91 0)
           (list 10 40.5 4.25)
           (cons 40 0)
           (cons 41 0)
           (cons 42 0)
           (cons 91 0)
           (list 10 0 4.25)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 40.5 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 40.5 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 27.83333333 -2.59333333)
           (cons 40 0)
           (cons 41 0)
           (cons 42 0)
           (cons 91 0)
           (list 10 27.83333333 -2.07333333)
           (cons 40 0)
           (cons 41 0)
           (cons 42 0)
           (cons 91 0)
           (list 10 28.3 -1.91666667)
           (cons 40 0)
           (cons 41 0)
           (cons 42 0)
           (cons 91 0)
           (list 10 30.7 -1.91666667)
           (cons 40 0)
           (cons 41 0)
           (cons 42 0)
           (cons 91 0)
           (list 10 31.16666667 -2.07333333)
           (cons 40 0)
           (cons 41 0)
           (cons 42 0)
           (cons 91 0)
           (list 10 31.16666667 -2.59333333)
           (cons 40 0)
           (cons 41 0)
           (cons 42 0)
           (cons 91 0)
           (list 10 30.7 -2.75)
           (cons 40 0)
           (cons 41 0)
           (cons 42 0)
           (cons 91 0)
           (list 10 28.3 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 27.83333333 -4.09333333)
           (cons 40 0)
           (cons 41 0)
           (cons 42 0)
           (cons 91 0)
           (list 10 27.83333333 -3.57333333)
           (cons 40 0)
           (cons 41 0)
           (cons 42 0)
           (cons 91 0)
           (list 10 28.3 -3.41666667)
           (cons 40 0)
           (cons 41 0)
           (cons 42 0)
           (cons 91 0)
           (list 10 30.7 -3.41666667)
           (cons 40 0)
           (cons 41 0)
           (cons 42 0)
           (cons 91 0)
           (list 10 31.16666667 -3.57333333)
           (cons 40 0)
           (cons 41 0)
           (cons 42 0)
           (cons 91 0)
           (list 10 31.16666667 -4.09333333)
           (cons 40 0)
           (cons 41 0)
           (cons 42 0)
           (cons 91 0)
           (list 10 30.7 -4.25)
           (cons 40 0)
           (cons 41 0)
           (cons 42 0)
           (cons 91 0)
           (list 10 28.3 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 27.83333333 2.07333333)
           (cons 40 0)
           (cons 41 0)
           (cons 42 0)
           (cons 91 0)
           (list 10 27.83333333 2.59333333)
           (cons 40 0)
           (cons 41 0)
           (cons 42 0)
           (cons 91 0)
           (list 10 28.3 2.75)
           (cons 40 0)
           (cons 41 0)
           (cons 42 0)
           (cons 91 0)
           (list 10 30.7 2.75)
           (cons 40 0)
           (cons 41 0)
           (cons 42 0)
           (cons 91 0)
           (list 10 31.16666667 2.59333333)
           (cons 40 0)
           (cons 41 0)
           (cons 42 0)
           (cons 91 0)
           (list 10 31.16666667 2.07333333)
           (cons 40 0)
           (cons 41 0)
           (cons 42 0)
           (cons 91 0)
           (list 10 30.7 1.91666667)
           (cons 40 0)
           (cons 41 0)
           (cons 42 0)
           (cons 91 0)
           (list 10 28.3 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 27.83333333 3.57333333)
           (cons 40 0)
           (cons 41 0)
           (cons 42 0)
           (cons 91 0)
           (list 10 27.83333333 4.09333333)
           (cons 40 0)
           (cons 41 0)
           (cons 42 0)
           (cons 91 0)
           (list 10 28.3 4.25)
           (cons 40 0)
           (cons 41 0)
           (cons 42 0)
           (cons 91 0)
           (list 10 30.7 4.25)
           (cons 40 0)
           (cons 41 0)
           (cons 42 0)
           (cons 91 0)
           (list 10 31.16666667 4.09333333)
           (cons 40 0)
           (cons 41 0)
           (cons 42 0)
           (cons 91 0)
           (list 10 31.16666667 3.57333333)
           (cons 40 0)
           (cons 41 0)
           (cons 42 0)
           (cons 91 0)
           (list 10 30.7 3.41666667)
           (cons 40 0)
           (cons 41 0)
           (cons 42 0)
           (cons 91 0)
           (list 10 28.3 3.41666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 31.83333333 -2.59333333)
           (cons 40 0)
           (cons 41 0)
           (cons 42 0)
           (cons 91 0)
           (list 10 31.83333333 -2.07333333)
           (cons 40 0)
           (cons 41 0)
           (cons 42 0)
           (cons 91 0)
           (list 10 32.3 -1.91666667)
           (cons 40 0)
           (cons 41 0)
           (cons 42 0)
           (cons 91 0)
           (list 10 34.7 -1.91666667)
           (cons 40 0)
           (cons 41 0)
           (cons 42 0)
           (cons 91 0)
           (list 10 35.16666667 -2.07333333)
           (cons 40 0)
           (cons 41 0)
           (cons 42 0)
           (cons 91 0)
           (list 10 35.16666667 -2.59333333)
           (cons 40 0)
           (cons 41 0)
           (cons 42 0)
           (cons 91 0)
           (list 10 34.7 -2.75)
           (cons 40 0)
           (cons 41 0)
           (cons 42 0)
           (cons 91 0)
           (list 10 32.3 -2.75)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 31.83333333 -4.09333333)
           (cons 40 0)
           (cons 41 0)
           (cons 42 0)
           (cons 91 0)
           (list 10 31.83333333 -3.57333333)
           (cons 40 0)
           (cons 41 0)
           (cons 42 0)
           (cons 91 0)
           (list 10 32.3 -3.41666667)
           (cons 40 0)
           (cons 41 0)
           (cons 42 0)
           (cons 91 0)
           (list 10 34.7 -3.41666667)
           (cons 40 0)
           (cons 41 0)
           (cons 42 0)
           (cons 91 0)
           (list 10 35.16666667 -3.57333333)
           (cons 40 0)
           (cons 41 0)
           (cons 42 0)
           (cons 91 0)
           (list 10 35.16666667 -4.09333333)
           (cons 40 0)
           (cons 41 0)
           (cons 42 0)
           (cons 91 0)
           (list 10 34.7 -4.25)
           (cons 40 0)
           (cons 41 0)
           (cons 42 0)
           (cons 91 0)
           (list 10 32.3 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 31.83333333 2.07333333)
           (cons 40 0)
           (cons 41 0)
           (cons 42 0)
           (cons 91 0)
           (list 10 31.83333333 2.59333333)
           (cons 40 0)
           (cons 41 0)
           (cons 42 0)
           (cons 91 0)
           (list 10 32.3 2.75)
           (cons 40 0)
           (cons 41 0)
           (cons 42 0)
           (cons 91 0)
           (list 10 34.7 2.75)
           (cons 40 0)
           (cons 41 0)
           (cons 42 0)
           (cons 91 0)
           (list 10 35.16666667 2.59333333)
           (cons 40 0)
           (cons 41 0)
           (cons 42 0)
           (cons 91 0)
           (list 10 35.16666667 2.07333333)
           (cons 40 0)
           (cons 41 0)
           (cons 42 0)
           (cons 91 0)
           (list 10 34.7 1.91666667)
           (cons 40 0)
           (cons 41 0)
           (cons 42 0)
           (cons 91 0)
           (list 10 32.3 1.91666667)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 31.83333333 3.57333333)
           (cons 40 0)
           (cons 41 0)
           (cons 42 0)
           (cons 91 0)
           (list 10 31.83333333 4.09333333)
           (cons 40 0)
           (cons 41 0)
           (cons 42 0)
           (cons 91 0)
           (list 10 32.3 4.25)
           (cons 40 0)
           (cons 41 0)
           (cons 42 0)
           (cons 91 0)
           (list 10 34.7 4.25)
           (cons 40 0)
           (cons 41 0)
           (cons 42 0)
           (cons 91 0)
           (list 10 35.16666667 4.09333333)
           (cons 40 0)
           (cons 41 0)
           (cons 42 0)
           (cons 91 0)
           (list 10 35.16666667 3.57333333)
           (cons 40 0)
           (cons 41 0)
           (cons 42 0)
           (cons 91 0)
           (list 10 34.7 3.41666667)
           (cons 40 0)
           (cons 41 0)
           (cons 42 0)
           (cons 91 0)
           (list 10 32.3 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -4.25 0)
           (cons 50 0)
          )
         )
         (entmake
          (list
           (cons 0 "POINT")
           (cons 100 "AcDbEntity")
           (cons 67 0)
           (cons 8 "0")
           (cons 100 "AcDbPoint")
           (list 10 0 4.25 0)
           (cons 50 0)
          )
         )
         (entmake
          (list
           (cons 0 "POINT")
           (cons 100 "AcDbEntity")
           (cons 67 0)
           (cons 8 "0")
           (cons 100 "AcDbPoint")
           (list 10 40.5 4.25 0)
           (cons 50 0)
          )
         )
         (entmake
          (list
           (cons 0 "POINT")
           (cons 100 "AcDbEntity")
           (cons 67 0)
           (cons 8 "0")
           (cons 100 "AcDbPoint")
           (list 10 40.5 -4.25 0)
           (cons 50 0)
          )
         )
         (entmake
          (list
           (cons 0 "POINT")
           (cons 100 "AcDbEntity")
           (cons 67 0)
           (cons 8 "0")
           (cons 100 "AcDbPoint")
           (list 10 6.3 -4.25 0)
           (cons 50 0)
          )
         )
         (entmake
          (list
           (cons 0 "POINT")
           (cons 100 "AcDbEntity")
           (cons 67 0)
           (cons 8 "0")
           (cons 100 "AcDbPoint")
           (list 10 6.3 4.25 0)
           (cons 50 0)
          )
         )
         (entmake
          (list
           (cons 0 "POINT")
           (cons 100 "AcDbEntity")
           (cons 67 0)
           (cons 8 "0")
           (cons 100 "AcDbPoint")
           (list 10 6.3 0 0)
           (cons 50 0)
          )
         )
         (entmake
          (list
           (cons 0 "POINT")
           (cons 100 "AcDbEntity")
           (cons 67 0)
           (cons 8 "0")
           (cons 100 "AcDbPoint")
           (list 10 31.5 -4.25 0)
           (cons 50 0)
          )
         )
         (entmake
          (list
           (cons 0 "POINT")
           (cons 100 "AcDbEntity")
           (cons 67 0)
           (cons 8 "0")
           (cons 100 "AcDbPoint")
           (list 10 31.5 4.25 0)
           (cons 50 0)
          )
         )
         (entmake
          (list
           (cons 0 "INSERT")
           (cons 100 "AcDbEntity")
           (cons 67 0)
           (cons 8 "0")
           (cons 100 "AcDbBlockReference")
           (cons 2 "WheelLeft2")
           (list 10 6.3 -3.41666667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRight2")
           (list 10 6.3 3.41666667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 4.00341207 1.85914261 0)
           (cons 40 0.65616798)
           (cons 1 "6.300")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 4.00341207 0.76552931 0)
           (cons 40 0.65616798)
           (cons 1 "6.300")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 4.00341207 -0.32808399 0)
           (cons 40 0.65616798)
           (cons 1 "31.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 4.00341207 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 4.00341207 -2.51531059 0)
           (cons 40 0.65616798)
           (cons 1 "41.9")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-A-BUS-REAR"))
        (progn
         (entmake)
         (entmake
          (list
           (cons 0 "BLOCK")
           (cons 2 "AASHTO-2011-A-BUS-REAR")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 5)
           (cons 70 129)
           (cons 43 0)
           (cons 38 0)
           (cons 39 0)
           (list 10 0 0)
           (cons 40 0)
           (cons 41 0)
           (cons 42 0)
           (cons 91 0)
           (list 10 2 4.25)
           (cons 40 0)
           (cons 41 0)
           (cons 42 0)
           (cons 91 0)
           (list 10 23.2 4.25)
           (cons 40 0)
           (cons 41 0)
           (cons 42 0)
           (cons 91 0)
           (list 10 23.2 -4.25)
           (cons 40 0)
           (cons 41 0)
           (cons 42 0)
           (cons 91 0)
           (list 10 2 -4.25)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 23.2 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 23.2 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2 -4.25 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 2 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.56666667)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.53333333 -4.09333333)
           (cons 40 0)
           (cons 41 0)
           (cons 42 0)
           (cons 91 0)
           (list 10 11.53333333 -3.57333333)
           (cons 40 0)
           (cons 41 0)
           (cons 42 0)
           (cons 91 0)
           (list 10 12 -3.41666667)
           (cons 40 0)
           (cons 41 0)
           (cons 42 0)
           (cons 91 0)
           (list 10 14.4 -3.41666667)
           (cons 40 0)
           (cons 41 0)
           (cons 42 0)
           (cons 91 0)
           (list 10 14.86666667 -3.57333333)
           (cons 40 0)
           (cons 41 0)
           (cons 42 0)
           (cons 91 0)
           (list 10 14.86666667 -4.09333333)
           (cons 40 0)
           (cons 41 0)
           (cons 42 0)
           (cons 91 0)
           (list 10 14.4 -4.25)
           (cons 40 0)
           (cons 41 0)
           (cons 42 0)
           (cons 91 0)
           (list 10 12 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.53333333 3.57333333)
           (cons 40 0)
           (cons 41 0)
           (cons 42 0)
           (cons 91 0)
           (list 10 11.53333333 4.09333333)
           (cons 40 0)
           (cons 41 0)
           (cons 42 0)
           (cons 91 0)
           (list 10 12 4.25)
           (cons 40 0)
           (cons 41 0)
           (cons 42 0)
           (cons 91 0)
           (list 10 14.4 4.25)
           (cons 40 0)
           (cons 41 0)
           (cons 42 0)
           (cons 91 0)
           (list 10 14.86666667 4.09333333)
           (cons 40 0)
           (cons 41 0)
           (cons 42 0)
           (cons 91 0)
           (list 10 14.86666667 3.57333333)
           (cons 40 0)
           (cons 41 0)
           (cons 42 0)
           (cons 91 0)
           (list 10 14.4 3.41666667)
           (cons 40 0)
           (cons 41 0)
           (cons 42 0)
           (cons 91 0)
           (list 10 12 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 13.2 -4.25 0)
           (cons 50 0)
          )
         )
         (entmake
          (list
           (cons 0 "POINT")
           (cons 100 "AcDbEntity")
           (cons 67 0)
           (cons 8 "0")
           (cons 100 "AcDbPoint")
           (list 10 13.2 4.25 0)
           (cons 50 0)
          )
         )
         (entmake
          (list
           (cons 0 "POINT")
           (cons 100 "AcDbEntity")
           (cons 67 0)
           (cons 8 "0")
           (cons 100 "AcDbPoint")
           (list 10 2 4.25 0)
           (cons 50 0)
          )
         )
         (entmake
          (list
           (cons 0 "POINT")
           (cons 100 "AcDbEntity")
           (cons 67 0)
           (cons 8 "0")
           (cons 100 "AcDbPoint")
           (list 10 23.2 4.25 0)
           (cons 50 0)
          )
         )
         (entmake
          (list
           (cons 0 "POINT")
           (cons 100 "AcDbEntity")
           (cons 67 0)
           (cons 8 "0")
           (cons 100 "AcDbPoint")
           (list 10 23.2 -4.25 0)
           (cons 50 0)
          )
         )
         (entmake
          (list
           (cons 0 "POINT")
           (cons 100 "AcDbEntity")
           (cons 67 0)
           (cons 8 "0")
           (cons 100 "AcDbPoint")
           (list 10 2 -4.25 0)
           (cons 50 0)
          )
         )
         (entmake
          (list
           (cons 0 "ATTDEF")
           (cons 100 "AcDbEntity")
           (cons 67 0)
           (cons 8 "0")
           (cons 100 "AcDbText")
           (list 10 -2.29658793 1.85914261 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 0.76552931 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -0.32808399 0)
           (cons 40 0.65616798)
           (cons 1 "13.200")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -1.42169729 0)
           (cons 40 0.65616798)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -2.29658793 -2.51531059 0)
           (cons 40 0.65616798)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AASHTO-2011-A-BUS-FRONT"))
        (progn
         (entmake)
         (entmake
          (list
           (cons 0 "BLOCK")
           (cons 2 "AASHTO-2011-A-BUS-FRONT")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 5)
           (cons 70 129)
           (cons 43 0)
           (cons 38 0)
           (cons 39 0)
           (list 10 0 4.25)
           (cons 40 0)
           (cons 41 0)
           (cons 42 0)
           (cons 91 0)
           (list 10 34.8 4.25)
           (cons 40 0)
           (cons 41 0)
           (cons 42 0)
           (cons 91 0)
           (list 10 36.8 0)
           (cons 40 0)
           (cons 41 0)
           (cons 42 0)
           (cons 91 0)
           (list 10 34.8 -4.25)
           (cons 40 0)
           (cons 41 0)
           (cons 42 0)
           (cons 91 0)
           (list 10 0 -4.25)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 34.8 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 34.8 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -4.25 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 34.8 0 0)
           (list 11 36.8 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 36.8 0 0)
           (cons 40 0.33333333)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 28.93333333 -4.09333333)
           (cons 40 0)
           (cons 41 0)
           (cons 42 0)
           (cons 91 0)
           (list 10 28.93333333 -3.57333333)
           (cons 40 0)
           (cons 41 0)
           (cons 42 0)
           (cons 91 0)
           (list 10 29.4 -3.41666667)
           (cons 40 0)
           (cons 41 0)
           (cons 42 0)
           (cons 91 0)
           (list 10 31.8 -3.41666667)
           (cons 40 0)
           (cons 41 0)
           (cons 42 0)
           (cons 91 0)
           (list 10 32.26666667 -3.57333333)
           (cons 40 0)
           (cons 41 0)
           (cons 42 0)
           (cons 91 0)
           (list 10 32.26666667 -4.09333333)
           (cons 40 0)
           (cons 41 0)
           (cons 42 0)
           (cons 91 0)
           (list 10 31.8 -4.25)
           (cons 40 0)
           (cons 41 0)
           (cons 42 0)
           (cons 91 0)
           (list 10 29.4 -4.25)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 28.93333333 3.57333333)
           (cons 40 0)
           (cons 41 0)
           (cons 42 0)
           (cons 91 0)
           (list 10 28.93333333 4.09333333)
           (cons 40 0)
           (cons 41 0)
           (cons 42 0)
           (cons 91 0)
           (list 10 29.4 4.25)
           (cons 40 0)
           (cons 41 0)
           (cons 42 0)
           (cons 91 0)
           (list 10 31.8 4.25)
           (cons 40 0)
           (cons 41 0)
           (cons 42 0)
           (cons 91 0)
           (list 10 32.26666667 4.09333333)
           (cons 40 0)
           (cons 41 0)
           (cons 42 0)
           (cons 91 0)
           (list 10 32.26666667 3.57333333)
           (cons 40 0)
           (cons 41 0)
           (cons 42 0)
           (cons 91 0)
           (list 10 31.8 3.41666667)
           (cons 40 0)
           (cons 41 0)
           (cons 42 0)
           (cons 91 0)
           (list 10 29.4 3.41666667)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 8.6 0 0)
           (cons 50 0)
          )
         )
         (entmake
          (list
           (cons 0 "POINT")
           (cons 100 "AcDbEntity")
           (cons 67 0)
           (cons 8 "0")
           (cons 100 "AcDbPoint")
           (list 10 0 -4.25 0)
           (cons 50 0)
          )
         )
         (entmake
          (list
           (cons 0 "POINT")
           (cons 100 "AcDbEntity")
           (cons 67 0)
           (cons 8 "0")
           (cons 100 "AcDbPoint")
           (list 10 0 4.25 0)
           (cons 50 0)
          )
         )
         (entmake
          (list
           (cons 0 "POINT")
           (cons 100 "AcDbEntity")
           (cons 67 0)
           (cons 8 "0")
           (cons 100 "AcDbPoint")
           (list 10 30.6 4.25 0)
           (cons 50 0)
          )
         )
         (entmake
          (list
           (cons 0 "POINT")
           (cons 100 "AcDbEntity")
           (cons 67 0)
           (cons 8 "0")
           (cons 100 "AcDbPoint")
           (list 10 30.6 -4.25 0)
           (cons 50 0)
          )
         )
         (entmake
          (list
           (cons 0 "POINT")
           (cons 100 "AcDbEntity")
           (cons 67 0)
           (cons 8 "0")
           (cons 100 "AcDbPoint")
           (list 10 8.6 -4.25 0)
           (cons 50 0)
          )
         )
         (entmake
          (list
           (cons 0 "POINT")
           (cons 100 "AcDbEntity")
           (cons 67 0)
           (cons 8 "0")
           (cons 100 "AcDbPoint")
           (list 10 8.6 4.25 0)
           (cons 50 0)
          )
         )
         (entmake
          (list
           (cons 0 "POINT")
           (cons 100 "AcDbEntity")
           (cons 67 0)
           (cons 8 "0")
           (cons 100 "AcDbPoint")
           (list 10 36.8 0 0)
           (cons 50 0)
          )
         )
         (entmake
          (list
           (cons 0 "INSERT")
           (cons 100 "AcDbEntity")
           (cons 67 0)
           (cons 8 "0")
           (cons 100 "AcDbBlockReference")
           (cons 2 "WheelLeft2")
           (list 10 8.6 -3.41666667 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRight2")
           (list 10 8.6 3.41666667 0)
           (cons 41 1)
           (cons 42 1)
           (cons 43 1)
           (cons 50 0)
           (cons 70 0)
           (cons 71 0)
           (cons 44 0)
           (cons 45 0)
          )
         )
         (entmake
          (list
           (cons 0 "ATTDEF")
           (cons 100 "AcDbEntity")
           (cons 67 0)
           (cons 8 "0")
           (cons 100 "AcDbText")
           (list 10 6.30341207 1.85914261 0)
           (cons 40 0.65616798)
           (cons 1 "8.500")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 6.30341207 0.76552931 0)
           (cons 40 0.65616798)
           (cons 1 "8.500")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 6.30341207 -0.32808399 0)
           (cons 40 0.65616798)
           (cons 1 "30.600")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 6.30341207 -1.42169729 0)
           (cons 40 0.65616798)
           (cons 1 "36.800")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 6.30341207 -2.51531059 0)
           (cons 40 0.65616798)
           (cons 1 "38.3")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-36-TRAILER2"))
        (progn
         (entmake)
         (entmake
          (list
           (cons 0 "BLOCK")
           (cons 2 "AB_INF-WB-36-TRAILER2")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 -1.3)
           (cons 40 0)
           (cons 41 0)
           (cons 42 0)
           (cons 91 0)
           (list 10 16.2 -1.3)
           (cons 40 0)
           (cons 41 0)
           (cons 42 0)
           (cons 91 0)
           (list 10 16.2 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 16.2 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 16.2 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.3062 -0.7445528)
           (cons 40 0)
           (cons 41 0)
           (cons 42 0)
           (cons 91 0)
           (list 10 13.3062 -0.5702072)
           (cons 40 0)
           (cons 41 0)
           (cons 42 0)
           (cons 91 0)
           (list 10 13.462664 -0.51768)
           (cons 40 0)
           (cons 41 0)
           (cons 42 0)
           (cons 91 0)
           (list 10 14.267336 -0.51768)
           (cons 40 0)
           (cons 41 0)
           (cons 42 0)
           (cons 91 0)
           (list 10 14.4238 -0.5702072)
           (cons 40 0)
           (cons 41 0)
           (cons 42 0)
           (cons 91 0)
           (list 10 14.4238 -0.7445528)
           (cons 40 0)
           (cons 41 0)
           (cons 42 0)
           (cons 91 0)
           (list 10 14.267336 -0.79708)
           (cons 40 0)
           (cons 41 0)
           (cons 42 0)
           (cons 91 0)
           (list 10 13.462664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.3062 -1.2474728)
           (cons 40 0)
           (cons 41 0)
           (cons 42 0)
           (cons 91 0)
           (list 10 13.3062 -1.0731272)
           (cons 40 0)
           (cons 41 0)
           (cons 42 0)
           (cons 91 0)
           (list 10 13.462664 -1.0206)
           (cons 40 0)
           (cons 41 0)
           (cons 42 0)
           (cons 91 0)
           (list 10 14.267336 -1.0206)
           (cons 40 0)
           (cons 41 0)
           (cons 42 0)
           (cons 91 0)
           (list 10 14.4238 -1.0731272)
           (cons 40 0)
           (cons 41 0)
           (cons 42 0)
           (cons 91 0)
           (list 10 14.4238 -1.2474728)
           (cons 40 0)
           (cons 41 0)
           (cons 42 0)
           (cons 91 0)
           (list 10 14.267336 -1.3)
           (cons 40 0)
           (cons 41 0)
           (cons 42 0)
           (cons 91 0)
           (list 10 13.462664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.3062 0.5702072)
           (cons 40 0)
           (cons 41 0)
           (cons 42 0)
           (cons 91 0)
           (list 10 13.3062 0.7445528)
           (cons 40 0)
           (cons 41 0)
           (cons 42 0)
           (cons 91 0)
           (list 10 13.462664 0.79708)
           (cons 40 0)
           (cons 41 0)
           (cons 42 0)
           (cons 91 0)
           (list 10 14.267336 0.79708)
           (cons 40 0)
           (cons 41 0)
           (cons 42 0)
           (cons 91 0)
           (list 10 14.4238 0.7445528)
           (cons 40 0)
           (cons 41 0)
           (cons 42 0)
           (cons 91 0)
           (list 10 14.4238 0.5702072)
           (cons 40 0)
           (cons 41 0)
           (cons 42 0)
           (cons 91 0)
           (list 10 14.267336 0.51768)
           (cons 40 0)
           (cons 41 0)
           (cons 42 0)
           (cons 91 0)
           (list 10 13.462664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.3062 1.0731272)
           (cons 40 0)
           (cons 41 0)
           (cons 42 0)
           (cons 91 0)
           (list 10 13.3062 1.2474728)
           (cons 40 0)
           (cons 41 0)
           (cons 42 0)
           (cons 91 0)
           (list 10 13.462664 1.3)
           (cons 40 0)
           (cons 41 0)
           (cons 42 0)
           (cons 91 0)
           (list 10 14.267336 1.3)
           (cons 40 0)
           (cons 41 0)
           (cons 42 0)
           (cons 91 0)
           (list 10 14.4238 1.2474728)
           (cons 40 0)
           (cons 41 0)
           (cons 42 0)
           (cons 91 0)
           (list 10 14.4238 1.0731272)
           (cons 40 0)
           (cons 41 0)
           (cons 42 0)
           (cons 91 0)
           (list 10 14.267336 1.0206)
           (cons 40 0)
           (cons 41 0)
           (cons 42 0)
           (cons 91 0)
           (list 10 13.462664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.5762 -0.7445528)
           (cons 40 0)
           (cons 41 0)
           (cons 42 0)
           (cons 91 0)
           (list 10 14.5762 -0.5702072)
           (cons 40 0)
           (cons 41 0)
           (cons 42 0)
           (cons 91 0)
           (list 10 14.732664 -0.51768)
           (cons 40 0)
           (cons 41 0)
           (cons 42 0)
           (cons 91 0)
           (list 10 15.537336 -0.51768)
           (cons 40 0)
           (cons 41 0)
           (cons 42 0)
           (cons 91 0)
           (list 10 15.6938 -0.5702072)
           (cons 40 0)
           (cons 41 0)
           (cons 42 0)
           (cons 91 0)
           (list 10 15.6938 -0.7445528)
           (cons 40 0)
           (cons 41 0)
           (cons 42 0)
           (cons 91 0)
           (list 10 15.537336 -0.79708)
           (cons 40 0)
           (cons 41 0)
           (cons 42 0)
           (cons 91 0)
           (list 10 14.732664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.5762 -1.2474728)
           (cons 40 0)
           (cons 41 0)
           (cons 42 0)
           (cons 91 0)
           (list 10 14.5762 -1.0731272)
           (cons 40 0)
           (cons 41 0)
           (cons 42 0)
           (cons 91 0)
           (list 10 14.732664 -1.0206)
           (cons 40 0)
           (cons 41 0)
           (cons 42 0)
           (cons 91 0)
           (list 10 15.537336 -1.0206)
           (cons 40 0)
           (cons 41 0)
           (cons 42 0)
           (cons 91 0)
           (list 10 15.6938 -1.0731272)
           (cons 40 0)
           (cons 41 0)
           (cons 42 0)
           (cons 91 0)
           (list 10 15.6938 -1.2474728)
           (cons 40 0)
           (cons 41 0)
           (cons 42 0)
           (cons 91 0)
           (list 10 15.537336 -1.3)
           (cons 40 0)
           (cons 41 0)
           (cons 42 0)
           (cons 91 0)
           (list 10 14.732664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.5762 0.5702072)
           (cons 40 0)
           (cons 41 0)
           (cons 42 0)
           (cons 91 0)
           (list 10 14.5762 0.7445528)
           (cons 40 0)
           (cons 41 0)
           (cons 42 0)
           (cons 91 0)
           (list 10 14.732664 0.79708)
           (cons 40 0)
           (cons 41 0)
           (cons 42 0)
           (cons 91 0)
           (list 10 15.537336 0.79708)
           (cons 40 0)
           (cons 41 0)
           (cons 42 0)
           (cons 91 0)
           (list 10 15.6938 0.7445528)
           (cons 40 0)
           (cons 41 0)
           (cons 42 0)
           (cons 91 0)
           (list 10 15.6938 0.5702072)
           (cons 40 0)
           (cons 41 0)
           (cons 42 0)
           (cons 91 0)
           (list 10 15.537336 0.51768)
           (cons 40 0)
           (cons 41 0)
           (cons 42 0)
           (cons 91 0)
           (list 10 14.732664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.5762 1.0731272)
           (cons 40 0)
           (cons 41 0)
           (cons 42 0)
           (cons 91 0)
           (list 10 14.5762 1.2474728)
           (cons 40 0)
           (cons 41 0)
           (cons 42 0)
           (cons 91 0)
           (list 10 14.732664 1.3)
           (cons 40 0)
           (cons 41 0)
           (cons 42 0)
           (cons 91 0)
           (list 10 15.537336 1.3)
           (cons 40 0)
           (cons 41 0)
           (cons 42 0)
           (cons 91 0)
           (list 10 15.6938 1.2474728)
           (cons 40 0)
           (cons 41 0)
           (cons 42 0)
           (cons 91 0)
           (list 10 15.6938 1.0731272)
           (cons 40 0)
           (cons 41 0)
           (cons 42 0)
           (cons 91 0)
           (list 10 15.537336 1.0206)
           (cons 40 0)
           (cons 41 0)
           (cons 42 0)
           (cons 91 0)
           (list 10 14.732664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 2 0 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 16.2 -1.3 0)
           (cons 50 0)
          )
         )
         (entmake
          (list
           (cons 0 "POINT")
           (cons 100 "AcDbEntity")
           (cons 67 0)
           (cons 8 "0")
           (cons 100 "AcDbPoint")
           (list 10 16.2 1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 14.5 1.3 0)
           (cons 50 0)
          )
         )
         (entmake
          (list
           (cons 0 "POINT")
           (cons 100 "AcDbEntity")
           (cons 67 0)
           (cons 8 "0")
           (cons 100 "AcDbPoint")
           (list 10 14.5 -1.3 0)
           (cons 50 0)
          )
         )
         (entmake
          (list
           (cons 0 "ATTDEF")
           (cons 100 "AcDbEntity")
           (cons 67 0)
           (cons 8 "0")
           (cons 100 "AcDbText")
           (list 10 1.3 0.56666667 0)
           (cons 40 0.2)
           (cons 1 "2.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.3 0.23333333 0)
           (cons 40 0.2)
           (cons 1 "2.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.3 -0.1 0)
           (cons 40 0.2)
           (cons 1 "14.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.3 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.3 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-36-PUP"))
        (progn
         (entmake)
         (entmake
          (list
           (cons 0 "BLOCK")
           (cons 2 "AB_INF-WB-36-PUP")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 3)
           (cons 70 129)
           (cons 43 0)
           (cons 38 0)
           (cons 39 0)
           (list 10 0 0)
           (cons 40 0)
           (cons 41 0)
           (cons 42 0)
           (cons 91 0)
           (list 10 3.7 -1.3)
           (cons 40 0)
           (cons 41 0)
           (cons 42 0)
           (cons 91 0)
           (list 10 3.7 1.3)
           (cons 40 0)
           (cons 41 0)
           (cons 42 0)
           (cons 91 0)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 3.7 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.1412 -0.7445528)
           (cons 40 0)
           (cons 41 0)
           (cons 42 0)
           (cons 91 0)
           (list 10 3.1412 -0.5702072)
           (cons 40 0)
           (cons 41 0)
           (cons 42 0)
           (cons 91 0)
           (list 10 3.297664 -0.51768)
           (cons 40 0)
           (cons 41 0)
           (cons 42 0)
           (cons 91 0)
           (list 10 4.102336 -0.51768)
           (cons 40 0)
           (cons 41 0)
           (cons 42 0)
           (cons 91 0)
           (list 10 4.2588 -0.5702072)
           (cons 40 0)
           (cons 41 0)
           (cons 42 0)
           (cons 91 0)
           (list 10 4.2588 -0.7445528)
           (cons 40 0)
           (cons 41 0)
           (cons 42 0)
           (cons 91 0)
           (list 10 4.102336 -0.79708)
           (cons 40 0)
           (cons 41 0)
           (cons 42 0)
           (cons 91 0)
           (list 10 3.297664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.1412 -1.2474728)
           (cons 40 0)
           (cons 41 0)
           (cons 42 0)
           (cons 91 0)
           (list 10 3.1412 -1.0731272)
           (cons 40 0)
           (cons 41 0)
           (cons 42 0)
           (cons 91 0)
           (list 10 3.297664 -1.0206)
           (cons 40 0)
           (cons 41 0)
           (cons 42 0)
           (cons 91 0)
           (list 10 4.102336 -1.0206)
           (cons 40 0)
           (cons 41 0)
           (cons 42 0)
           (cons 91 0)
           (list 10 4.2588 -1.0731272)
           (cons 40 0)
           (cons 41 0)
           (cons 42 0)
           (cons 91 0)
           (list 10 4.2588 -1.2474728)
           (cons 40 0)
           (cons 41 0)
           (cons 42 0)
           (cons 91 0)
           (list 10 4.102336 -1.3)
           (cons 40 0)
           (cons 41 0)
           (cons 42 0)
           (cons 91 0)
           (list 10 3.297664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.1412 0.5702072)
           (cons 40 0)
           (cons 41 0)
           (cons 42 0)
           (cons 91 0)
           (list 10 3.1412 0.7445528)
           (cons 40 0)
           (cons 41 0)
           (cons 42 0)
           (cons 91 0)
           (list 10 3.297664 0.79708)
           (cons 40 0)
           (cons 41 0)
           (cons 42 0)
           (cons 91 0)
           (list 10 4.102336 0.79708)
           (cons 40 0)
           (cons 41 0)
           (cons 42 0)
           (cons 91 0)
           (list 10 4.2588 0.7445528)
           (cons 40 0)
           (cons 41 0)
           (cons 42 0)
           (cons 91 0)
           (list 10 4.2588 0.5702072)
           (cons 40 0)
           (cons 41 0)
           (cons 42 0)
           (cons 91 0)
           (list 10 4.102336 0.51768)
           (cons 40 0)
           (cons 41 0)
           (cons 42 0)
           (cons 91 0)
           (list 10 3.297664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.1412 1.0731272)
           (cons 40 0)
           (cons 41 0)
           (cons 42 0)
           (cons 91 0)
           (list 10 3.1412 1.2474728)
           (cons 40 0)
           (cons 41 0)
           (cons 42 0)
           (cons 91 0)
           (list 10 3.297664 1.3)
           (cons 40 0)
           (cons 41 0)
           (cons 42 0)
           (cons 91 0)
           (list 10 4.102336 1.3)
           (cons 40 0)
           (cons 41 0)
           (cons 42 0)
           (cons 91 0)
           (list 10 4.2588 1.2474728)
           (cons 40 0)
           (cons 41 0)
           (cons 42 0)
           (cons 91 0)
           (list 10 4.2588 1.0731272)
           (cons 40 0)
           (cons 41 0)
           (cons 42 0)
           (cons 91 0)
           (list 10 4.102336 1.0206)
           (cons 40 0)
           (cons 41 0)
           (cons 42 0)
           (cons 91 0)
           (list 10 3.297664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 3.7 -1.3 0)
           (cons 50 0)
          )
         )
         (entmake
          (list
           (cons 0 "POINT")
           (cons 100 "AcDbEntity")
           (cons 67 0)
           (cons 8 "0")
           (cons 100 "AcDbPoint")
           (list 10 3.7 1.3 0)
           (cons 50 0)
          )
         )
         (entmake
          (list
           (cons 0 "POINT")
           (cons 100 "AcDbEntity")
           (cons 67 0)
           (cons 8 "0")
           (cons 100 "AcDbPoint")
           (list 10 3.7 0 0)
           (cons 50 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "3.700")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "3.700")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-36-TRAILER1"))
        (progn
         (entmake)
         (entmake
          (list
           (cons 0 "BLOCK")
           (cons 2 "AB_INF-WB-36-TRAILER1")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 -1.3)
           (cons 40 0)
           (cons 41 0)
           (cons 42 0)
           (cons 91 0)
           (list 10 16.2 -1.3)
           (cons 40 0)
           (cons 41 0)
           (cons 42 0)
           (cons 91 0)
           (list 10 16.2 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 16.2 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 16.2 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.2062 -0.7445528)
           (cons 40 0)
           (cons 41 0)
           (cons 42 0)
           (cons 91 0)
           (list 10 13.2062 -0.5702072)
           (cons 40 0)
           (cons 41 0)
           (cons 42 0)
           (cons 91 0)
           (list 10 13.362664 -0.51768)
           (cons 40 0)
           (cons 41 0)
           (cons 42 0)
           (cons 91 0)
           (list 10 14.167336 -0.51768)
           (cons 40 0)
           (cons 41 0)
           (cons 42 0)
           (cons 91 0)
           (list 10 14.3238 -0.5702072)
           (cons 40 0)
           (cons 41 0)
           (cons 42 0)
           (cons 91 0)
           (list 10 14.3238 -0.7445528)
           (cons 40 0)
           (cons 41 0)
           (cons 42 0)
           (cons 91 0)
           (list 10 14.167336 -0.79708)
           (cons 40 0)
           (cons 41 0)
           (cons 42 0)
           (cons 91 0)
           (list 10 13.362664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.2062 -1.2474728)
           (cons 40 0)
           (cons 41 0)
           (cons 42 0)
           (cons 91 0)
           (list 10 13.2062 -1.0731272)
           (cons 40 0)
           (cons 41 0)
           (cons 42 0)
           (cons 91 0)
           (list 10 13.362664 -1.0206)
           (cons 40 0)
           (cons 41 0)
           (cons 42 0)
           (cons 91 0)
           (list 10 14.167336 -1.0206)
           (cons 40 0)
           (cons 41 0)
           (cons 42 0)
           (cons 91 0)
           (list 10 14.3238 -1.0731272)
           (cons 40 0)
           (cons 41 0)
           (cons 42 0)
           (cons 91 0)
           (list 10 14.3238 -1.2474728)
           (cons 40 0)
           (cons 41 0)
           (cons 42 0)
           (cons 91 0)
           (list 10 14.167336 -1.3)
           (cons 40 0)
           (cons 41 0)
           (cons 42 0)
           (cons 91 0)
           (list 10 13.362664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.2062 0.5702072)
           (cons 40 0)
           (cons 41 0)
           (cons 42 0)
           (cons 91 0)
           (list 10 13.2062 0.7445528)
           (cons 40 0)
           (cons 41 0)
           (cons 42 0)
           (cons 91 0)
           (list 10 13.362664 0.79708)
           (cons 40 0)
           (cons 41 0)
           (cons 42 0)
           (cons 91 0)
           (list 10 14.167336 0.79708)
           (cons 40 0)
           (cons 41 0)
           (cons 42 0)
           (cons 91 0)
           (list 10 14.3238 0.7445528)
           (cons 40 0)
           (cons 41 0)
           (cons 42 0)
           (cons 91 0)
           (list 10 14.3238 0.5702072)
           (cons 40 0)
           (cons 41 0)
           (cons 42 0)
           (cons 91 0)
           (list 10 14.167336 0.51768)
           (cons 40 0)
           (cons 41 0)
           (cons 42 0)
           (cons 91 0)
           (list 10 13.362664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.2062 1.0731272)
           (cons 40 0)
           (cons 41 0)
           (cons 42 0)
           (cons 91 0)
           (list 10 13.2062 1.2474728)
           (cons 40 0)
           (cons 41 0)
           (cons 42 0)
           (cons 91 0)
           (list 10 13.362664 1.3)
           (cons 40 0)
           (cons 41 0)
           (cons 42 0)
           (cons 91 0)
           (list 10 14.167336 1.3)
           (cons 40 0)
           (cons 41 0)
           (cons 42 0)
           (cons 91 0)
           (list 10 14.3238 1.2474728)
           (cons 40 0)
           (cons 41 0)
           (cons 42 0)
           (cons 91 0)
           (list 10 14.3238 1.0731272)
           (cons 40 0)
           (cons 41 0)
           (cons 42 0)
           (cons 91 0)
           (list 10 14.167336 1.0206)
           (cons 40 0)
           (cons 41 0)
           (cons 42 0)
           (cons 91 0)
           (list 10 13.362664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.4762 -0.7445528)
           (cons 40 0)
           (cons 41 0)
           (cons 42 0)
           (cons 91 0)
           (list 10 14.4762 -0.5702072)
           (cons 40 0)
           (cons 41 0)
           (cons 42 0)
           (cons 91 0)
           (list 10 14.632664 -0.51768)
           (cons 40 0)
           (cons 41 0)
           (cons 42 0)
           (cons 91 0)
           (list 10 15.437336 -0.51768)
           (cons 40 0)
           (cons 41 0)
           (cons 42 0)
           (cons 91 0)
           (list 10 15.5938 -0.5702072)
           (cons 40 0)
           (cons 41 0)
           (cons 42 0)
           (cons 91 0)
           (list 10 15.5938 -0.7445528)
           (cons 40 0)
           (cons 41 0)
           (cons 42 0)
           (cons 91 0)
           (list 10 15.437336 -0.79708)
           (cons 40 0)
           (cons 41 0)
           (cons 42 0)
           (cons 91 0)
           (list 10 14.632664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.4762 -1.2474728)
           (cons 40 0)
           (cons 41 0)
           (cons 42 0)
           (cons 91 0)
           (list 10 14.4762 -1.0731272)
           (cons 40 0)
           (cons 41 0)
           (cons 42 0)
           (cons 91 0)
           (list 10 14.632664 -1.0206)
           (cons 40 0)
           (cons 41 0)
           (cons 42 0)
           (cons 91 0)
           (list 10 15.437336 -1.0206)
           (cons 40 0)
           (cons 41 0)
           (cons 42 0)
           (cons 91 0)
           (list 10 15.5938 -1.0731272)
           (cons 40 0)
           (cons 41 0)
           (cons 42 0)
           (cons 91 0)
           (list 10 15.5938 -1.2474728)
           (cons 40 0)
           (cons 41 0)
           (cons 42 0)
           (cons 91 0)
           (list 10 15.437336 -1.3)
           (cons 40 0)
           (cons 41 0)
           (cons 42 0)
           (cons 91 0)
           (list 10 14.632664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.4762 0.5702072)
           (cons 40 0)
           (cons 41 0)
           (cons 42 0)
           (cons 91 0)
           (list 10 14.4762 0.7445528)
           (cons 40 0)
           (cons 41 0)
           (cons 42 0)
           (cons 91 0)
           (list 10 14.632664 0.79708)
           (cons 40 0)
           (cons 41 0)
           (cons 42 0)
           (cons 91 0)
           (list 10 15.437336 0.79708)
           (cons 40 0)
           (cons 41 0)
           (cons 42 0)
           (cons 91 0)
           (list 10 15.5938 0.7445528)
           (cons 40 0)
           (cons 41 0)
           (cons 42 0)
           (cons 91 0)
           (list 10 15.5938 0.5702072)
           (cons 40 0)
           (cons 41 0)
           (cons 42 0)
           (cons 91 0)
           (list 10 15.437336 0.51768)
           (cons 40 0)
           (cons 41 0)
           (cons 42 0)
           (cons 91 0)
           (list 10 14.632664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.4762 1.0731272)
           (cons 40 0)
           (cons 41 0)
           (cons 42 0)
           (cons 91 0)
           (list 10 14.4762 1.2474728)
           (cons 40 0)
           (cons 41 0)
           (cons 42 0)
           (cons 91 0)
           (list 10 14.632664 1.3)
           (cons 40 0)
           (cons 41 0)
           (cons 42 0)
           (cons 91 0)
           (list 10 15.437336 1.3)
           (cons 40 0)
           (cons 41 0)
           (cons 42 0)
           (cons 91 0)
           (list 10 15.5938 1.2474728)
           (cons 40 0)
           (cons 41 0)
           (cons 42 0)
           (cons 91 0)
           (list 10 15.5938 1.0731272)
           (cons 40 0)
           (cons 41 0)
           (cons 42 0)
           (cons 91 0)
           (list 10 15.437336 1.0206)
           (cons 40 0)
           (cons 41 0)
           (cons 42 0)
           (cons 91 0)
           (list 10 14.632664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 1.9 0 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 16.2 1.3 0)
           (cons 50 0)
          )
         )
         (entmake
          (list
           (cons 0 "POINT")
           (cons 100 "AcDbEntity")
           (cons 67 0)
           (cons 8 "0")
           (cons 100 "AcDbPoint")
           (list 10 16.2 0 0)
           (cons 50 0)
          )
         )
         (entmake
          (list
           (cons 0 "POINT")
           (cons 100 "AcDbEntity")
           (cons 67 0)
           (cons 8 "0")
           (cons 100 "AcDbPoint")
           (list 10 16.2 -1.3 0)
           (cons 50 0)
          )
         )
         (entmake
          (list
           (cons 0 "POINT")
           (cons 100 "AcDbEntity")
           (cons 67 0)
           (cons 8 "0")
           (cons 100 "AcDbPoint")
           (list 10 14.4 1.3 0)
           (cons 50 0)
          )
         )
         (entmake
          (list
           (cons 0 "POINT")
           (cons 100 "AcDbEntity")
           (cons 67 0)
           (cons 8 "0")
           (cons 100 "AcDbPoint")
           (list 10 14.4 -1.3 0)
           (cons 50 0)
          )
         )
         (entmake
          (list
           (cons 0 "ATTDEF")
           (cons 100 "AcDbEntity")
           (cons 67 0)
           (cons 8 "0")
           (cons 100 "AcDbText")
           (list 10 1.2 0.56666667 0)
           (cons 40 0.2)
           (cons 1 "1.900")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.2 0.23333333 0)
           (cons 40 0.2)
           (cons 1 "1.900")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.2 -0.1 0)
           (cons 40 0.2)
           (cons 1 "14.400")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.2 -0.43333333 0)
           (cons 40 0.2)
           (cons 1 "16.200")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.2 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-36-TRUCK"))
        (progn
         (entmake)
         (entmake
          (list
           (cons 0 "BLOCK")
           (cons 2 "AB_INF-WB-36-TRUCK")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 -1.3)
           (cons 40 0)
           (cons 41 0)
           (cons 42 0)
           (cons 91 0)
           (list 10 6.435 -1.3)
           (cons 40 0)
           (cons 41 0)
           (cons 42 0)
           (cons 91 0)
           (list 10 6.435 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.435 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.435 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 5.8 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 6.06263966 -0.26263966 0)
           (list 11 6.06263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.6062 -0.7445528)
           (cons 40 0)
           (cons 41 0)
           (cons 42 0)
           (cons 91 0)
           (list 10 4.6062 -0.5702072)
           (cons 40 0)
           (cons 41 0)
           (cons 42 0)
           (cons 91 0)
           (list 10 4.762664 -0.51768)
           (cons 40 0)
           (cons 41 0)
           (cons 42 0)
           (cons 91 0)
           (list 10 5.567336 -0.51768)
           (cons 40 0)
           (cons 41 0)
           (cons 42 0)
           (cons 91 0)
           (list 10 5.7238 -0.5702072)
           (cons 40 0)
           (cons 41 0)
           (cons 42 0)
           (cons 91 0)
           (list 10 5.7238 -0.7445528)
           (cons 40 0)
           (cons 41 0)
           (cons 42 0)
           (cons 91 0)
           (list 10 5.567336 -0.79708)
           (cons 40 0)
           (cons 41 0)
           (cons 42 0)
           (cons 91 0)
           (list 10 4.762664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.6062 -1.2474728)
           (cons 40 0)
           (cons 41 0)
           (cons 42 0)
           (cons 91 0)
           (list 10 4.6062 -1.0731272)
           (cons 40 0)
           (cons 41 0)
           (cons 42 0)
           (cons 91 0)
           (list 10 4.762664 -1.0206)
           (cons 40 0)
           (cons 41 0)
           (cons 42 0)
           (cons 91 0)
           (list 10 5.567336 -1.0206)
           (cons 40 0)
           (cons 41 0)
           (cons 42 0)
           (cons 91 0)
           (list 10 5.7238 -1.0731272)
           (cons 40 0)
           (cons 41 0)
           (cons 42 0)
           (cons 91 0)
           (list 10 5.7238 -1.2474728)
           (cons 40 0)
           (cons 41 0)
           (cons 42 0)
           (cons 91 0)
           (list 10 5.567336 -1.3)
           (cons 40 0)
           (cons 41 0)
           (cons 42 0)
           (cons 91 0)
           (list 10 4.762664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.6062 0.5702072)
           (cons 40 0)
           (cons 41 0)
           (cons 42 0)
           (cons 91 0)
           (list 10 4.6062 0.7445528)
           (cons 40 0)
           (cons 41 0)
           (cons 42 0)
           (cons 91 0)
           (list 10 4.762664 0.79708)
           (cons 40 0)
           (cons 41 0)
           (cons 42 0)
           (cons 91 0)
           (list 10 5.567336 0.79708)
           (cons 40 0)
           (cons 41 0)
           (cons 42 0)
           (cons 91 0)
           (list 10 5.7238 0.7445528)
           (cons 40 0)
           (cons 41 0)
           (cons 42 0)
           (cons 91 0)
           (list 10 5.7238 0.5702072)
           (cons 40 0)
           (cons 41 0)
           (cons 42 0)
           (cons 91 0)
           (list 10 5.567336 0.51768)
           (cons 40 0)
           (cons 41 0)
           (cons 42 0)
           (cons 91 0)
           (list 10 4.762664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.6062 1.0731272)
           (cons 40 0)
           (cons 41 0)
           (cons 42 0)
           (cons 91 0)
           (list 10 4.6062 1.2474728)
           (cons 40 0)
           (cons 41 0)
           (cons 42 0)
           (cons 91 0)
           (list 10 4.762664 1.3)
           (cons 40 0)
           (cons 41 0)
           (cons 42 0)
           (cons 91 0)
           (list 10 5.567336 1.3)
           (cons 40 0)
           (cons 41 0)
           (cons 42 0)
           (cons 91 0)
           (list 10 5.7238 1.2474728)
           (cons 40 0)
           (cons 41 0)
           (cons 42 0)
           (cons 91 0)
           (list 10 5.7238 1.0731272)
           (cons 40 0)
           (cons 41 0)
           (cons 42 0)
           (cons 91 0)
           (list 10 5.567336 1.0206)
           (cons 40 0)
           (cons 41 0)
           (cons 42 0)
           (cons 91 0)
           (list 10 4.762664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.8762 -0.7445528)
           (cons 40 0)
           (cons 41 0)
           (cons 42 0)
           (cons 91 0)
           (list 10 5.8762 -0.5702072)
           (cons 40 0)
           (cons 41 0)
           (cons 42 0)
           (cons 91 0)
           (list 10 6.032664 -0.51768)
           (cons 40 0)
           (cons 41 0)
           (cons 42 0)
           (cons 91 0)
           (list 10 6.837336 -0.51768)
           (cons 40 0)
           (cons 41 0)
           (cons 42 0)
           (cons 91 0)
           (list 10 6.9938 -0.5702072)
           (cons 40 0)
           (cons 41 0)
           (cons 42 0)
           (cons 91 0)
           (list 10 6.9938 -0.7445528)
           (cons 40 0)
           (cons 41 0)
           (cons 42 0)
           (cons 91 0)
           (list 10 6.837336 -0.79708)
           (cons 40 0)
           (cons 41 0)
           (cons 42 0)
           (cons 91 0)
           (list 10 6.032664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.8762 -1.2474728)
           (cons 40 0)
           (cons 41 0)
           (cons 42 0)
           (cons 91 0)
           (list 10 5.8762 -1.0731272)
           (cons 40 0)
           (cons 41 0)
           (cons 42 0)
           (cons 91 0)
           (list 10 6.032664 -1.0206)
           (cons 40 0)
           (cons 41 0)
           (cons 42 0)
           (cons 91 0)
           (list 10 6.837336 -1.0206)
           (cons 40 0)
           (cons 41 0)
           (cons 42 0)
           (cons 91 0)
           (list 10 6.9938 -1.0731272)
           (cons 40 0)
           (cons 41 0)
           (cons 42 0)
           (cons 91 0)
           (list 10 6.9938 -1.2474728)
           (cons 40 0)
           (cons 41 0)
           (cons 42 0)
           (cons 91 0)
           (list 10 6.837336 -1.3)
           (cons 40 0)
           (cons 41 0)
           (cons 42 0)
           (cons 91 0)
           (list 10 6.032664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.8762 0.5702072)
           (cons 40 0)
           (cons 41 0)
           (cons 42 0)
           (cons 91 0)
           (list 10 5.8762 0.7445528)
           (cons 40 0)
           (cons 41 0)
           (cons 42 0)
           (cons 91 0)
           (list 10 6.032664 0.79708)
           (cons 40 0)
           (cons 41 0)
           (cons 42 0)
           (cons 91 0)
           (list 10 6.837336 0.79708)
           (cons 40 0)
           (cons 41 0)
           (cons 42 0)
           (cons 91 0)
           (list 10 6.9938 0.7445528)
           (cons 40 0)
           (cons 41 0)
           (cons 42 0)
           (cons 91 0)
           (list 10 6.9938 0.5702072)
           (cons 40 0)
           (cons 41 0)
           (cons 42 0)
           (cons 91 0)
           (list 10 6.837336 0.51768)
           (cons 40 0)
           (cons 41 0)
           (cons 42 0)
           (cons 91 0)
           (list 10 6.032664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.8762 1.0731272)
           (cons 40 0)
           (cons 41 0)
           (cons 42 0)
           (cons 91 0)
           (list 10 5.8762 1.2474728)
           (cons 40 0)
           (cons 41 0)
           (cons 42 0)
           (cons 91 0)
           (list 10 6.032664 1.3)
           (cons 40 0)
           (cons 41 0)
           (cons 42 0)
           (cons 91 0)
           (list 10 6.837336 1.3)
           (cons 40 0)
           (cons 41 0)
           (cons 42 0)
           (cons 91 0)
           (list 10 6.9938 1.2474728)
           (cons 40 0)
           (cons 41 0)
           (cons 42 0)
           (cons 91 0)
           (list 10 6.9938 1.0731272)
           (cons 40 0)
           (cons 41 0)
           (cons 42 0)
           (cons 91 0)
           (list 10 6.837336 1.0206)
           (cons 40 0)
           (cons 41 0)
           (cons 42 0)
           (cons 91 0)
           (list 10 6.032664 1.0206)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelRightM1")
           (list 10 0.7 1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM1")
           (list 10 0.7 -1.0206 0)
           (cons 41 1)
           (cons 42 1)
           (cons 43 1)
           (cons 50 0)
           (cons 70 0)
           (cons 71 0)
           (cons 44 0)
           (cons 45 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0.7 1.3 0)
           (cons 50 0)
          )
         )
         (entmake
          (list
           (cons 0 "POINT")
           (cons 100 "AcDbEntity")
           (cons 67 0)
           (cons 8 "0")
           (cons 100 "AcDbPoint")
           (list 10 0.7 -1.3 0)
           (cons 50 0)
          )
         )
         (entmake
          (list
           (cons 0 "POINT")
           (cons 100 "AcDbEntity")
           (cons 67 0)
           (cons 8 "0")
           (cons 100 "AcDbPoint")
           (list 10 0.7 0 0)
           (cons 50 0)
          )
         )
         (entmake
          (list
           (cons 0 "POINT")
           (cons 100 "AcDbEntity")
           (cons 67 0)
           (cons 8 "0")
           (cons 100 "AcDbPoint")
           (list 10 5.8 1.3 0)
           (cons 50 0)
          )
         )
         (entmake
          (list
           (cons 0 "POINT")
           (cons 100 "AcDbEntity")
           (cons 67 0)
           (cons 8 "0")
           (cons 100 "AcDbPoint")
           (list 10 5.8 0 0)
           (cons 50 0)
          )
         )
         (entmake
          (list
           (cons 0 "POINT")
           (cons 100 "AcDbEntity")
           (cons 67 0)
           (cons 8 "0")
           (cons 100 "AcDbPoint")
           (list 10 5.8 -1.3 0)
           (cons 50 0)
          )
         )
         (entmake
          (list
           (cons 0 "ATTDEF")
           (cons 100 "AcDbEntity")
           (cons 67 0)
           (cons 8 "0")
           (cons 100 "AcDbText")
           (list 10 0 0.56666667 0)
           (cons 40 0.2)
           (cons 1 "0.700")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0 0.23333333 0)
           (cons 40 0.2)
           (cons 1 "0.700")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0 -0.1 0)
           (cons 40 0.2)
           (cons 1 "5.800")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0 -0.43333333 0)
           (cons 40 0.2)
           (cons 1 "5.800")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0 -0.76666667 0)
           (cons 40 0.2)
           (cons 1 "17.19")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-33-TRAILER2"))
        (progn
         (entmake)
         (entmake
          (list
           (cons 0 "BLOCK")
           (cons 2 "AB_INF-WB-33-TRAILER2")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 8.6 -1.3)
           (cons 40 0)
           (cons 41 0)
           (cons 42 0)
           (cons 91 0)
           (list 10 8.6 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.6 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.6 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9062 -0.7445528)
           (cons 40 0)
           (cons 41 0)
           (cons 42 0)
           (cons 91 0)
           (list 10 5.9062 -0.5702072)
           (cons 40 0)
           (cons 41 0)
           (cons 42 0)
           (cons 91 0)
           (list 10 6.062664 -0.51768)
           (cons 40 0)
           (cons 41 0)
           (cons 42 0)
           (cons 91 0)
           (list 10 6.867336 -0.51768)
           (cons 40 0)
           (cons 41 0)
           (cons 42 0)
           (cons 91 0)
           (list 10 7.0238 -0.5702072)
           (cons 40 0)
           (cons 41 0)
           (cons 42 0)
           (cons 91 0)
           (list 10 7.0238 -0.7445528)
           (cons 40 0)
           (cons 41 0)
           (cons 42 0)
           (cons 91 0)
           (list 10 6.867336 -0.79708)
           (cons 40 0)
           (cons 41 0)
           (cons 42 0)
           (cons 91 0)
           (list 10 6.062664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9062 -1.2474728)
           (cons 40 0)
           (cons 41 0)
           (cons 42 0)
           (cons 91 0)
           (list 10 5.9062 -1.0731272)
           (cons 40 0)
           (cons 41 0)
           (cons 42 0)
           (cons 91 0)
           (list 10 6.062664 -1.0206)
           (cons 40 0)
           (cons 41 0)
           (cons 42 0)
           (cons 91 0)
           (list 10 6.867336 -1.0206)
           (cons 40 0)
           (cons 41 0)
           (cons 42 0)
           (cons 91 0)
           (list 10 7.0238 -1.0731272)
           (cons 40 0)
           (cons 41 0)
           (cons 42 0)
           (cons 91 0)
           (list 10 7.0238 -1.2474728)
           (cons 40 0)
           (cons 41 0)
           (cons 42 0)
           (cons 91 0)
           (list 10 6.867336 -1.3)
           (cons 40 0)
           (cons 41 0)
           (cons 42 0)
           (cons 91 0)
           (list 10 6.062664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9062 0.5702072)
           (cons 40 0)
           (cons 41 0)
           (cons 42 0)
           (cons 91 0)
           (list 10 5.9062 0.7445528)
           (cons 40 0)
           (cons 41 0)
           (cons 42 0)
           (cons 91 0)
           (list 10 6.062664 0.79708)
           (cons 40 0)
           (cons 41 0)
           (cons 42 0)
           (cons 91 0)
           (list 10 6.867336 0.79708)
           (cons 40 0)
           (cons 41 0)
           (cons 42 0)
           (cons 91 0)
           (list 10 7.0238 0.7445528)
           (cons 40 0)
           (cons 41 0)
           (cons 42 0)
           (cons 91 0)
           (list 10 7.0238 0.5702072)
           (cons 40 0)
           (cons 41 0)
           (cons 42 0)
           (cons 91 0)
           (list 10 6.867336 0.51768)
           (cons 40 0)
           (cons 41 0)
           (cons 42 0)
           (cons 91 0)
           (list 10 6.062664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9062 1.0731272)
           (cons 40 0)
           (cons 41 0)
           (cons 42 0)
           (cons 91 0)
           (list 10 5.9062 1.2474728)
           (cons 40 0)
           (cons 41 0)
           (cons 42 0)
           (cons 91 0)
           (list 10 6.062664 1.3)
           (cons 40 0)
           (cons 41 0)
           (cons 42 0)
           (cons 91 0)
           (list 10 6.867336 1.3)
           (cons 40 0)
           (cons 41 0)
           (cons 42 0)
           (cons 91 0)
           (list 10 7.0238 1.2474728)
           (cons 40 0)
           (cons 41 0)
           (cons 42 0)
           (cons 91 0)
           (list 10 7.0238 1.0731272)
           (cons 40 0)
           (cons 41 0)
           (cons 42 0)
           (cons 91 0)
           (list 10 6.867336 1.0206)
           (cons 40 0)
           (cons 41 0)
           (cons 42 0)
           (cons 91 0)
           (list 10 6.062664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1762 -0.7445528)
           (cons 40 0)
           (cons 41 0)
           (cons 42 0)
           (cons 91 0)
           (list 10 7.1762 -0.5702072)
           (cons 40 0)
           (cons 41 0)
           (cons 42 0)
           (cons 91 0)
           (list 10 7.332664 -0.51768)
           (cons 40 0)
           (cons 41 0)
           (cons 42 0)
           (cons 91 0)
           (list 10 8.137336 -0.51768)
           (cons 40 0)
           (cons 41 0)
           (cons 42 0)
           (cons 91 0)
           (list 10 8.2938 -0.5702072)
           (cons 40 0)
           (cons 41 0)
           (cons 42 0)
           (cons 91 0)
           (list 10 8.2938 -0.7445528)
           (cons 40 0)
           (cons 41 0)
           (cons 42 0)
           (cons 91 0)
           (list 10 8.137336 -0.79708)
           (cons 40 0)
           (cons 41 0)
           (cons 42 0)
           (cons 91 0)
           (list 10 7.332664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1762 -1.2474728)
           (cons 40 0)
           (cons 41 0)
           (cons 42 0)
           (cons 91 0)
           (list 10 7.1762 -1.0731272)
           (cons 40 0)
           (cons 41 0)
           (cons 42 0)
           (cons 91 0)
           (list 10 7.332664 -1.0206)
           (cons 40 0)
           (cons 41 0)
           (cons 42 0)
           (cons 91 0)
           (list 10 8.137336 -1.0206)
           (cons 40 0)
           (cons 41 0)
           (cons 42 0)
           (cons 91 0)
           (list 10 8.2938 -1.0731272)
           (cons 40 0)
           (cons 41 0)
           (cons 42 0)
           (cons 91 0)
           (list 10 8.2938 -1.2474728)
           (cons 40 0)
           (cons 41 0)
           (cons 42 0)
           (cons 91 0)
           (list 10 8.137336 -1.3)
           (cons 40 0)
           (cons 41 0)
           (cons 42 0)
           (cons 91 0)
           (list 10 7.332664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1762 0.5702072)
           (cons 40 0)
           (cons 41 0)
           (cons 42 0)
           (cons 91 0)
           (list 10 7.1762 0.7445528)
           (cons 40 0)
           (cons 41 0)
           (cons 42 0)
           (cons 91 0)
           (list 10 7.332664 0.79708)
           (cons 40 0)
           (cons 41 0)
           (cons 42 0)
           (cons 91 0)
           (list 10 8.137336 0.79708)
           (cons 40 0)
           (cons 41 0)
           (cons 42 0)
           (cons 91 0)
           (list 10 8.2938 0.7445528)
           (cons 40 0)
           (cons 41 0)
           (cons 42 0)
           (cons 91 0)
           (list 10 8.2938 0.5702072)
           (cons 40 0)
           (cons 41 0)
           (cons 42 0)
           (cons 91 0)
           (list 10 8.137336 0.51768)
           (cons 40 0)
           (cons 41 0)
           (cons 42 0)
           (cons 91 0)
           (list 10 7.332664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1762 1.0731272)
           (cons 40 0)
           (cons 41 0)
           (cons 42 0)
           (cons 91 0)
           (list 10 7.1762 1.2474728)
           (cons 40 0)
           (cons 41 0)
           (cons 42 0)
           (cons 91 0)
           (list 10 7.332664 1.3)
           (cons 40 0)
           (cons 41 0)
           (cons 42 0)
           (cons 91 0)
           (list 10 8.137336 1.3)
           (cons 40 0)
           (cons 41 0)
           (cons 42 0)
           (cons 91 0)
           (list 10 8.2938 1.2474728)
           (cons 40 0)
           (cons 41 0)
           (cons 42 0)
           (cons 91 0)
           (list 10 8.2938 1.0731272)
           (cons 40 0)
           (cons 41 0)
           (cons 42 0)
           (cons 91 0)
           (list 10 8.137336 1.0206)
           (cons 40 0)
           (cons 41 0)
           (cons 42 0)
           (cons 91 0)
           (list 10 7.332664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0.6 0 0)
           (cons 50 0)
          )
         )
         (entmake
          (list
           (cons 0 "POINT")
           (cons 100 "AcDbEntity")
           (cons 67 0)
           (cons 8 "0")
           (cons 100 "AcDbPoint")
           (list 10 8.6 1.3 0)
           (cons 50 0)
          )
         )
         (entmake
          (list
           (cons 0 "POINT")
           (cons 100 "AcDbEntity")
           (cons 67 0)
           (cons 8 "0")
           (cons 100 "AcDbPoint")
           (list 10 8.6 -1.3 0)
           (cons 50 0)
          )
         )
         (entmake
          (list
           (cons 0 "POINT")
           (cons 100 "AcDbEntity")
           (cons 67 0)
           (cons 8 "0")
           (cons 100 "AcDbPoint")
           (list 10 7.1 1.3 0)
           (cons 50 0)
          )
         )
         (entmake
          (list
           (cons 0 "POINT")
           (cons 100 "AcDbEntity")
           (cons 67 0)
           (cons 8 "0")
           (cons 100 "AcDbPoint")
           (list 10 7.1 -1.3 0)
           (cons 50 0)
          )
         )
         (entmake
          (list
           (cons 0 "ATTDEF")
           (cons 100 "AcDbEntity")
           (cons 67 0)
           (cons 8 "0")
           (cons 100 "AcDbText")
           (list 10 -0.1 0.56666667 0)
           (cons 40 0.2)
           (cons 1 "0.600")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 0.23333333 0)
           (cons 40 0.2)
           (cons 1 "0.600")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 -0.1 0)
           (cons 40 0.2)
           (cons 1 "7.100")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-33-PUP"))
        (progn
         (entmake)
         (entmake
          (list
           (cons 0 "BLOCK")
           (cons 2 "AB_INF-WB-33-PUP")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 3)
           (cons 70 129)
           (cons 43 0)
           (cons 38 0)
           (cons 39 0)
           (list 10 0 0)
           (cons 40 0)
           (cons 41 0)
           (cons 42 0)
           (cons 91 0)
           (list 10 2.1 1.3)
           (cons 40 0)
           (cons 41 0)
           (cons 42 0)
           (cons 91 0)
           (list 10 2.1 -1.3)
           (cons 40 0)
           (cons 41 0)
           (cons 42 0)
           (cons 91 0)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 2.1 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 -0.7445528)
           (cons 40 0)
           (cons 41 0)
           (cons 42 0)
           (cons 91 0)
           (list 10 1.5412 -0.5702072)
           (cons 40 0)
           (cons 41 0)
           (cons 42 0)
           (cons 91 0)
           (list 10 1.697664 -0.51768)
           (cons 40 0)
           (cons 41 0)
           (cons 42 0)
           (cons 91 0)
           (list 10 2.502336 -0.51768)
           (cons 40 0)
           (cons 41 0)
           (cons 42 0)
           (cons 91 0)
           (list 10 2.6588 -0.5702072)
           (cons 40 0)
           (cons 41 0)
           (cons 42 0)
           (cons 91 0)
           (list 10 2.6588 -0.7445528)
           (cons 40 0)
           (cons 41 0)
           (cons 42 0)
           (cons 91 0)
           (list 10 2.502336 -0.79708)
           (cons 40 0)
           (cons 41 0)
           (cons 42 0)
           (cons 91 0)
           (list 10 1.697664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 -1.2474728)
           (cons 40 0)
           (cons 41 0)
           (cons 42 0)
           (cons 91 0)
           (list 10 1.5412 -1.0731272)
           (cons 40 0)
           (cons 41 0)
           (cons 42 0)
           (cons 91 0)
           (list 10 1.697664 -1.0206)
           (cons 40 0)
           (cons 41 0)
           (cons 42 0)
           (cons 91 0)
           (list 10 2.502336 -1.0206)
           (cons 40 0)
           (cons 41 0)
           (cons 42 0)
           (cons 91 0)
           (list 10 2.6588 -1.0731272)
           (cons 40 0)
           (cons 41 0)
           (cons 42 0)
           (cons 91 0)
           (list 10 2.6588 -1.2474728)
           (cons 40 0)
           (cons 41 0)
           (cons 42 0)
           (cons 91 0)
           (list 10 2.502336 -1.3)
           (cons 40 0)
           (cons 41 0)
           (cons 42 0)
           (cons 91 0)
           (list 10 1.697664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 0.5702072)
           (cons 40 0)
           (cons 41 0)
           (cons 42 0)
           (cons 91 0)
           (list 10 1.5412 0.7445528)
           (cons 40 0)
           (cons 41 0)
           (cons 42 0)
           (cons 91 0)
           (list 10 1.697664 0.79708)
           (cons 40 0)
           (cons 41 0)
           (cons 42 0)
           (cons 91 0)
           (list 10 2.502336 0.79708)
           (cons 40 0)
           (cons 41 0)
           (cons 42 0)
           (cons 91 0)
           (list 10 2.6588 0.7445528)
           (cons 40 0)
           (cons 41 0)
           (cons 42 0)
           (cons 91 0)
           (list 10 2.6588 0.5702072)
           (cons 40 0)
           (cons 41 0)
           (cons 42 0)
           (cons 91 0)
           (list 10 2.502336 0.51768)
           (cons 40 0)
           (cons 41 0)
           (cons 42 0)
           (cons 91 0)
           (list 10 1.697664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 1.0731272)
           (cons 40 0)
           (cons 41 0)
           (cons 42 0)
           (cons 91 0)
           (list 10 1.5412 1.2474728)
           (cons 40 0)
           (cons 41 0)
           (cons 42 0)
           (cons 91 0)
           (list 10 1.697664 1.3)
           (cons 40 0)
           (cons 41 0)
           (cons 42 0)
           (cons 91 0)
           (list 10 2.502336 1.3)
           (cons 40 0)
           (cons 41 0)
           (cons 42 0)
           (cons 91 0)
           (list 10 2.6588 1.2474728)
           (cons 40 0)
           (cons 41 0)
           (cons 42 0)
           (cons 91 0)
           (list 10 2.6588 1.0731272)
           (cons 40 0)
           (cons 41 0)
           (cons 42 0)
           (cons 91 0)
           (list 10 2.502336 1.0206)
           (cons 40 0)
           (cons 41 0)
           (cons 42 0)
           (cons 91 0)
           (list 10 1.697664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 2.1 1.3 0)
           (cons 50 0)
          )
         )
         (entmake
          (list
           (cons 0 "POINT")
           (cons 100 "AcDbEntity")
           (cons 67 0)
           (cons 8 "0")
           (cons 100 "AcDbPoint")
           (list 10 2.1 -1.3 0)
           (cons 50 0)
          )
         )
         (entmake
          (list
           (cons 0 "POINT")
           (cons 100 "AcDbEntity")
           (cons 67 0)
           (cons 8 "0")
           (cons 100 "AcDbPoint")
           (list 10 2.1 0 0)
           (cons 50 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "2.100")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "2.100")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-33-TRAILER1"))
        (progn
         (entmake)
         (entmake
          (list
           (cons 0 "BLOCK")
           (cons 2 "AB_INF-WB-33-TRAILER1")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 8.6 -1.3)
           (cons 40 0)
           (cons 41 0)
           (cons 42 0)
           (cons 91 0)
           (list 10 8.6 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.6 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.6 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9062 -0.7445528)
           (cons 40 0)
           (cons 41 0)
           (cons 42 0)
           (cons 91 0)
           (list 10 5.9062 -0.5702072)
           (cons 40 0)
           (cons 41 0)
           (cons 42 0)
           (cons 91 0)
           (list 10 6.062664 -0.51768)
           (cons 40 0)
           (cons 41 0)
           (cons 42 0)
           (cons 91 0)
           (list 10 6.867336 -0.51768)
           (cons 40 0)
           (cons 41 0)
           (cons 42 0)
           (cons 91 0)
           (list 10 7.0238 -0.5702072)
           (cons 40 0)
           (cons 41 0)
           (cons 42 0)
           (cons 91 0)
           (list 10 7.0238 -0.7445528)
           (cons 40 0)
           (cons 41 0)
           (cons 42 0)
           (cons 91 0)
           (list 10 6.867336 -0.79708)
           (cons 40 0)
           (cons 41 0)
           (cons 42 0)
           (cons 91 0)
           (list 10 6.062664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9062 -1.2474728)
           (cons 40 0)
           (cons 41 0)
           (cons 42 0)
           (cons 91 0)
           (list 10 5.9062 -1.0731272)
           (cons 40 0)
           (cons 41 0)
           (cons 42 0)
           (cons 91 0)
           (list 10 6.062664 -1.0206)
           (cons 40 0)
           (cons 41 0)
           (cons 42 0)
           (cons 91 0)
           (list 10 6.867336 -1.0206)
           (cons 40 0)
           (cons 41 0)
           (cons 42 0)
           (cons 91 0)
           (list 10 7.0238 -1.0731272)
           (cons 40 0)
           (cons 41 0)
           (cons 42 0)
           (cons 91 0)
           (list 10 7.0238 -1.2474728)
           (cons 40 0)
           (cons 41 0)
           (cons 42 0)
           (cons 91 0)
           (list 10 6.867336 -1.3)
           (cons 40 0)
           (cons 41 0)
           (cons 42 0)
           (cons 91 0)
           (list 10 6.062664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9062 0.5702072)
           (cons 40 0)
           (cons 41 0)
           (cons 42 0)
           (cons 91 0)
           (list 10 5.9062 0.7445528)
           (cons 40 0)
           (cons 41 0)
           (cons 42 0)
           (cons 91 0)
           (list 10 6.062664 0.79708)
           (cons 40 0)
           (cons 41 0)
           (cons 42 0)
           (cons 91 0)
           (list 10 6.867336 0.79708)
           (cons 40 0)
           (cons 41 0)
           (cons 42 0)
           (cons 91 0)
           (list 10 7.0238 0.7445528)
           (cons 40 0)
           (cons 41 0)
           (cons 42 0)
           (cons 91 0)
           (list 10 7.0238 0.5702072)
           (cons 40 0)
           (cons 41 0)
           (cons 42 0)
           (cons 91 0)
           (list 10 6.867336 0.51768)
           (cons 40 0)
           (cons 41 0)
           (cons 42 0)
           (cons 91 0)
           (list 10 6.062664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9062 1.0731272)
           (cons 40 0)
           (cons 41 0)
           (cons 42 0)
           (cons 91 0)
           (list 10 5.9062 1.2474728)
           (cons 40 0)
           (cons 41 0)
           (cons 42 0)
           (cons 91 0)
           (list 10 6.062664 1.3)
           (cons 40 0)
           (cons 41 0)
           (cons 42 0)
           (cons 91 0)
           (list 10 6.867336 1.3)
           (cons 40 0)
           (cons 41 0)
           (cons 42 0)
           (cons 91 0)
           (list 10 7.0238 1.2474728)
           (cons 40 0)
           (cons 41 0)
           (cons 42 0)
           (cons 91 0)
           (list 10 7.0238 1.0731272)
           (cons 40 0)
           (cons 41 0)
           (cons 42 0)
           (cons 91 0)
           (list 10 6.867336 1.0206)
           (cons 40 0)
           (cons 41 0)
           (cons 42 0)
           (cons 91 0)
           (list 10 6.062664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1762 -0.7445528)
           (cons 40 0)
           (cons 41 0)
           (cons 42 0)
           (cons 91 0)
           (list 10 7.1762 -0.5702072)
           (cons 40 0)
           (cons 41 0)
           (cons 42 0)
           (cons 91 0)
           (list 10 7.332664 -0.51768)
           (cons 40 0)
           (cons 41 0)
           (cons 42 0)
           (cons 91 0)
           (list 10 8.137336 -0.51768)
           (cons 40 0)
           (cons 41 0)
           (cons 42 0)
           (cons 91 0)
           (list 10 8.2938 -0.5702072)
           (cons 40 0)
           (cons 41 0)
           (cons 42 0)
           (cons 91 0)
           (list 10 8.2938 -0.7445528)
           (cons 40 0)
           (cons 41 0)
           (cons 42 0)
           (cons 91 0)
           (list 10 8.137336 -0.79708)
           (cons 40 0)
           (cons 41 0)
           (cons 42 0)
           (cons 91 0)
           (list 10 7.332664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1762 -1.2474728)
           (cons 40 0)
           (cons 41 0)
           (cons 42 0)
           (cons 91 0)
           (list 10 7.1762 -1.0731272)
           (cons 40 0)
           (cons 41 0)
           (cons 42 0)
           (cons 91 0)
           (list 10 7.332664 -1.0206)
           (cons 40 0)
           (cons 41 0)
           (cons 42 0)
           (cons 91 0)
           (list 10 8.137336 -1.0206)
           (cons 40 0)
           (cons 41 0)
           (cons 42 0)
           (cons 91 0)
           (list 10 8.2938 -1.0731272)
           (cons 40 0)
           (cons 41 0)
           (cons 42 0)
           (cons 91 0)
           (list 10 8.2938 -1.2474728)
           (cons 40 0)
           (cons 41 0)
           (cons 42 0)
           (cons 91 0)
           (list 10 8.137336 -1.3)
           (cons 40 0)
           (cons 41 0)
           (cons 42 0)
           (cons 91 0)
           (list 10 7.332664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1762 0.5702072)
           (cons 40 0)
           (cons 41 0)
           (cons 42 0)
           (cons 91 0)
           (list 10 7.1762 0.7445528)
           (cons 40 0)
           (cons 41 0)
           (cons 42 0)
           (cons 91 0)
           (list 10 7.332664 0.79708)
           (cons 40 0)
           (cons 41 0)
           (cons 42 0)
           (cons 91 0)
           (list 10 8.137336 0.79708)
           (cons 40 0)
           (cons 41 0)
           (cons 42 0)
           (cons 91 0)
           (list 10 8.2938 0.7445528)
           (cons 40 0)
           (cons 41 0)
           (cons 42 0)
           (cons 91 0)
           (list 10 8.2938 0.5702072)
           (cons 40 0)
           (cons 41 0)
           (cons 42 0)
           (cons 91 0)
           (list 10 8.137336 0.51768)
           (cons 40 0)
           (cons 41 0)
           (cons 42 0)
           (cons 91 0)
           (list 10 7.332664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1762 1.0731272)
           (cons 40 0)
           (cons 41 0)
           (cons 42 0)
           (cons 91 0)
           (list 10 7.1762 1.2474728)
           (cons 40 0)
           (cons 41 0)
           (cons 42 0)
           (cons 91 0)
           (list 10 7.332664 1.3)
           (cons 40 0)
           (cons 41 0)
           (cons 42 0)
           (cons 91 0)
           (list 10 8.137336 1.3)
           (cons 40 0)
           (cons 41 0)
           (cons 42 0)
           (cons 91 0)
           (list 10 8.2938 1.2474728)
           (cons 40 0)
           (cons 41 0)
           (cons 42 0)
           (cons 91 0)
           (list 10 8.2938 1.0731272)
           (cons 40 0)
           (cons 41 0)
           (cons 42 0)
           (cons 91 0)
           (list 10 8.137336 1.0206)
           (cons 40 0)
           (cons 41 0)
           (cons 42 0)
           (cons 91 0)
           (list 10 7.332664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0.6 0 0)
           (cons 50 0)
          )
         )
         (entmake
          (list
           (cons 0 "POINT")
           (cons 100 "AcDbEntity")
           (cons 67 0)
           (cons 8 "0")
           (cons 100 "AcDbPoint")
           (list 10 8.6 1.3 0)
           (cons 50 0)
          )
         )
         (entmake
          (list
           (cons 0 "POINT")
           (cons 100 "AcDbEntity")
           (cons 67 0)
           (cons 8 "0")
           (cons 100 "AcDbPoint")
           (list 10 8.6 -1.3 0)
           (cons 50 0)
          )
         )
         (entmake
          (list
           (cons 0 "POINT")
           (cons 100 "AcDbEntity")
           (cons 67 0)
           (cons 8 "0")
           (cons 100 "AcDbPoint")
           (list 10 7.1 1.3 0)
           (cons 50 0)
          )
         )
         (entmake
          (list
           (cons 0 "POINT")
           (cons 100 "AcDbEntity")
           (cons 67 0)
           (cons 8 "0")
           (cons 100 "AcDbPoint")
           (list 10 7.1 -1.3 0)
           (cons 50 0)
          )
         )
         (entmake
          (list
           (cons 0 "POINT")
           (cons 100 "AcDbEntity")
           (cons 67 0)
           (cons 8 "0")
           (cons 100 "AcDbPoint")
           (list 10 8.6 0 0)
           (cons 50 0)
          )
         )
         (entmake
          (list
           (cons 0 "ATTDEF")
           (cons 100 "AcDbEntity")
           (cons 67 0)
           (cons 8 "0")
           (cons 100 "AcDbText")
           (list 10 -0.1 0.56666667 0)
           (cons 40 0.2)
           (cons 1 "0.600")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 0.23333333 0)
           (cons 40 0.2)
           (cons 1 "0.600")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 -0.1 0)
           (cons 40 0.2)
           (cons 1 "7.100")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 -0.43333333 0)
           (cons 40 0.2)
           (cons 1 "8.600")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-33-PUP"))
        (progn
         (entmake)
         (entmake
          (list
           (cons 0 "BLOCK")
           (cons 2 "AB_INF-WB-33-PUP")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 3)
           (cons 70 129)
           (cons 43 0)
           (cons 38 0)
           (cons 39 0)
           (list 10 0 0)
           (cons 40 0)
           (cons 41 0)
           (cons 42 0)
           (cons 91 0)
           (list 10 2.1 1.3)
           (cons 40 0)
           (cons 41 0)
           (cons 42 0)
           (cons 91 0)
           (list 10 2.1 -1.3)
           (cons 40 0)
           (cons 41 0)
           (cons 42 0)
           (cons 91 0)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 2.1 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 -0.7445528)
           (cons 40 0)
           (cons 41 0)
           (cons 42 0)
           (cons 91 0)
           (list 10 1.5412 -0.5702072)
           (cons 40 0)
           (cons 41 0)
           (cons 42 0)
           (cons 91 0)
           (list 10 1.697664 -0.51768)
           (cons 40 0)
           (cons 41 0)
           (cons 42 0)
           (cons 91 0)
           (list 10 2.502336 -0.51768)
           (cons 40 0)
           (cons 41 0)
           (cons 42 0)
           (cons 91 0)
           (list 10 2.6588 -0.5702072)
           (cons 40 0)
           (cons 41 0)
           (cons 42 0)
           (cons 91 0)
           (list 10 2.6588 -0.7445528)
           (cons 40 0)
           (cons 41 0)
           (cons 42 0)
           (cons 91 0)
           (list 10 2.502336 -0.79708)
           (cons 40 0)
           (cons 41 0)
           (cons 42 0)
           (cons 91 0)
           (list 10 1.697664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 -1.2474728)
           (cons 40 0)
           (cons 41 0)
           (cons 42 0)
           (cons 91 0)
           (list 10 1.5412 -1.0731272)
           (cons 40 0)
           (cons 41 0)
           (cons 42 0)
           (cons 91 0)
           (list 10 1.697664 -1.0206)
           (cons 40 0)
           (cons 41 0)
           (cons 42 0)
           (cons 91 0)
           (list 10 2.502336 -1.0206)
           (cons 40 0)
           (cons 41 0)
           (cons 42 0)
           (cons 91 0)
           (list 10 2.6588 -1.0731272)
           (cons 40 0)
           (cons 41 0)
           (cons 42 0)
           (cons 91 0)
           (list 10 2.6588 -1.2474728)
           (cons 40 0)
           (cons 41 0)
           (cons 42 0)
           (cons 91 0)
           (list 10 2.502336 -1.3)
           (cons 40 0)
           (cons 41 0)
           (cons 42 0)
           (cons 91 0)
           (list 10 1.697664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 0.5702072)
           (cons 40 0)
           (cons 41 0)
           (cons 42 0)
           (cons 91 0)
           (list 10 1.5412 0.7445528)
           (cons 40 0)
           (cons 41 0)
           (cons 42 0)
           (cons 91 0)
           (list 10 1.697664 0.79708)
           (cons 40 0)
           (cons 41 0)
           (cons 42 0)
           (cons 91 0)
           (list 10 2.502336 0.79708)
           (cons 40 0)
           (cons 41 0)
           (cons 42 0)
           (cons 91 0)
           (list 10 2.6588 0.7445528)
           (cons 40 0)
           (cons 41 0)
           (cons 42 0)
           (cons 91 0)
           (list 10 2.6588 0.5702072)
           (cons 40 0)
           (cons 41 0)
           (cons 42 0)
           (cons 91 0)
           (list 10 2.502336 0.51768)
           (cons 40 0)
           (cons 41 0)
           (cons 42 0)
           (cons 91 0)
           (list 10 1.697664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 1.0731272)
           (cons 40 0)
           (cons 41 0)
           (cons 42 0)
           (cons 91 0)
           (list 10 1.5412 1.2474728)
           (cons 40 0)
           (cons 41 0)
           (cons 42 0)
           (cons 91 0)
           (list 10 1.697664 1.3)
           (cons 40 0)
           (cons 41 0)
           (cons 42 0)
           (cons 91 0)
           (list 10 2.502336 1.3)
           (cons 40 0)
           (cons 41 0)
           (cons 42 0)
           (cons 91 0)
           (list 10 2.6588 1.2474728)
           (cons 40 0)
           (cons 41 0)
           (cons 42 0)
           (cons 91 0)
           (list 10 2.6588 1.0731272)
           (cons 40 0)
           (cons 41 0)
           (cons 42 0)
           (cons 91 0)
           (list 10 2.502336 1.0206)
           (cons 40 0)
           (cons 41 0)
           (cons 42 0)
           (cons 91 0)
           (list 10 1.697664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 2.1 1.3 0)
           (cons 50 0)
          )
         )
         (entmake
          (list
           (cons 0 "POINT")
           (cons 100 "AcDbEntity")
           (cons 67 0)
           (cons 8 "0")
           (cons 100 "AcDbPoint")
           (list 10 2.1 -1.3 0)
           (cons 50 0)
          )
         )
         (entmake
          (list
           (cons 0 "POINT")
           (cons 100 "AcDbEntity")
           (cons 67 0)
           (cons 8 "0")
           (cons 100 "AcDbPoint")
           (list 10 2.1 0 0)
           (cons 50 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "2.100")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "2.100")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-33-TRAILER1"))
        (progn
         (entmake)
         (entmake
          (list
           (cons 0 "BLOCK")
           (cons 2 "AB_INF-WB-33-TRAILER1")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 8.6 -1.3)
           (cons 40 0)
           (cons 41 0)
           (cons 42 0)
           (cons 91 0)
           (list 10 8.6 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.6 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.6 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9062 -0.7445528)
           (cons 40 0)
           (cons 41 0)
           (cons 42 0)
           (cons 91 0)
           (list 10 5.9062 -0.5702072)
           (cons 40 0)
           (cons 41 0)
           (cons 42 0)
           (cons 91 0)
           (list 10 6.062664 -0.51768)
           (cons 40 0)
           (cons 41 0)
           (cons 42 0)
           (cons 91 0)
           (list 10 6.867336 -0.51768)
           (cons 40 0)
           (cons 41 0)
           (cons 42 0)
           (cons 91 0)
           (list 10 7.0238 -0.5702072)
           (cons 40 0)
           (cons 41 0)
           (cons 42 0)
           (cons 91 0)
           (list 10 7.0238 -0.7445528)
           (cons 40 0)
           (cons 41 0)
           (cons 42 0)
           (cons 91 0)
           (list 10 6.867336 -0.79708)
           (cons 40 0)
           (cons 41 0)
           (cons 42 0)
           (cons 91 0)
           (list 10 6.062664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9062 -1.2474728)
           (cons 40 0)
           (cons 41 0)
           (cons 42 0)
           (cons 91 0)
           (list 10 5.9062 -1.0731272)
           (cons 40 0)
           (cons 41 0)
           (cons 42 0)
           (cons 91 0)
           (list 10 6.062664 -1.0206)
           (cons 40 0)
           (cons 41 0)
           (cons 42 0)
           (cons 91 0)
           (list 10 6.867336 -1.0206)
           (cons 40 0)
           (cons 41 0)
           (cons 42 0)
           (cons 91 0)
           (list 10 7.0238 -1.0731272)
           (cons 40 0)
           (cons 41 0)
           (cons 42 0)
           (cons 91 0)
           (list 10 7.0238 -1.2474728)
           (cons 40 0)
           (cons 41 0)
           (cons 42 0)
           (cons 91 0)
           (list 10 6.867336 -1.3)
           (cons 40 0)
           (cons 41 0)
           (cons 42 0)
           (cons 91 0)
           (list 10 6.062664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9062 0.5702072)
           (cons 40 0)
           (cons 41 0)
           (cons 42 0)
           (cons 91 0)
           (list 10 5.9062 0.7445528)
           (cons 40 0)
           (cons 41 0)
           (cons 42 0)
           (cons 91 0)
           (list 10 6.062664 0.79708)
           (cons 40 0)
           (cons 41 0)
           (cons 42 0)
           (cons 91 0)
           (list 10 6.867336 0.79708)
           (cons 40 0)
           (cons 41 0)
           (cons 42 0)
           (cons 91 0)
           (list 10 7.0238 0.7445528)
           (cons 40 0)
           (cons 41 0)
           (cons 42 0)
           (cons 91 0)
           (list 10 7.0238 0.5702072)
           (cons 40 0)
           (cons 41 0)
           (cons 42 0)
           (cons 91 0)
           (list 10 6.867336 0.51768)
           (cons 40 0)
           (cons 41 0)
           (cons 42 0)
           (cons 91 0)
           (list 10 6.062664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9062 1.0731272)
           (cons 40 0)
           (cons 41 0)
           (cons 42 0)
           (cons 91 0)
           (list 10 5.9062 1.2474728)
           (cons 40 0)
           (cons 41 0)
           (cons 42 0)
           (cons 91 0)
           (list 10 6.062664 1.3)
           (cons 40 0)
           (cons 41 0)
           (cons 42 0)
           (cons 91 0)
           (list 10 6.867336 1.3)
           (cons 40 0)
           (cons 41 0)
           (cons 42 0)
           (cons 91 0)
           (list 10 7.0238 1.2474728)
           (cons 40 0)
           (cons 41 0)
           (cons 42 0)
           (cons 91 0)
           (list 10 7.0238 1.0731272)
           (cons 40 0)
           (cons 41 0)
           (cons 42 0)
           (cons 91 0)
           (list 10 6.867336 1.0206)
           (cons 40 0)
           (cons 41 0)
           (cons 42 0)
           (cons 91 0)
           (list 10 6.062664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1762 -0.7445528)
           (cons 40 0)
           (cons 41 0)
           (cons 42 0)
           (cons 91 0)
           (list 10 7.1762 -0.5702072)
           (cons 40 0)
           (cons 41 0)
           (cons 42 0)
           (cons 91 0)
           (list 10 7.332664 -0.51768)
           (cons 40 0)
           (cons 41 0)
           (cons 42 0)
           (cons 91 0)
           (list 10 8.137336 -0.51768)
           (cons 40 0)
           (cons 41 0)
           (cons 42 0)
           (cons 91 0)
           (list 10 8.2938 -0.5702072)
           (cons 40 0)
           (cons 41 0)
           (cons 42 0)
           (cons 91 0)
           (list 10 8.2938 -0.7445528)
           (cons 40 0)
           (cons 41 0)
           (cons 42 0)
           (cons 91 0)
           (list 10 8.137336 -0.79708)
           (cons 40 0)
           (cons 41 0)
           (cons 42 0)
           (cons 91 0)
           (list 10 7.332664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1762 -1.2474728)
           (cons 40 0)
           (cons 41 0)
           (cons 42 0)
           (cons 91 0)
           (list 10 7.1762 -1.0731272)
           (cons 40 0)
           (cons 41 0)
           (cons 42 0)
           (cons 91 0)
           (list 10 7.332664 -1.0206)
           (cons 40 0)
           (cons 41 0)
           (cons 42 0)
           (cons 91 0)
           (list 10 8.137336 -1.0206)
           (cons 40 0)
           (cons 41 0)
           (cons 42 0)
           (cons 91 0)
           (list 10 8.2938 -1.0731272)
           (cons 40 0)
           (cons 41 0)
           (cons 42 0)
           (cons 91 0)
           (list 10 8.2938 -1.2474728)
           (cons 40 0)
           (cons 41 0)
           (cons 42 0)
           (cons 91 0)
           (list 10 8.137336 -1.3)
           (cons 40 0)
           (cons 41 0)
           (cons 42 0)
           (cons 91 0)
           (list 10 7.332664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1762 0.5702072)
           (cons 40 0)
           (cons 41 0)
           (cons 42 0)
           (cons 91 0)
           (list 10 7.1762 0.7445528)
           (cons 40 0)
           (cons 41 0)
           (cons 42 0)
           (cons 91 0)
           (list 10 7.332664 0.79708)
           (cons 40 0)
           (cons 41 0)
           (cons 42 0)
           (cons 91 0)
           (list 10 8.137336 0.79708)
           (cons 40 0)
           (cons 41 0)
           (cons 42 0)
           (cons 91 0)
           (list 10 8.2938 0.7445528)
           (cons 40 0)
           (cons 41 0)
           (cons 42 0)
           (cons 91 0)
           (list 10 8.2938 0.5702072)
           (cons 40 0)
           (cons 41 0)
           (cons 42 0)
           (cons 91 0)
           (list 10 8.137336 0.51768)
           (cons 40 0)
           (cons 41 0)
           (cons 42 0)
           (cons 91 0)
           (list 10 7.332664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1762 1.0731272)
           (cons 40 0)
           (cons 41 0)
           (cons 42 0)
           (cons 91 0)
           (list 10 7.1762 1.2474728)
           (cons 40 0)
           (cons 41 0)
           (cons 42 0)
           (cons 91 0)
           (list 10 7.332664 1.3)
           (cons 40 0)
           (cons 41 0)
           (cons 42 0)
           (cons 91 0)
           (list 10 8.137336 1.3)
           (cons 40 0)
           (cons 41 0)
           (cons 42 0)
           (cons 91 0)
           (list 10 8.2938 1.2474728)
           (cons 40 0)
           (cons 41 0)
           (cons 42 0)
           (cons 91 0)
           (list 10 8.2938 1.0731272)
           (cons 40 0)
           (cons 41 0)
           (cons 42 0)
           (cons 91 0)
           (list 10 8.137336 1.0206)
           (cons 40 0)
           (cons 41 0)
           (cons 42 0)
           (cons 91 0)
           (list 10 7.332664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0.6 0 0)
           (cons 50 0)
          )
         )
         (entmake
          (list
           (cons 0 "POINT")
           (cons 100 "AcDbEntity")
           (cons 67 0)
           (cons 8 "0")
           (cons 100 "AcDbPoint")
           (list 10 8.6 1.3 0)
           (cons 50 0)
          )
         )
         (entmake
          (list
           (cons 0 "POINT")
           (cons 100 "AcDbEntity")
           (cons 67 0)
           (cons 8 "0")
           (cons 100 "AcDbPoint")
           (list 10 8.6 -1.3 0)
           (cons 50 0)
          )
         )
         (entmake
          (list
           (cons 0 "POINT")
           (cons 100 "AcDbEntity")
           (cons 67 0)
           (cons 8 "0")
           (cons 100 "AcDbPoint")
           (list 10 7.1 1.3 0)
           (cons 50 0)
          )
         )
         (entmake
          (list
           (cons 0 "POINT")
           (cons 100 "AcDbEntity")
           (cons 67 0)
           (cons 8 "0")
           (cons 100 "AcDbPoint")
           (list 10 7.1 -1.3 0)
           (cons 50 0)
          )
         )
         (entmake
          (list
           (cons 0 "POINT")
           (cons 100 "AcDbEntity")
           (cons 67 0)
           (cons 8 "0")
           (cons 100 "AcDbPoint")
           (list 10 8.6 0 0)
           (cons 50 0)
          )
         )
         (entmake
          (list
           (cons 0 "ATTDEF")
           (cons 100 "AcDbEntity")
           (cons 67 0)
           (cons 8 "0")
           (cons 100 "AcDbText")
           (list 10 -0.1 0.56666667 0)
           (cons 40 0.2)
           (cons 1 "0.600")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 0.23333333 0)
           (cons 40 0.2)
           (cons 1 "0.600")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 -0.1 0)
           (cons 40 0.2)
           (cons 1 "7.100")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 -0.43333333 0)
           (cons 40 0.2)
           (cons 1 "8.600")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-33-TRUCK"))
        (progn
         (entmake)
         (entmake
          (list
           (cons 0 "BLOCK")
           (cons 2 "AB_INF-WB-33-TRUCK")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 7.435 -1.3)
           (cons 40 0)
           (cons 41 0)
           (cons 42 0)
           (cons 91 0)
           (list 10 7.435 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.435 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.435 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 6.8 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 7.06263966 -0.26263966 0)
           (list 11 7.06263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.6062 -0.7445528)
           (cons 40 0)
           (cons 41 0)
           (cons 42 0)
           (cons 91 0)
           (list 10 5.6062 -0.5702072)
           (cons 40 0)
           (cons 41 0)
           (cons 42 0)
           (cons 91 0)
           (list 10 5.762664 -0.51768)
           (cons 40 0)
           (cons 41 0)
           (cons 42 0)
           (cons 91 0)
           (list 10 6.567336 -0.51768)
           (cons 40 0)
           (cons 41 0)
           (cons 42 0)
           (cons 91 0)
           (list 10 6.7238 -0.5702072)
           (cons 40 0)
           (cons 41 0)
           (cons 42 0)
           (cons 91 0)
           (list 10 6.7238 -0.7445528)
           (cons 40 0)
           (cons 41 0)
           (cons 42 0)
           (cons 91 0)
           (list 10 6.567336 -0.79708)
           (cons 40 0)
           (cons 41 0)
           (cons 42 0)
           (cons 91 0)
           (list 10 5.762664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.6062 -1.2474728)
           (cons 40 0)
           (cons 41 0)
           (cons 42 0)
           (cons 91 0)
           (list 10 5.6062 -1.0731272)
           (cons 40 0)
           (cons 41 0)
           (cons 42 0)
           (cons 91 0)
           (list 10 5.762664 -1.0206)
           (cons 40 0)
           (cons 41 0)
           (cons 42 0)
           (cons 91 0)
           (list 10 6.567336 -1.0206)
           (cons 40 0)
           (cons 41 0)
           (cons 42 0)
           (cons 91 0)
           (list 10 6.7238 -1.0731272)
           (cons 40 0)
           (cons 41 0)
           (cons 42 0)
           (cons 91 0)
           (list 10 6.7238 -1.2474728)
           (cons 40 0)
           (cons 41 0)
           (cons 42 0)
           (cons 91 0)
           (list 10 6.567336 -1.3)
           (cons 40 0)
           (cons 41 0)
           (cons 42 0)
           (cons 91 0)
           (list 10 5.762664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.6062 0.5702072)
           (cons 40 0)
           (cons 41 0)
           (cons 42 0)
           (cons 91 0)
           (list 10 5.6062 0.7445528)
           (cons 40 0)
           (cons 41 0)
           (cons 42 0)
           (cons 91 0)
           (list 10 5.762664 0.79708)
           (cons 40 0)
           (cons 41 0)
           (cons 42 0)
           (cons 91 0)
           (list 10 6.567336 0.79708)
           (cons 40 0)
           (cons 41 0)
           (cons 42 0)
           (cons 91 0)
           (list 10 6.7238 0.7445528)
           (cons 40 0)
           (cons 41 0)
           (cons 42 0)
           (cons 91 0)
           (list 10 6.7238 0.5702072)
           (cons 40 0)
           (cons 41 0)
           (cons 42 0)
           (cons 91 0)
           (list 10 6.567336 0.51768)
           (cons 40 0)
           (cons 41 0)
           (cons 42 0)
           (cons 91 0)
           (list 10 5.762664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.6062 1.0731272)
           (cons 40 0)
           (cons 41 0)
           (cons 42 0)
           (cons 91 0)
           (list 10 5.6062 1.2474728)
           (cons 40 0)
           (cons 41 0)
           (cons 42 0)
           (cons 91 0)
           (list 10 5.762664 1.3)
           (cons 40 0)
           (cons 41 0)
           (cons 42 0)
           (cons 91 0)
           (list 10 6.567336 1.3)
           (cons 40 0)
           (cons 41 0)
           (cons 42 0)
           (cons 91 0)
           (list 10 6.7238 1.2474728)
           (cons 40 0)
           (cons 41 0)
           (cons 42 0)
           (cons 91 0)
           (list 10 6.7238 1.0731272)
           (cons 40 0)
           (cons 41 0)
           (cons 42 0)
           (cons 91 0)
           (list 10 6.567336 1.0206)
           (cons 40 0)
           (cons 41 0)
           (cons 42 0)
           (cons 91 0)
           (list 10 5.762664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.8762 -0.7445528)
           (cons 40 0)
           (cons 41 0)
           (cons 42 0)
           (cons 91 0)
           (list 10 6.8762 -0.5702072)
           (cons 40 0)
           (cons 41 0)
           (cons 42 0)
           (cons 91 0)
           (list 10 7.032664 -0.51768)
           (cons 40 0)
           (cons 41 0)
           (cons 42 0)
           (cons 91 0)
           (list 10 7.837336 -0.51768)
           (cons 40 0)
           (cons 41 0)
           (cons 42 0)
           (cons 91 0)
           (list 10 7.9938 -0.5702072)
           (cons 40 0)
           (cons 41 0)
           (cons 42 0)
           (cons 91 0)
           (list 10 7.9938 -0.7445528)
           (cons 40 0)
           (cons 41 0)
           (cons 42 0)
           (cons 91 0)
           (list 10 7.837336 -0.79708)
           (cons 40 0)
           (cons 41 0)
           (cons 42 0)
           (cons 91 0)
           (list 10 7.032664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.8762 -1.2474728)
           (cons 40 0)
           (cons 41 0)
           (cons 42 0)
           (cons 91 0)
           (list 10 6.8762 -1.0731272)
           (cons 40 0)
           (cons 41 0)
           (cons 42 0)
           (cons 91 0)
           (list 10 7.032664 -1.0206)
           (cons 40 0)
           (cons 41 0)
           (cons 42 0)
           (cons 91 0)
           (list 10 7.837336 -1.0206)
           (cons 40 0)
           (cons 41 0)
           (cons 42 0)
           (cons 91 0)
           (list 10 7.9938 -1.0731272)
           (cons 40 0)
           (cons 41 0)
           (cons 42 0)
           (cons 91 0)
           (list 10 7.9938 -1.2474728)
           (cons 40 0)
           (cons 41 0)
           (cons 42 0)
           (cons 91 0)
           (list 10 7.837336 -1.3)
           (cons 40 0)
           (cons 41 0)
           (cons 42 0)
           (cons 91 0)
           (list 10 7.032664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.8762 0.5702072)
           (cons 40 0)
           (cons 41 0)
           (cons 42 0)
           (cons 91 0)
           (list 10 6.8762 0.7445528)
           (cons 40 0)
           (cons 41 0)
           (cons 42 0)
           (cons 91 0)
           (list 10 7.032664 0.79708)
           (cons 40 0)
           (cons 41 0)
           (cons 42 0)
           (cons 91 0)
           (list 10 7.837336 0.79708)
           (cons 40 0)
           (cons 41 0)
           (cons 42 0)
           (cons 91 0)
           (list 10 7.9938 0.7445528)
           (cons 40 0)
           (cons 41 0)
           (cons 42 0)
           (cons 91 0)
           (list 10 7.9938 0.5702072)
           (cons 40 0)
           (cons 41 0)
           (cons 42 0)
           (cons 91 0)
           (list 10 7.837336 0.51768)
           (cons 40 0)
           (cons 41 0)
           (cons 42 0)
           (cons 91 0)
           (list 10 7.032664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.8762 1.0731272)
           (cons 40 0)
           (cons 41 0)
           (cons 42 0)
           (cons 91 0)
           (list 10 6.8762 1.2474728)
           (cons 40 0)
           (cons 41 0)
           (cons 42 0)
           (cons 91 0)
           (list 10 7.032664 1.3)
           (cons 40 0)
           (cons 41 0)
           (cons 42 0)
           (cons 91 0)
           (list 10 7.837336 1.3)
           (cons 40 0)
           (cons 41 0)
           (cons 42 0)
           (cons 91 0)
           (list 10 7.9938 1.2474728)
           (cons 40 0)
           (cons 41 0)
           (cons 42 0)
           (cons 91 0)
           (list 10 7.9938 1.0731272)
           (cons 40 0)
           (cons 41 0)
           (cons 42 0)
           (cons 91 0)
           (list 10 7.837336 1.0206)
           (cons 40 0)
           (cons 41 0)
           (cons 42 0)
           (cons 91 0)
           (list 10 7.032664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0.7 0 0)
           (cons 50 0)
          )
         )
         (entmake
          (list
           (cons 0 "INSERT")
           (cons 100 "AcDbEntity")
           (cons 67 0)
           (cons 8 "0")
           (cons 100 "AcDbBlockReference")
           (cons 2 "WheelRightM1")
           (list 10 0.7 -1.3 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM1")
           (list 10 0.7 1.3 0)
           (cons 41 1)
           (cons 42 1)
           (cons 43 1)
           (cons 50 0)
           (cons 70 0)
           (cons 71 0)
           (cons 44 0)
           (cons 45 0)
          )
         )
         (entmake
          (list
           (cons 0 "POINT")
           (cons 100 "AcDbEntity")
           (cons 67 0)
           (cons 8 "0")
           (cons 100 "AcDbPoint")
           (list 10 6.8 1.3 0)
           (cons 50 0)
          )
         )
         (entmake
          (list
           (cons 0 "POINT")
           (cons 100 "AcDbEntity")
           (cons 67 0)
           (cons 8 "0")
           (cons 100 "AcDbPoint")
           (list 10 6.8 -1.3 0)
           (cons 50 0)
          )
         )
         (entmake
          (list
           (cons 0 "POINT")
           (cons 100 "AcDbEntity")
           (cons 67 0)
           (cons 8 "0")
           (cons 100 "AcDbPoint")
           (list 10 6.8 0 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0.7 -1.3 0)
           (cons 50 0)
          )
         )
         (entmake
          (list
           (cons 0 "POINT")
           (cons 100 "AcDbEntity")
           (cons 67 0)
           (cons 8 "0")
           (cons 100 "AcDbPoint")
           (list 10 0.7 1.3 0)
           (cons 50 0)
          )
         )
         (entmake
          (list
           (cons 0 "ATTDEF")
           (cons 100 "AcDbEntity")
           (cons 67 0)
           (cons 8 "0")
           (cons 100 "AcDbText")
           (list 10 0 0.56666667 0)
           (cons 40 0.2)
           (cons 1 "0.700")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0 0.23333333 0)
           (cons 40 0.2)
           (cons 1 "0.700")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0 -0.1 0)
           (cons 40 0.2)
           (cons 1 "6.800")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0 -0.43333333 0)
           (cons 40 0.2)
           (cons 1 "6.800")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0 -0.76666667 0)
           (cons 40 0.2)
           (cons 1 "25.22")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-28-TRAILER2"))
        (progn
         (entmake)
         (entmake
          (list
           (cons 0 "BLOCK")
           (cons 2 "AB_INF-WB-28-TRAILER2")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 -1.3)
           (cons 40 0)
           (cons 41 0)
           (cons 42 0)
           (cons 91 0)
           (list 10 8.5 -1.3)
           (cons 40 0)
           (cons 41 0)
           (cons 42 0)
           (cons 91 0)
           (list 10 8.5 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.5 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.5 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9062 -0.7445528)
           (cons 40 0)
           (cons 41 0)
           (cons 42 0)
           (cons 91 0)
           (list 10 5.9062 -0.5702072)
           (cons 40 0)
           (cons 41 0)
           (cons 42 0)
           (cons 91 0)
           (list 10 6.062664 -0.51768)
           (cons 40 0)
           (cons 41 0)
           (cons 42 0)
           (cons 91 0)
           (list 10 6.867336 -0.51768)
           (cons 40 0)
           (cons 41 0)
           (cons 42 0)
           (cons 91 0)
           (list 10 7.0238 -0.5702072)
           (cons 40 0)
           (cons 41 0)
           (cons 42 0)
           (cons 91 0)
           (list 10 7.0238 -0.7445528)
           (cons 40 0)
           (cons 41 0)
           (cons 42 0)
           (cons 91 0)
           (list 10 6.867336 -0.79708)
           (cons 40 0)
           (cons 41 0)
           (cons 42 0)
           (cons 91 0)
           (list 10 6.062664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9062 -1.2474728)
           (cons 40 0)
           (cons 41 0)
           (cons 42 0)
           (cons 91 0)
           (list 10 5.9062 -1.0731272)
           (cons 40 0)
           (cons 41 0)
           (cons 42 0)
           (cons 91 0)
           (list 10 6.062664 -1.0206)
           (cons 40 0)
           (cons 41 0)
           (cons 42 0)
           (cons 91 0)
           (list 10 6.867336 -1.0206)
           (cons 40 0)
           (cons 41 0)
           (cons 42 0)
           (cons 91 0)
           (list 10 7.0238 -1.0731272)
           (cons 40 0)
           (cons 41 0)
           (cons 42 0)
           (cons 91 0)
           (list 10 7.0238 -1.2474728)
           (cons 40 0)
           (cons 41 0)
           (cons 42 0)
           (cons 91 0)
           (list 10 6.867336 -1.3)
           (cons 40 0)
           (cons 41 0)
           (cons 42 0)
           (cons 91 0)
           (list 10 6.062664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9062 0.5702072)
           (cons 40 0)
           (cons 41 0)
           (cons 42 0)
           (cons 91 0)
           (list 10 5.9062 0.7445528)
           (cons 40 0)
           (cons 41 0)
           (cons 42 0)
           (cons 91 0)
           (list 10 6.062664 0.79708)
           (cons 40 0)
           (cons 41 0)
           (cons 42 0)
           (cons 91 0)
           (list 10 6.867336 0.79708)
           (cons 40 0)
           (cons 41 0)
           (cons 42 0)
           (cons 91 0)
           (list 10 7.0238 0.7445528)
           (cons 40 0)
           (cons 41 0)
           (cons 42 0)
           (cons 91 0)
           (list 10 7.0238 0.5702072)
           (cons 40 0)
           (cons 41 0)
           (cons 42 0)
           (cons 91 0)
           (list 10 6.867336 0.51768)
           (cons 40 0)
           (cons 41 0)
           (cons 42 0)
           (cons 91 0)
           (list 10 6.062664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9062 1.0731272)
           (cons 40 0)
           (cons 41 0)
           (cons 42 0)
           (cons 91 0)
           (list 10 5.9062 1.2474728)
           (cons 40 0)
           (cons 41 0)
           (cons 42 0)
           (cons 91 0)
           (list 10 6.062664 1.3)
           (cons 40 0)
           (cons 41 0)
           (cons 42 0)
           (cons 91 0)
           (list 10 6.867336 1.3)
           (cons 40 0)
           (cons 41 0)
           (cons 42 0)
           (cons 91 0)
           (list 10 7.0238 1.2474728)
           (cons 40 0)
           (cons 41 0)
           (cons 42 0)
           (cons 91 0)
           (list 10 7.0238 1.0731272)
           (cons 40 0)
           (cons 41 0)
           (cons 42 0)
           (cons 91 0)
           (list 10 6.867336 1.0206)
           (cons 40 0)
           (cons 41 0)
           (cons 42 0)
           (cons 91 0)
           (list 10 6.062664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1762 -0.7445528)
           (cons 40 0)
           (cons 41 0)
           (cons 42 0)
           (cons 91 0)
           (list 10 7.1762 -0.5702072)
           (cons 40 0)
           (cons 41 0)
           (cons 42 0)
           (cons 91 0)
           (list 10 7.332664 -0.51768)
           (cons 40 0)
           (cons 41 0)
           (cons 42 0)
           (cons 91 0)
           (list 10 8.137336 -0.51768)
           (cons 40 0)
           (cons 41 0)
           (cons 42 0)
           (cons 91 0)
           (list 10 8.2938 -0.5702072)
           (cons 40 0)
           (cons 41 0)
           (cons 42 0)
           (cons 91 0)
           (list 10 8.2938 -0.7445528)
           (cons 40 0)
           (cons 41 0)
           (cons 42 0)
           (cons 91 0)
           (list 10 8.137336 -0.79708)
           (cons 40 0)
           (cons 41 0)
           (cons 42 0)
           (cons 91 0)
           (list 10 7.332664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1762 -1.2474728)
           (cons 40 0)
           (cons 41 0)
           (cons 42 0)
           (cons 91 0)
           (list 10 7.1762 -1.0731272)
           (cons 40 0)
           (cons 41 0)
           (cons 42 0)
           (cons 91 0)
           (list 10 7.332664 -1.0206)
           (cons 40 0)
           (cons 41 0)
           (cons 42 0)
           (cons 91 0)
           (list 10 8.137336 -1.0206)
           (cons 40 0)
           (cons 41 0)
           (cons 42 0)
           (cons 91 0)
           (list 10 8.2938 -1.0731272)
           (cons 40 0)
           (cons 41 0)
           (cons 42 0)
           (cons 91 0)
           (list 10 8.2938 -1.2474728)
           (cons 40 0)
           (cons 41 0)
           (cons 42 0)
           (cons 91 0)
           (list 10 8.137336 -1.3)
           (cons 40 0)
           (cons 41 0)
           (cons 42 0)
           (cons 91 0)
           (list 10 7.332664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1762 0.5702072)
           (cons 40 0)
           (cons 41 0)
           (cons 42 0)
           (cons 91 0)
           (list 10 7.1762 0.7445528)
           (cons 40 0)
           (cons 41 0)
           (cons 42 0)
           (cons 91 0)
           (list 10 7.332664 0.79708)
           (cons 40 0)
           (cons 41 0)
           (cons 42 0)
           (cons 91 0)
           (list 10 8.137336 0.79708)
           (cons 40 0)
           (cons 41 0)
           (cons 42 0)
           (cons 91 0)
           (list 10 8.2938 0.7445528)
           (cons 40 0)
           (cons 41 0)
           (cons 42 0)
           (cons 91 0)
           (list 10 8.2938 0.5702072)
           (cons 40 0)
           (cons 41 0)
           (cons 42 0)
           (cons 91 0)
           (list 10 8.137336 0.51768)
           (cons 40 0)
           (cons 41 0)
           (cons 42 0)
           (cons 91 0)
           (list 10 7.332664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1762 1.0731272)
           (cons 40 0)
           (cons 41 0)
           (cons 42 0)
           (cons 91 0)
           (list 10 7.1762 1.2474728)
           (cons 40 0)
           (cons 41 0)
           (cons 42 0)
           (cons 91 0)
           (list 10 7.332664 1.3)
           (cons 40 0)
           (cons 41 0)
           (cons 42 0)
           (cons 91 0)
           (list 10 8.137336 1.3)
           (cons 40 0)
           (cons 41 0)
           (cons 42 0)
           (cons 91 0)
           (list 10 8.2938 1.2474728)
           (cons 40 0)
           (cons 41 0)
           (cons 42 0)
           (cons 91 0)
           (list 10 8.2938 1.0731272)
           (cons 40 0)
           (cons 41 0)
           (cons 42 0)
           (cons 91 0)
           (list 10 8.137336 1.0206)
           (cons 40 0)
           (cons 41 0)
           (cons 42 0)
           (cons 91 0)
           (list 10 7.332664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0.6 0 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 8.5 1.3 0)
           (cons 50 0)
          )
         )
         (entmake
          (list
           (cons 0 "POINT")
           (cons 100 "AcDbEntity")
           (cons 67 0)
           (cons 8 "0")
           (cons 100 "AcDbPoint")
           (list 10 8.5 -1.3 0)
           (cons 50 0)
          )
         )
         (entmake
          (list
           (cons 0 "POINT")
           (cons 100 "AcDbEntity")
           (cons 67 0)
           (cons 8 "0")
           (cons 100 "AcDbPoint")
           (list 10 7.1 1.3 0)
           (cons 50 0)
          )
         )
         (entmake
          (list
           (cons 0 "POINT")
           (cons 100 "AcDbEntity")
           (cons 67 0)
           (cons 8 "0")
           (cons 100 "AcDbPoint")
           (list 10 7.1 -1.3 0)
           (cons 50 0)
          )
         )
         (entmake
          (list
           (cons 0 "ATTDEF")
           (cons 100 "AcDbEntity")
           (cons 67 0)
           (cons 8 "0")
           (cons 100 "AcDbText")
           (list 10 -0.1 0.56666667 0)
           (cons 40 0.2)
           (cons 1 "0.600")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 0.23333333 0)
           (cons 40 0.2)
           (cons 1 "0.600")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 -0.1 0)
           (cons 40 0.2)
           (cons 1 "7.100")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-28-PUP"))
        (progn
         (entmake)
         (entmake
          (list
           (cons 0 "BLOCK")
           (cons 2 "AB_INF-WB-28-PUP")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 3)
           (cons 70 129)
           (cons 43 0)
           (cons 38 0)
           (cons 39 0)
           (list 10 0 0)
           (cons 40 0)
           (cons 41 0)
           (cons 42 0)
           (cons 91 0)
           (list 10 2.1 1.3)
           (cons 40 0)
           (cons 41 0)
           (cons 42 0)
           (cons 91 0)
           (list 10 2.1 -1.3)
           (cons 40 0)
           (cons 41 0)
           (cons 42 0)
           (cons 91 0)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 2.1 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 -0.7445528)
           (cons 40 0)
           (cons 41 0)
           (cons 42 0)
           (cons 91 0)
           (list 10 1.5412 -0.5702072)
           (cons 40 0)
           (cons 41 0)
           (cons 42 0)
           (cons 91 0)
           (list 10 1.697664 -0.51768)
           (cons 40 0)
           (cons 41 0)
           (cons 42 0)
           (cons 91 0)
           (list 10 2.502336 -0.51768)
           (cons 40 0)
           (cons 41 0)
           (cons 42 0)
           (cons 91 0)
           (list 10 2.6588 -0.5702072)
           (cons 40 0)
           (cons 41 0)
           (cons 42 0)
           (cons 91 0)
           (list 10 2.6588 -0.7445528)
           (cons 40 0)
           (cons 41 0)
           (cons 42 0)
           (cons 91 0)
           (list 10 2.502336 -0.79708)
           (cons 40 0)
           (cons 41 0)
           (cons 42 0)
           (cons 91 0)
           (list 10 1.697664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 -1.2474728)
           (cons 40 0)
           (cons 41 0)
           (cons 42 0)
           (cons 91 0)
           (list 10 1.5412 -1.0731272)
           (cons 40 0)
           (cons 41 0)
           (cons 42 0)
           (cons 91 0)
           (list 10 1.697664 -1.0206)
           (cons 40 0)
           (cons 41 0)
           (cons 42 0)
           (cons 91 0)
           (list 10 2.502336 -1.0206)
           (cons 40 0)
           (cons 41 0)
           (cons 42 0)
           (cons 91 0)
           (list 10 2.6588 -1.0731272)
           (cons 40 0)
           (cons 41 0)
           (cons 42 0)
           (cons 91 0)
           (list 10 2.6588 -1.2474728)
           (cons 40 0)
           (cons 41 0)
           (cons 42 0)
           (cons 91 0)
           (list 10 2.502336 -1.3)
           (cons 40 0)
           (cons 41 0)
           (cons 42 0)
           (cons 91 0)
           (list 10 1.697664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 0.5702072)
           (cons 40 0)
           (cons 41 0)
           (cons 42 0)
           (cons 91 0)
           (list 10 1.5412 0.7445528)
           (cons 40 0)
           (cons 41 0)
           (cons 42 0)
           (cons 91 0)
           (list 10 1.697664 0.79708)
           (cons 40 0)
           (cons 41 0)
           (cons 42 0)
           (cons 91 0)
           (list 10 2.502336 0.79708)
           (cons 40 0)
           (cons 41 0)
           (cons 42 0)
           (cons 91 0)
           (list 10 2.6588 0.7445528)
           (cons 40 0)
           (cons 41 0)
           (cons 42 0)
           (cons 91 0)
           (list 10 2.6588 0.5702072)
           (cons 40 0)
           (cons 41 0)
           (cons 42 0)
           (cons 91 0)
           (list 10 2.502336 0.51768)
           (cons 40 0)
           (cons 41 0)
           (cons 42 0)
           (cons 91 0)
           (list 10 1.697664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 1.0731272)
           (cons 40 0)
           (cons 41 0)
           (cons 42 0)
           (cons 91 0)
           (list 10 1.5412 1.2474728)
           (cons 40 0)
           (cons 41 0)
           (cons 42 0)
           (cons 91 0)
           (list 10 1.697664 1.3)
           (cons 40 0)
           (cons 41 0)
           (cons 42 0)
           (cons 91 0)
           (list 10 2.502336 1.3)
           (cons 40 0)
           (cons 41 0)
           (cons 42 0)
           (cons 91 0)
           (list 10 2.6588 1.2474728)
           (cons 40 0)
           (cons 41 0)
           (cons 42 0)
           (cons 91 0)
           (list 10 2.6588 1.0731272)
           (cons 40 0)
           (cons 41 0)
           (cons 42 0)
           (cons 91 0)
           (list 10 2.502336 1.0206)
           (cons 40 0)
           (cons 41 0)
           (cons 42 0)
           (cons 91 0)
           (list 10 1.697664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 2.1 1.3 0)
           (cons 50 0)
          )
         )
         (entmake
          (list
           (cons 0 "POINT")
           (cons 100 "AcDbEntity")
           (cons 67 0)
           (cons 8 "0")
           (cons 100 "AcDbPoint")
           (list 10 2.1 -1.3 0)
           (cons 50 0)
          )
         )
         (entmake
          (list
           (cons 0 "POINT")
           (cons 100 "AcDbEntity")
           (cons 67 0)
           (cons 8 "0")
           (cons 100 "AcDbPoint")
           (list 10 2.1 0 0)
           (cons 50 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "2.100")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "2.100")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-28-TRAILER1"))
        (progn
         (entmake)
         (entmake
          (list
           (cons 0 "BLOCK")
           (cons 2 "AB_INF-WB-28-TRAILER1")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 -1.3)
           (cons 40 0)
           (cons 41 0)
           (cons 42 0)
           (cons 91 0)
           (list 10 16.2 -1.3)
           (cons 40 0)
           (cons 41 0)
           (cons 42 0)
           (cons 91 0)
           (list 10 16.2 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 16.2 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 16.2 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.2062 -0.7445528)
           (cons 40 0)
           (cons 41 0)
           (cons 42 0)
           (cons 91 0)
           (list 10 13.2062 -0.5702072)
           (cons 40 0)
           (cons 41 0)
           (cons 42 0)
           (cons 91 0)
           (list 10 13.362664 -0.51768)
           (cons 40 0)
           (cons 41 0)
           (cons 42 0)
           (cons 91 0)
           (list 10 14.167336 -0.51768)
           (cons 40 0)
           (cons 41 0)
           (cons 42 0)
           (cons 91 0)
           (list 10 14.3238 -0.5702072)
           (cons 40 0)
           (cons 41 0)
           (cons 42 0)
           (cons 91 0)
           (list 10 14.3238 -0.7445528)
           (cons 40 0)
           (cons 41 0)
           (cons 42 0)
           (cons 91 0)
           (list 10 14.167336 -0.79708)
           (cons 40 0)
           (cons 41 0)
           (cons 42 0)
           (cons 91 0)
           (list 10 13.362664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.2062 -1.2474728)
           (cons 40 0)
           (cons 41 0)
           (cons 42 0)
           (cons 91 0)
           (list 10 13.2062 -1.0731272)
           (cons 40 0)
           (cons 41 0)
           (cons 42 0)
           (cons 91 0)
           (list 10 13.362664 -1.0206)
           (cons 40 0)
           (cons 41 0)
           (cons 42 0)
           (cons 91 0)
           (list 10 14.167336 -1.0206)
           (cons 40 0)
           (cons 41 0)
           (cons 42 0)
           (cons 91 0)
           (list 10 14.3238 -1.0731272)
           (cons 40 0)
           (cons 41 0)
           (cons 42 0)
           (cons 91 0)
           (list 10 14.3238 -1.2474728)
           (cons 40 0)
           (cons 41 0)
           (cons 42 0)
           (cons 91 0)
           (list 10 14.167336 -1.3)
           (cons 40 0)
           (cons 41 0)
           (cons 42 0)
           (cons 91 0)
           (list 10 13.362664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.2062 0.5702072)
           (cons 40 0)
           (cons 41 0)
           (cons 42 0)
           (cons 91 0)
           (list 10 13.2062 0.7445528)
           (cons 40 0)
           (cons 41 0)
           (cons 42 0)
           (cons 91 0)
           (list 10 13.362664 0.79708)
           (cons 40 0)
           (cons 41 0)
           (cons 42 0)
           (cons 91 0)
           (list 10 14.167336 0.79708)
           (cons 40 0)
           (cons 41 0)
           (cons 42 0)
           (cons 91 0)
           (list 10 14.3238 0.7445528)
           (cons 40 0)
           (cons 41 0)
           (cons 42 0)
           (cons 91 0)
           (list 10 14.3238 0.5702072)
           (cons 40 0)
           (cons 41 0)
           (cons 42 0)
           (cons 91 0)
           (list 10 14.167336 0.51768)
           (cons 40 0)
           (cons 41 0)
           (cons 42 0)
           (cons 91 0)
           (list 10 13.362664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.2062 1.0731272)
           (cons 40 0)
           (cons 41 0)
           (cons 42 0)
           (cons 91 0)
           (list 10 13.2062 1.2474728)
           (cons 40 0)
           (cons 41 0)
           (cons 42 0)
           (cons 91 0)
           (list 10 13.362664 1.3)
           (cons 40 0)
           (cons 41 0)
           (cons 42 0)
           (cons 91 0)
           (list 10 14.167336 1.3)
           (cons 40 0)
           (cons 41 0)
           (cons 42 0)
           (cons 91 0)
           (list 10 14.3238 1.2474728)
           (cons 40 0)
           (cons 41 0)
           (cons 42 0)
           (cons 91 0)
           (list 10 14.3238 1.0731272)
           (cons 40 0)
           (cons 41 0)
           (cons 42 0)
           (cons 91 0)
           (list 10 14.167336 1.0206)
           (cons 40 0)
           (cons 41 0)
           (cons 42 0)
           (cons 91 0)
           (list 10 13.362664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.4762 -0.7445528)
           (cons 40 0)
           (cons 41 0)
           (cons 42 0)
           (cons 91 0)
           (list 10 14.4762 -0.5702072)
           (cons 40 0)
           (cons 41 0)
           (cons 42 0)
           (cons 91 0)
           (list 10 14.632664 -0.51768)
           (cons 40 0)
           (cons 41 0)
           (cons 42 0)
           (cons 91 0)
           (list 10 15.437336 -0.51768)
           (cons 40 0)
           (cons 41 0)
           (cons 42 0)
           (cons 91 0)
           (list 10 15.5938 -0.5702072)
           (cons 40 0)
           (cons 41 0)
           (cons 42 0)
           (cons 91 0)
           (list 10 15.5938 -0.7445528)
           (cons 40 0)
           (cons 41 0)
           (cons 42 0)
           (cons 91 0)
           (list 10 15.437336 -0.79708)
           (cons 40 0)
           (cons 41 0)
           (cons 42 0)
           (cons 91 0)
           (list 10 14.632664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.4762 -1.2474728)
           (cons 40 0)
           (cons 41 0)
           (cons 42 0)
           (cons 91 0)
           (list 10 14.4762 -1.0731272)
           (cons 40 0)
           (cons 41 0)
           (cons 42 0)
           (cons 91 0)
           (list 10 14.632664 -1.0206)
           (cons 40 0)
           (cons 41 0)
           (cons 42 0)
           (cons 91 0)
           (list 10 15.437336 -1.0206)
           (cons 40 0)
           (cons 41 0)
           (cons 42 0)
           (cons 91 0)
           (list 10 15.5938 -1.0731272)
           (cons 40 0)
           (cons 41 0)
           (cons 42 0)
           (cons 91 0)
           (list 10 15.5938 -1.2474728)
           (cons 40 0)
           (cons 41 0)
           (cons 42 0)
           (cons 91 0)
           (list 10 15.437336 -1.3)
           (cons 40 0)
           (cons 41 0)
           (cons 42 0)
           (cons 91 0)
           (list 10 14.632664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.4762 0.5702072)
           (cons 40 0)
           (cons 41 0)
           (cons 42 0)
           (cons 91 0)
           (list 10 14.4762 0.7445528)
           (cons 40 0)
           (cons 41 0)
           (cons 42 0)
           (cons 91 0)
           (list 10 14.632664 0.79708)
           (cons 40 0)
           (cons 41 0)
           (cons 42 0)
           (cons 91 0)
           (list 10 15.437336 0.79708)
           (cons 40 0)
           (cons 41 0)
           (cons 42 0)
           (cons 91 0)
           (list 10 15.5938 0.7445528)
           (cons 40 0)
           (cons 41 0)
           (cons 42 0)
           (cons 91 0)
           (list 10 15.5938 0.5702072)
           (cons 40 0)
           (cons 41 0)
           (cons 42 0)
           (cons 91 0)
           (list 10 15.437336 0.51768)
           (cons 40 0)
           (cons 41 0)
           (cons 42 0)
           (cons 91 0)
           (list 10 14.632664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.4762 1.0731272)
           (cons 40 0)
           (cons 41 0)
           (cons 42 0)
           (cons 91 0)
           (list 10 14.4762 1.2474728)
           (cons 40 0)
           (cons 41 0)
           (cons 42 0)
           (cons 91 0)
           (list 10 14.632664 1.3)
           (cons 40 0)
           (cons 41 0)
           (cons 42 0)
           (cons 91 0)
           (list 10 15.437336 1.3)
           (cons 40 0)
           (cons 41 0)
           (cons 42 0)
           (cons 91 0)
           (list 10 15.5938 1.2474728)
           (cons 40 0)
           (cons 41 0)
           (cons 42 0)
           (cons 91 0)
           (list 10 15.5938 1.0731272)
           (cons 40 0)
           (cons 41 0)
           (cons 42 0)
           (cons 91 0)
           (list 10 15.437336 1.0206)
           (cons 40 0)
           (cons 41 0)
           (cons 42 0)
           (cons 91 0)
           (list 10 14.632664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 1.9 0 0)
           (cons 50 0)
          )
         )
         (entmake
          (list
           (cons 0 "POINT")
           (cons 100 "AcDbEntity")
           (cons 67 0)
           (cons 8 "0")
           (cons 100 "AcDbPoint")
           (list 10 14.4 1.3 0)
           (cons 50 0)
          )
         )
         (entmake
          (list
           (cons 0 "POINT")
           (cons 100 "AcDbEntity")
           (cons 67 0)
           (cons 8 "0")
           (cons 100 "AcDbPoint")
           (list 10 14.4 -1.3 0)
           (cons 50 0)
          )
         )
         (entmake
          (list
           (cons 0 "POINT")
           (cons 100 "AcDbEntity")
           (cons 67 0)
           (cons 8 "0")
           (cons 100 "AcDbPoint")
           (list 10 16.2 -1.3 0)
           (cons 50 0)
          )
         )
         (entmake
          (list
           (cons 0 "POINT")
           (cons 100 "AcDbEntity")
           (cons 67 0)
           (cons 8 "0")
           (cons 100 "AcDbPoint")
           (list 10 16.2 1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 16.2 0 0)
           (cons 50 0)
          )
         )
         (entmake
          (list
           (cons 0 "ATTDEF")
           (cons 100 "AcDbEntity")
           (cons 67 0)
           (cons 8 "0")
           (cons 100 "AcDbText")
           (list 10 1.2 0.56666667 0)
           (cons 40 0.2)
           (cons 1 "1.900")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.2 0.23333333 0)
           (cons 40 0.2)
           (cons 1 "1.900")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.2 -0.1 0)
           (cons 40 0.2)
           (cons 1 "14.400")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.2 -0.43333333 0)
           (cons 40 0.2)
           (cons 1 "16.200")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.2 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-28-TRUCK"))
        (progn
         (entmake)
         (entmake
          (list
           (cons 0 "BLOCK")
           (cons 2 "AB_INF-WB-28-TRUCK")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 -1.3)
           (cons 40 0)
           (cons 41 0)
           (cons 42 0)
           (cons 91 0)
           (list 10 6.335 -1.3)
           (cons 40 0)
           (cons 41 0)
           (cons 42 0)
           (cons 91 0)
           (list 10 6.335 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.335 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.335 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 5.7 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 5.96263966 -0.26263966 0)
           (list 11 5.96263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.5062 -0.7445528)
           (cons 40 0)
           (cons 41 0)
           (cons 42 0)
           (cons 91 0)
           (list 10 4.5062 -0.5702072)
           (cons 40 0)
           (cons 41 0)
           (cons 42 0)
           (cons 91 0)
           (list 10 4.662664 -0.51768)
           (cons 40 0)
           (cons 41 0)
           (cons 42 0)
           (cons 91 0)
           (list 10 5.467336 -0.51768)
           (cons 40 0)
           (cons 41 0)
           (cons 42 0)
           (cons 91 0)
           (list 10 5.6238 -0.5702072)
           (cons 40 0)
           (cons 41 0)
           (cons 42 0)
           (cons 91 0)
           (list 10 5.6238 -0.7445528)
           (cons 40 0)
           (cons 41 0)
           (cons 42 0)
           (cons 91 0)
           (list 10 5.467336 -0.79708)
           (cons 40 0)
           (cons 41 0)
           (cons 42 0)
           (cons 91 0)
           (list 10 4.662664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.5062 -1.2474728)
           (cons 40 0)
           (cons 41 0)
           (cons 42 0)
           (cons 91 0)
           (list 10 4.5062 -1.0731272)
           (cons 40 0)
           (cons 41 0)
           (cons 42 0)
           (cons 91 0)
           (list 10 4.662664 -1.0206)
           (cons 40 0)
           (cons 41 0)
           (cons 42 0)
           (cons 91 0)
           (list 10 5.467336 -1.0206)
           (cons 40 0)
           (cons 41 0)
           (cons 42 0)
           (cons 91 0)
           (list 10 5.6238 -1.0731272)
           (cons 40 0)
           (cons 41 0)
           (cons 42 0)
           (cons 91 0)
           (list 10 5.6238 -1.2474728)
           (cons 40 0)
           (cons 41 0)
           (cons 42 0)
           (cons 91 0)
           (list 10 5.467336 -1.3)
           (cons 40 0)
           (cons 41 0)
           (cons 42 0)
           (cons 91 0)
           (list 10 4.662664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.5062 0.5702072)
           (cons 40 0)
           (cons 41 0)
           (cons 42 0)
           (cons 91 0)
           (list 10 4.5062 0.7445528)
           (cons 40 0)
           (cons 41 0)
           (cons 42 0)
           (cons 91 0)
           (list 10 4.662664 0.79708)
           (cons 40 0)
           (cons 41 0)
           (cons 42 0)
           (cons 91 0)
           (list 10 5.467336 0.79708)
           (cons 40 0)
           (cons 41 0)
           (cons 42 0)
           (cons 91 0)
           (list 10 5.6238 0.7445528)
           (cons 40 0)
           (cons 41 0)
           (cons 42 0)
           (cons 91 0)
           (list 10 5.6238 0.5702072)
           (cons 40 0)
           (cons 41 0)
           (cons 42 0)
           (cons 91 0)
           (list 10 5.467336 0.51768)
           (cons 40 0)
           (cons 41 0)
           (cons 42 0)
           (cons 91 0)
           (list 10 4.662664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.5062 1.0731272)
           (cons 40 0)
           (cons 41 0)
           (cons 42 0)
           (cons 91 0)
           (list 10 4.5062 1.2474728)
           (cons 40 0)
           (cons 41 0)
           (cons 42 0)
           (cons 91 0)
           (list 10 4.662664 1.3)
           (cons 40 0)
           (cons 41 0)
           (cons 42 0)
           (cons 91 0)
           (list 10 5.467336 1.3)
           (cons 40 0)
           (cons 41 0)
           (cons 42 0)
           (cons 91 0)
           (list 10 5.6238 1.2474728)
           (cons 40 0)
           (cons 41 0)
           (cons 42 0)
           (cons 91 0)
           (list 10 5.6238 1.0731272)
           (cons 40 0)
           (cons 41 0)
           (cons 42 0)
           (cons 91 0)
           (list 10 5.467336 1.0206)
           (cons 40 0)
           (cons 41 0)
           (cons 42 0)
           (cons 91 0)
           (list 10 4.662664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.7762 -0.7445528)
           (cons 40 0)
           (cons 41 0)
           (cons 42 0)
           (cons 91 0)
           (list 10 5.7762 -0.5702072)
           (cons 40 0)
           (cons 41 0)
           (cons 42 0)
           (cons 91 0)
           (list 10 5.932664 -0.51768)
           (cons 40 0)
           (cons 41 0)
           (cons 42 0)
           (cons 91 0)
           (list 10 6.737336 -0.51768)
           (cons 40 0)
           (cons 41 0)
           (cons 42 0)
           (cons 91 0)
           (list 10 6.8938 -0.5702072)
           (cons 40 0)
           (cons 41 0)
           (cons 42 0)
           (cons 91 0)
           (list 10 6.8938 -0.7445528)
           (cons 40 0)
           (cons 41 0)
           (cons 42 0)
           (cons 91 0)
           (list 10 6.737336 -0.79708)
           (cons 40 0)
           (cons 41 0)
           (cons 42 0)
           (cons 91 0)
           (list 10 5.932664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.7762 -1.2474728)
           (cons 40 0)
           (cons 41 0)
           (cons 42 0)
           (cons 91 0)
           (list 10 5.7762 -1.0731272)
           (cons 40 0)
           (cons 41 0)
           (cons 42 0)
           (cons 91 0)
           (list 10 5.932664 -1.0206)
           (cons 40 0)
           (cons 41 0)
           (cons 42 0)
           (cons 91 0)
           (list 10 6.737336 -1.0206)
           (cons 40 0)
           (cons 41 0)
           (cons 42 0)
           (cons 91 0)
           (list 10 6.8938 -1.0731272)
           (cons 40 0)
           (cons 41 0)
           (cons 42 0)
           (cons 91 0)
           (list 10 6.8938 -1.2474728)
           (cons 40 0)
           (cons 41 0)
           (cons 42 0)
           (cons 91 0)
           (list 10 6.737336 -1.3)
           (cons 40 0)
           (cons 41 0)
           (cons 42 0)
           (cons 91 0)
           (list 10 5.932664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.7762 0.5702072)
           (cons 40 0)
           (cons 41 0)
           (cons 42 0)
           (cons 91 0)
           (list 10 5.7762 0.7445528)
           (cons 40 0)
           (cons 41 0)
           (cons 42 0)
           (cons 91 0)
           (list 10 5.932664 0.79708)
           (cons 40 0)
           (cons 41 0)
           (cons 42 0)
           (cons 91 0)
           (list 10 6.737336 0.79708)
           (cons 40 0)
           (cons 41 0)
           (cons 42 0)
           (cons 91 0)
           (list 10 6.8938 0.7445528)
           (cons 40 0)
           (cons 41 0)
           (cons 42 0)
           (cons 91 0)
           (list 10 6.8938 0.5702072)
           (cons 40 0)
           (cons 41 0)
           (cons 42 0)
           (cons 91 0)
           (list 10 6.737336 0.51768)
           (cons 40 0)
           (cons 41 0)
           (cons 42 0)
           (cons 91 0)
           (list 10 5.932664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.7762 1.0731272)
           (cons 40 0)
           (cons 41 0)
           (cons 42 0)
           (cons 91 0)
           (list 10 5.7762 1.2474728)
           (cons 40 0)
           (cons 41 0)
           (cons 42 0)
           (cons 91 0)
           (list 10 5.932664 1.3)
           (cons 40 0)
           (cons 41 0)
           (cons 42 0)
           (cons 91 0)
           (list 10 6.737336 1.3)
           (cons 40 0)
           (cons 41 0)
           (cons 42 0)
           (cons 91 0)
           (list 10 6.8938 1.2474728)
           (cons 40 0)
           (cons 41 0)
           (cons 42 0)
           (cons 91 0)
           (list 10 6.8938 1.0731272)
           (cons 40 0)
           (cons 41 0)
           (cons 42 0)
           (cons 91 0)
           (list 10 6.737336 1.0206)
           (cons 40 0)
           (cons 41 0)
           (cons 42 0)
           (cons 91 0)
           (list 10 5.932664 1.0206)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelLeftM1")
           (list 10 0.7 -1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM1")
           (list 10 0.7 1.0206 0)
           (cons 41 1)
           (cons 42 1)
           (cons 43 1)
           (cons 50 0)
           (cons 70 0)
           (cons 71 0)
           (cons 44 0)
           (cons 45 0)
          )
         )
         (entmake
          (list
           (cons 0 "POINT")
           (cons 100 "AcDbEntity")
           (cons 67 0)
           (cons 8 "0")
           (cons 100 "AcDbPoint")
           (list 10 5.7 1.3 0)
           (cons 50 0)
          )
         )
         (entmake
          (list
           (cons 0 "POINT")
           (cons 100 "AcDbEntity")
           (cons 67 0)
           (cons 8 "0")
           (cons 100 "AcDbPoint")
           (list 10 5.7 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0.7 -1.3 0)
           (cons 50 0)
          )
         )
         (entmake
          (list
           (cons 0 "POINT")
           (cons 100 "AcDbEntity")
           (cons 67 0)
           (cons 8 "0")
           (cons 100 "AcDbPoint")
           (list 10 0.7 1.3 0)
           (cons 50 0)
          )
         )
         (entmake
          (list
           (cons 0 "POINT")
           (cons 100 "AcDbEntity")
           (cons 67 0)
           (cons 8 "0")
           (cons 100 "AcDbPoint")
           (list 10 0.7 0 0)
           (cons 50 0)
          )
         )
         (entmake
          (list
           (cons 0 "POINT")
           (cons 100 "AcDbEntity")
           (cons 67 0)
           (cons 8 "0")
           (cons 100 "AcDbPoint")
           (list 10 5.7 0 0)
           (cons 50 0)
          )
         )
         (entmake
          (list
           (cons 0 "ATTDEF")
           (cons 100 "AcDbEntity")
           (cons 67 0)
           (cons 8 "0")
           (cons 100 "AcDbText")
           (list 10 0 0.56666667 0)
           (cons 40 0.2)
           (cons 1 "0.700")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0 0.23333333 0)
           (cons 40 0.2)
           (cons 1 "0.700")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0 -0.1 0)
           (cons 40 0.2)
           (cons 1 "5.700")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0 -0.43333333 0)
           (cons 40 0.2)
           (cons 1 "5.700")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0 -0.76666667 0)
           (cons 40 0.2)
           (cons 1 "19.79")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-23-TRAILER2"))
        (progn
         (entmake)
         (entmake
          (list
           (cons 0 "BLOCK")
           (cons 2 "AB_INF-WB-23-TRAILER2")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 10.8 -1.3)
           (cons 40 0)
           (cons 41 0)
           (cons 42 0)
           (cons 91 0)
           (list 10 10.8 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 10.8 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 10.8 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.1062 -0.7445528)
           (cons 40 0)
           (cons 41 0)
           (cons 42 0)
           (cons 91 0)
           (list 10 8.1062 -0.5702072)
           (cons 40 0)
           (cons 41 0)
           (cons 42 0)
           (cons 91 0)
           (list 10 8.262664 -0.51768)
           (cons 40 0)
           (cons 41 0)
           (cons 42 0)
           (cons 91 0)
           (list 10 9.067336 -0.51768)
           (cons 40 0)
           (cons 41 0)
           (cons 42 0)
           (cons 91 0)
           (list 10 9.2238 -0.5702072)
           (cons 40 0)
           (cons 41 0)
           (cons 42 0)
           (cons 91 0)
           (list 10 9.2238 -0.7445528)
           (cons 40 0)
           (cons 41 0)
           (cons 42 0)
           (cons 91 0)
           (list 10 9.067336 -0.79708)
           (cons 40 0)
           (cons 41 0)
           (cons 42 0)
           (cons 91 0)
           (list 10 8.262664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.1062 -1.2474728)
           (cons 40 0)
           (cons 41 0)
           (cons 42 0)
           (cons 91 0)
           (list 10 8.1062 -1.0731272)
           (cons 40 0)
           (cons 41 0)
           (cons 42 0)
           (cons 91 0)
           (list 10 8.262664 -1.0206)
           (cons 40 0)
           (cons 41 0)
           (cons 42 0)
           (cons 91 0)
           (list 10 9.067336 -1.0206)
           (cons 40 0)
           (cons 41 0)
           (cons 42 0)
           (cons 91 0)
           (list 10 9.2238 -1.0731272)
           (cons 40 0)
           (cons 41 0)
           (cons 42 0)
           (cons 91 0)
           (list 10 9.2238 -1.2474728)
           (cons 40 0)
           (cons 41 0)
           (cons 42 0)
           (cons 91 0)
           (list 10 9.067336 -1.3)
           (cons 40 0)
           (cons 41 0)
           (cons 42 0)
           (cons 91 0)
           (list 10 8.262664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.1062 0.5702072)
           (cons 40 0)
           (cons 41 0)
           (cons 42 0)
           (cons 91 0)
           (list 10 8.1062 0.7445528)
           (cons 40 0)
           (cons 41 0)
           (cons 42 0)
           (cons 91 0)
           (list 10 8.262664 0.79708)
           (cons 40 0)
           (cons 41 0)
           (cons 42 0)
           (cons 91 0)
           (list 10 9.067336 0.79708)
           (cons 40 0)
           (cons 41 0)
           (cons 42 0)
           (cons 91 0)
           (list 10 9.2238 0.7445528)
           (cons 40 0)
           (cons 41 0)
           (cons 42 0)
           (cons 91 0)
           (list 10 9.2238 0.5702072)
           (cons 40 0)
           (cons 41 0)
           (cons 42 0)
           (cons 91 0)
           (list 10 9.067336 0.51768)
           (cons 40 0)
           (cons 41 0)
           (cons 42 0)
           (cons 91 0)
           (list 10 8.262664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.1062 1.0731272)
           (cons 40 0)
           (cons 41 0)
           (cons 42 0)
           (cons 91 0)
           (list 10 8.1062 1.2474728)
           (cons 40 0)
           (cons 41 0)
           (cons 42 0)
           (cons 91 0)
           (list 10 8.262664 1.3)
           (cons 40 0)
           (cons 41 0)
           (cons 42 0)
           (cons 91 0)
           (list 10 9.067336 1.3)
           (cons 40 0)
           (cons 41 0)
           (cons 42 0)
           (cons 91 0)
           (list 10 9.2238 1.2474728)
           (cons 40 0)
           (cons 41 0)
           (cons 42 0)
           (cons 91 0)
           (list 10 9.2238 1.0731272)
           (cons 40 0)
           (cons 41 0)
           (cons 42 0)
           (cons 91 0)
           (list 10 9.067336 1.0206)
           (cons 40 0)
           (cons 41 0)
           (cons 42 0)
           (cons 91 0)
           (list 10 8.262664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.3762 -0.7445528)
           (cons 40 0)
           (cons 41 0)
           (cons 42 0)
           (cons 91 0)
           (list 10 9.3762 -0.5702072)
           (cons 40 0)
           (cons 41 0)
           (cons 42 0)
           (cons 91 0)
           (list 10 9.532664 -0.51768)
           (cons 40 0)
           (cons 41 0)
           (cons 42 0)
           (cons 91 0)
           (list 10 10.337336 -0.51768)
           (cons 40 0)
           (cons 41 0)
           (cons 42 0)
           (cons 91 0)
           (list 10 10.4938 -0.5702072)
           (cons 40 0)
           (cons 41 0)
           (cons 42 0)
           (cons 91 0)
           (list 10 10.4938 -0.7445528)
           (cons 40 0)
           (cons 41 0)
           (cons 42 0)
           (cons 91 0)
           (list 10 10.337336 -0.79708)
           (cons 40 0)
           (cons 41 0)
           (cons 42 0)
           (cons 91 0)
           (list 10 9.532664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.3762 -1.2474728)
           (cons 40 0)
           (cons 41 0)
           (cons 42 0)
           (cons 91 0)
           (list 10 9.3762 -1.0731272)
           (cons 40 0)
           (cons 41 0)
           (cons 42 0)
           (cons 91 0)
           (list 10 9.532664 -1.0206)
           (cons 40 0)
           (cons 41 0)
           (cons 42 0)
           (cons 91 0)
           (list 10 10.337336 -1.0206)
           (cons 40 0)
           (cons 41 0)
           (cons 42 0)
           (cons 91 0)
           (list 10 10.4938 -1.0731272)
           (cons 40 0)
           (cons 41 0)
           (cons 42 0)
           (cons 91 0)
           (list 10 10.4938 -1.2474728)
           (cons 40 0)
           (cons 41 0)
           (cons 42 0)
           (cons 91 0)
           (list 10 10.337336 -1.3)
           (cons 40 0)
           (cons 41 0)
           (cons 42 0)
           (cons 91 0)
           (list 10 9.532664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.3762 0.5702072)
           (cons 40 0)
           (cons 41 0)
           (cons 42 0)
           (cons 91 0)
           (list 10 9.3762 0.7445528)
           (cons 40 0)
           (cons 41 0)
           (cons 42 0)
           (cons 91 0)
           (list 10 9.532664 0.79708)
           (cons 40 0)
           (cons 41 0)
           (cons 42 0)
           (cons 91 0)
           (list 10 10.337336 0.79708)
           (cons 40 0)
           (cons 41 0)
           (cons 42 0)
           (cons 91 0)
           (list 10 10.4938 0.7445528)
           (cons 40 0)
           (cons 41 0)
           (cons 42 0)
           (cons 91 0)
           (list 10 10.4938 0.5702072)
           (cons 40 0)
           (cons 41 0)
           (cons 42 0)
           (cons 91 0)
           (list 10 10.337336 0.51768)
           (cons 40 0)
           (cons 41 0)
           (cons 42 0)
           (cons 91 0)
           (list 10 9.532664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.3762 1.0731272)
           (cons 40 0)
           (cons 41 0)
           (cons 42 0)
           (cons 91 0)
           (list 10 9.3762 1.2474728)
           (cons 40 0)
           (cons 41 0)
           (cons 42 0)
           (cons 91 0)
           (list 10 9.532664 1.3)
           (cons 40 0)
           (cons 41 0)
           (cons 42 0)
           (cons 91 0)
           (list 10 10.337336 1.3)
           (cons 40 0)
           (cons 41 0)
           (cons 42 0)
           (cons 91 0)
           (list 10 10.4938 1.2474728)
           (cons 40 0)
           (cons 41 0)
           (cons 42 0)
           (cons 91 0)
           (list 10 10.4938 1.0731272)
           (cons 40 0)
           (cons 41 0)
           (cons 42 0)
           (cons 91 0)
           (list 10 10.337336 1.0206)
           (cons 40 0)
           (cons 41 0)
           (cons 42 0)
           (cons 91 0)
           (list 10 9.532664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 1.3 0 0)
           (cons 50 0)
          )
         )
         (entmake
          (list
           (cons 0 "POINT")
           (cons 100 "AcDbEntity")
           (cons 67 0)
           (cons 8 "0")
           (cons 100 "AcDbPoint")
           (list 10 9.3 1.3 0)
           (cons 50 0)
          )
         )
         (entmake
          (list
           (cons 0 "POINT")
           (cons 100 "AcDbEntity")
           (cons 67 0)
           (cons 8 "0")
           (cons 100 "AcDbPoint")
           (list 10 9.3 -1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 10.8 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 10.8 1.3 0)
           (cons 50 0)
          )
         )
         (entmake
          (list
           (cons 0 "ATTDEF")
           (cons 100 "AcDbEntity")
           (cons 67 0)
           (cons 8 "0")
           (cons 100 "AcDbText")
           (list 10 0.6 0.56666667 0)
           (cons 40 0.2)
           (cons 1 "1.300")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 0.23333333 0)
           (cons 40 0.2)
           (cons 1 "1.300")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.1 0)
           (cons 40 0.2)
           (cons 1 "9.300")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-23-TRAILER1"))
        (progn
         (entmake)
         (entmake
          (list
           (cons 0 "BLOCK")
           (cons 2 "AB_INF-WB-23-TRAILER1")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 10.57 -1.3)
           (cons 40 0)
           (cons 41 0)
           (cons 42 0)
           (cons 91 0)
           (list 10 10.57 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.6 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.6 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 10.57 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 10.57 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.6 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.6 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 10.57 0 0)
           (list 11 10.8 0 0)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 10.8 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 11.06263966 -0.26263966 0)
           (list 11 11.06263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.4712 -0.7445528)
           (cons 40 0)
           (cons 41 0)
           (cons 42 0)
           (cons 91 0)
           (list 10 7.4712 -0.5702072)
           (cons 40 0)
           (cons 41 0)
           (cons 42 0)
           (cons 91 0)
           (list 10 7.627664 -0.51768)
           (cons 40 0)
           (cons 41 0)
           (cons 42 0)
           (cons 91 0)
           (list 10 8.432336 -0.51768)
           (cons 40 0)
           (cons 41 0)
           (cons 42 0)
           (cons 91 0)
           (list 10 8.5888 -0.5702072)
           (cons 40 0)
           (cons 41 0)
           (cons 42 0)
           (cons 91 0)
           (list 10 8.5888 -0.7445528)
           (cons 40 0)
           (cons 41 0)
           (cons 42 0)
           (cons 91 0)
           (list 10 8.432336 -0.79708)
           (cons 40 0)
           (cons 41 0)
           (cons 42 0)
           (cons 91 0)
           (list 10 7.627664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.4712 -1.2474728)
           (cons 40 0)
           (cons 41 0)
           (cons 42 0)
           (cons 91 0)
           (list 10 7.4712 -1.0731272)
           (cons 40 0)
           (cons 41 0)
           (cons 42 0)
           (cons 91 0)
           (list 10 7.627664 -1.0206)
           (cons 40 0)
           (cons 41 0)
           (cons 42 0)
           (cons 91 0)
           (list 10 8.432336 -1.0206)
           (cons 40 0)
           (cons 41 0)
           (cons 42 0)
           (cons 91 0)
           (list 10 8.5888 -1.0731272)
           (cons 40 0)
           (cons 41 0)
           (cons 42 0)
           (cons 91 0)
           (list 10 8.5888 -1.2474728)
           (cons 40 0)
           (cons 41 0)
           (cons 42 0)
           (cons 91 0)
           (list 10 8.432336 -1.3)
           (cons 40 0)
           (cons 41 0)
           (cons 42 0)
           (cons 91 0)
           (list 10 7.627664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.4712 0.5702072)
           (cons 40 0)
           (cons 41 0)
           (cons 42 0)
           (cons 91 0)
           (list 10 7.4712 0.7445528)
           (cons 40 0)
           (cons 41 0)
           (cons 42 0)
           (cons 91 0)
           (list 10 7.627664 0.79708)
           (cons 40 0)
           (cons 41 0)
           (cons 42 0)
           (cons 91 0)
           (list 10 8.432336 0.79708)
           (cons 40 0)
           (cons 41 0)
           (cons 42 0)
           (cons 91 0)
           (list 10 8.5888 0.7445528)
           (cons 40 0)
           (cons 41 0)
           (cons 42 0)
           (cons 91 0)
           (list 10 8.5888 0.5702072)
           (cons 40 0)
           (cons 41 0)
           (cons 42 0)
           (cons 91 0)
           (list 10 8.432336 0.51768)
           (cons 40 0)
           (cons 41 0)
           (cons 42 0)
           (cons 91 0)
           (list 10 7.627664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.4712 1.0731272)
           (cons 40 0)
           (cons 41 0)
           (cons 42 0)
           (cons 91 0)
           (list 10 7.4712 1.2474728)
           (cons 40 0)
           (cons 41 0)
           (cons 42 0)
           (cons 91 0)
           (list 10 7.627664 1.3)
           (cons 40 0)
           (cons 41 0)
           (cons 42 0)
           (cons 91 0)
           (list 10 8.432336 1.3)
           (cons 40 0)
           (cons 41 0)
           (cons 42 0)
           (cons 91 0)
           (list 10 8.5888 1.2474728)
           (cons 40 0)
           (cons 41 0)
           (cons 42 0)
           (cons 91 0)
           (list 10 8.5888 1.0731272)
           (cons 40 0)
           (cons 41 0)
           (cons 42 0)
           (cons 91 0)
           (list 10 8.432336 1.0206)
           (cons 40 0)
           (cons 41 0)
           (cons 42 0)
           (cons 91 0)
           (list 10 7.627664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.7412 -0.7445528)
           (cons 40 0)
           (cons 41 0)
           (cons 42 0)
           (cons 91 0)
           (list 10 8.7412 -0.5702072)
           (cons 40 0)
           (cons 41 0)
           (cons 42 0)
           (cons 91 0)
           (list 10 8.897664 -0.51768)
           (cons 40 0)
           (cons 41 0)
           (cons 42 0)
           (cons 91 0)
           (list 10 9.702336 -0.51768)
           (cons 40 0)
           (cons 41 0)
           (cons 42 0)
           (cons 91 0)
           (list 10 9.8588 -0.5702072)
           (cons 40 0)
           (cons 41 0)
           (cons 42 0)
           (cons 91 0)
           (list 10 9.8588 -0.7445528)
           (cons 40 0)
           (cons 41 0)
           (cons 42 0)
           (cons 91 0)
           (list 10 9.702336 -0.79708)
           (cons 40 0)
           (cons 41 0)
           (cons 42 0)
           (cons 91 0)
           (list 10 8.897664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.7412 -1.2474728)
           (cons 40 0)
           (cons 41 0)
           (cons 42 0)
           (cons 91 0)
           (list 10 8.7412 -1.0731272)
           (cons 40 0)
           (cons 41 0)
           (cons 42 0)
           (cons 91 0)
           (list 10 8.897664 -1.0206)
           (cons 40 0)
           (cons 41 0)
           (cons 42 0)
           (cons 91 0)
           (list 10 9.702336 -1.0206)
           (cons 40 0)
           (cons 41 0)
           (cons 42 0)
           (cons 91 0)
           (list 10 9.8588 -1.0731272)
           (cons 40 0)
           (cons 41 0)
           (cons 42 0)
           (cons 91 0)
           (list 10 9.8588 -1.2474728)
           (cons 40 0)
           (cons 41 0)
           (cons 42 0)
           (cons 91 0)
           (list 10 9.702336 -1.3)
           (cons 40 0)
           (cons 41 0)
           (cons 42 0)
           (cons 91 0)
           (list 10 8.897664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.7412 0.5702072)
           (cons 40 0)
           (cons 41 0)
           (cons 42 0)
           (cons 91 0)
           (list 10 8.7412 0.7445528)
           (cons 40 0)
           (cons 41 0)
           (cons 42 0)
           (cons 91 0)
           (list 10 8.897664 0.79708)
           (cons 40 0)
           (cons 41 0)
           (cons 42 0)
           (cons 91 0)
           (list 10 9.702336 0.79708)
           (cons 40 0)
           (cons 41 0)
           (cons 42 0)
           (cons 91 0)
           (list 10 9.8588 0.7445528)
           (cons 40 0)
           (cons 41 0)
           (cons 42 0)
           (cons 91 0)
           (list 10 9.8588 0.5702072)
           (cons 40 0)
           (cons 41 0)
           (cons 42 0)
           (cons 91 0)
           (list 10 9.702336 0.51768)
           (cons 40 0)
           (cons 41 0)
           (cons 42 0)
           (cons 91 0)
           (list 10 8.897664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.7412 1.0731272)
           (cons 40 0)
           (cons 41 0)
           (cons 42 0)
           (cons 91 0)
           (list 10 8.7412 1.2474728)
           (cons 40 0)
           (cons 41 0)
           (cons 42 0)
           (cons 91 0)
           (list 10 8.897664 1.3)
           (cons 40 0)
           (cons 41 0)
           (cons 42 0)
           (cons 91 0)
           (list 10 9.702336 1.3)
           (cons 40 0)
           (cons 41 0)
           (cons 42 0)
           (cons 91 0)
           (list 10 9.8588 1.2474728)
           (cons 40 0)
           (cons 41 0)
           (cons 42 0)
           (cons 91 0)
           (list 10 9.8588 1.0731272)
           (cons 40 0)
           (cons 41 0)
           (cons 42 0)
           (cons 91 0)
           (list 10 9.702336 1.0206)
           (cons 40 0)
           (cons 41 0)
           (cons 42 0)
           (cons 91 0)
           (list 10 8.897664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.0112 -0.7445528)
           (cons 40 0)
           (cons 41 0)
           (cons 42 0)
           (cons 91 0)
           (list 10 10.0112 -0.5702072)
           (cons 40 0)
           (cons 41 0)
           (cons 42 0)
           (cons 91 0)
           (list 10 10.167664 -0.51768)
           (cons 40 0)
           (cons 41 0)
           (cons 42 0)
           (cons 91 0)
           (list 10 10.972336 -0.51768)
           (cons 40 0)
           (cons 41 0)
           (cons 42 0)
           (cons 91 0)
           (list 10 11.1288 -0.5702072)
           (cons 40 0)
           (cons 41 0)
           (cons 42 0)
           (cons 91 0)
           (list 10 11.1288 -0.7445528)
           (cons 40 0)
           (cons 41 0)
           (cons 42 0)
           (cons 91 0)
           (list 10 10.972336 -0.79708)
           (cons 40 0)
           (cons 41 0)
           (cons 42 0)
           (cons 91 0)
           (list 10 10.167664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.0112 -1.2474728)
           (cons 40 0)
           (cons 41 0)
           (cons 42 0)
           (cons 91 0)
           (list 10 10.0112 -1.0731272)
           (cons 40 0)
           (cons 41 0)
           (cons 42 0)
           (cons 91 0)
           (list 10 10.167664 -1.0206)
           (cons 40 0)
           (cons 41 0)
           (cons 42 0)
           (cons 91 0)
           (list 10 10.972336 -1.0206)
           (cons 40 0)
           (cons 41 0)
           (cons 42 0)
           (cons 91 0)
           (list 10 11.1288 -1.0731272)
           (cons 40 0)
           (cons 41 0)
           (cons 42 0)
           (cons 91 0)
           (list 10 11.1288 -1.2474728)
           (cons 40 0)
           (cons 41 0)
           (cons 42 0)
           (cons 91 0)
           (list 10 10.972336 -1.3)
           (cons 40 0)
           (cons 41 0)
           (cons 42 0)
           (cons 91 0)
           (list 10 10.167664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.0112 0.5702072)
           (cons 40 0)
           (cons 41 0)
           (cons 42 0)
           (cons 91 0)
           (list 10 10.0112 0.7445528)
           (cons 40 0)
           (cons 41 0)
           (cons 42 0)
           (cons 91 0)
           (list 10 10.167664 0.79708)
           (cons 40 0)
           (cons 41 0)
           (cons 42 0)
           (cons 91 0)
           (list 10 10.972336 0.79708)
           (cons 40 0)
           (cons 41 0)
           (cons 42 0)
           (cons 91 0)
           (list 10 11.1288 0.7445528)
           (cons 40 0)
           (cons 41 0)
           (cons 42 0)
           (cons 91 0)
           (list 10 11.1288 0.5702072)
           (cons 40 0)
           (cons 41 0)
           (cons 42 0)
           (cons 91 0)
           (list 10 10.972336 0.51768)
           (cons 40 0)
           (cons 41 0)
           (cons 42 0)
           (cons 91 0)
           (list 10 10.167664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.0112 1.0731272)
           (cons 40 0)
           (cons 41 0)
           (cons 42 0)
           (cons 91 0)
           (list 10 10.0112 1.2474728)
           (cons 40 0)
           (cons 41 0)
           (cons 42 0)
           (cons 91 0)
           (list 10 10.167664 1.3)
           (cons 40 0)
           (cons 41 0)
           (cons 42 0)
           (cons 91 0)
           (list 10 10.972336 1.3)
           (cons 40 0)
           (cons 41 0)
           (cons 42 0)
           (cons 91 0)
           (list 10 11.1288 1.2474728)
           (cons 40 0)
           (cons 41 0)
           (cons 42 0)
           (cons 91 0)
           (list 10 11.1288 1.0731272)
           (cons 40 0)
           (cons 41 0)
           (cons 42 0)
           (cons 91 0)
           (list 10 10.972336 1.0206)
           (cons 40 0)
           (cons 41 0)
           (cons 42 0)
           (cons 91 0)
           (list 10 10.167664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 9.3 1.3 0)
           (cons 50 0)
          )
         )
         (entmake
          (list
           (cons 0 "POINT")
           (cons 100 "AcDbEntity")
           (cons 67 0)
           (cons 8 "0")
           (cons 100 "AcDbPoint")
           (list 10 9.3 -1.3 0)
           (cons 50 0)
          )
         )
         (entmake
          (list
           (cons 0 "POINT")
           (cons 100 "AcDbEntity")
           (cons 67 0)
           (cons 8 "0")
           (cons 100 "AcDbPoint")
           (list 10 1.3 0 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 10.8 0 0)
           (cons 50 0)
          )
         )
         (entmake
          (list
           (cons 0 "ATTDEF")
           (cons 100 "AcDbEntity")
           (cons 67 0)
           (cons 8 "0")
           (cons 100 "AcDbText")
           (list 10 0.6 0.56666667 0)
           (cons 40 0.2)
           (cons 1 "1.300")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 0.23333333 0)
           (cons 40 0.2)
           (cons 1 "1.300")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.1 0)
           (cons 40 0.2)
           (cons 1 "9.300")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.43333333 0)
           (cons 40 0.2)
           (cons 1 "10.800")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-23-TRUCK"))
        (progn
         (entmake)
         (entmake
          (list
           (cons 0 "BLOCK")
           (cons 2 "AB_INF-WB-23-TRUCK")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 6.635 -1.3)
           (cons 40 0)
           (cons 41 0)
           (cons 42 0)
           (cons 91 0)
           (list 10 6.635 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.635 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.635 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 6 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 6.26263966 -0.26263966 0)
           (list 11 6.26263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.8062 -0.7445528)
           (cons 40 0)
           (cons 41 0)
           (cons 42 0)
           (cons 91 0)
           (list 10 4.8062 -0.5702072)
           (cons 40 0)
           (cons 41 0)
           (cons 42 0)
           (cons 91 0)
           (list 10 4.962664 -0.51768)
           (cons 40 0)
           (cons 41 0)
           (cons 42 0)
           (cons 91 0)
           (list 10 5.767336 -0.51768)
           (cons 40 0)
           (cons 41 0)
           (cons 42 0)
           (cons 91 0)
           (list 10 5.9238 -0.5702072)
           (cons 40 0)
           (cons 41 0)
           (cons 42 0)
           (cons 91 0)
           (list 10 5.9238 -0.7445528)
           (cons 40 0)
           (cons 41 0)
           (cons 42 0)
           (cons 91 0)
           (list 10 5.767336 -0.79708)
           (cons 40 0)
           (cons 41 0)
           (cons 42 0)
           (cons 91 0)
           (list 10 4.962664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.8062 -1.2474728)
           (cons 40 0)
           (cons 41 0)
           (cons 42 0)
           (cons 91 0)
           (list 10 4.8062 -1.0731272)
           (cons 40 0)
           (cons 41 0)
           (cons 42 0)
           (cons 91 0)
           (list 10 4.962664 -1.0206)
           (cons 40 0)
           (cons 41 0)
           (cons 42 0)
           (cons 91 0)
           (list 10 5.767336 -1.0206)
           (cons 40 0)
           (cons 41 0)
           (cons 42 0)
           (cons 91 0)
           (list 10 5.9238 -1.0731272)
           (cons 40 0)
           (cons 41 0)
           (cons 42 0)
           (cons 91 0)
           (list 10 5.9238 -1.2474728)
           (cons 40 0)
           (cons 41 0)
           (cons 42 0)
           (cons 91 0)
           (list 10 5.767336 -1.3)
           (cons 40 0)
           (cons 41 0)
           (cons 42 0)
           (cons 91 0)
           (list 10 4.962664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.8062 0.5702072)
           (cons 40 0)
           (cons 41 0)
           (cons 42 0)
           (cons 91 0)
           (list 10 4.8062 0.7445528)
           (cons 40 0)
           (cons 41 0)
           (cons 42 0)
           (cons 91 0)
           (list 10 4.962664 0.79708)
           (cons 40 0)
           (cons 41 0)
           (cons 42 0)
           (cons 91 0)
           (list 10 5.767336 0.79708)
           (cons 40 0)
           (cons 41 0)
           (cons 42 0)
           (cons 91 0)
           (list 10 5.9238 0.7445528)
           (cons 40 0)
           (cons 41 0)
           (cons 42 0)
           (cons 91 0)
           (list 10 5.9238 0.5702072)
           (cons 40 0)
           (cons 41 0)
           (cons 42 0)
           (cons 91 0)
           (list 10 5.767336 0.51768)
           (cons 40 0)
           (cons 41 0)
           (cons 42 0)
           (cons 91 0)
           (list 10 4.962664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.8062 1.0731272)
           (cons 40 0)
           (cons 41 0)
           (cons 42 0)
           (cons 91 0)
           (list 10 4.8062 1.2474728)
           (cons 40 0)
           (cons 41 0)
           (cons 42 0)
           (cons 91 0)
           (list 10 4.962664 1.3)
           (cons 40 0)
           (cons 41 0)
           (cons 42 0)
           (cons 91 0)
           (list 10 5.767336 1.3)
           (cons 40 0)
           (cons 41 0)
           (cons 42 0)
           (cons 91 0)
           (list 10 5.9238 1.2474728)
           (cons 40 0)
           (cons 41 0)
           (cons 42 0)
           (cons 91 0)
           (list 10 5.9238 1.0731272)
           (cons 40 0)
           (cons 41 0)
           (cons 42 0)
           (cons 91 0)
           (list 10 5.767336 1.0206)
           (cons 40 0)
           (cons 41 0)
           (cons 42 0)
           (cons 91 0)
           (list 10 4.962664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.0762 -0.7445528)
           (cons 40 0)
           (cons 41 0)
           (cons 42 0)
           (cons 91 0)
           (list 10 6.0762 -0.5702072)
           (cons 40 0)
           (cons 41 0)
           (cons 42 0)
           (cons 91 0)
           (list 10 6.232664 -0.51768)
           (cons 40 0)
           (cons 41 0)
           (cons 42 0)
           (cons 91 0)
           (list 10 7.037336 -0.51768)
           (cons 40 0)
           (cons 41 0)
           (cons 42 0)
           (cons 91 0)
           (list 10 7.1938 -0.5702072)
           (cons 40 0)
           (cons 41 0)
           (cons 42 0)
           (cons 91 0)
           (list 10 7.1938 -0.7445528)
           (cons 40 0)
           (cons 41 0)
           (cons 42 0)
           (cons 91 0)
           (list 10 7.037336 -0.79708)
           (cons 40 0)
           (cons 41 0)
           (cons 42 0)
           (cons 91 0)
           (list 10 6.232664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.0762 -1.2474728)
           (cons 40 0)
           (cons 41 0)
           (cons 42 0)
           (cons 91 0)
           (list 10 6.0762 -1.0731272)
           (cons 40 0)
           (cons 41 0)
           (cons 42 0)
           (cons 91 0)
           (list 10 6.232664 -1.0206)
           (cons 40 0)
           (cons 41 0)
           (cons 42 0)
           (cons 91 0)
           (list 10 7.037336 -1.0206)
           (cons 40 0)
           (cons 41 0)
           (cons 42 0)
           (cons 91 0)
           (list 10 7.1938 -1.0731272)
           (cons 40 0)
           (cons 41 0)
           (cons 42 0)
           (cons 91 0)
           (list 10 7.1938 -1.2474728)
           (cons 40 0)
           (cons 41 0)
           (cons 42 0)
           (cons 91 0)
           (list 10 7.037336 -1.3)
           (cons 40 0)
           (cons 41 0)
           (cons 42 0)
           (cons 91 0)
           (list 10 6.232664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.0762 0.5702072)
           (cons 40 0)
           (cons 41 0)
           (cons 42 0)
           (cons 91 0)
           (list 10 6.0762 0.7445528)
           (cons 40 0)
           (cons 41 0)
           (cons 42 0)
           (cons 91 0)
           (list 10 6.232664 0.79708)
           (cons 40 0)
           (cons 41 0)
           (cons 42 0)
           (cons 91 0)
           (list 10 7.037336 0.79708)
           (cons 40 0)
           (cons 41 0)
           (cons 42 0)
           (cons 91 0)
           (list 10 7.1938 0.7445528)
           (cons 40 0)
           (cons 41 0)
           (cons 42 0)
           (cons 91 0)
           (list 10 7.1938 0.5702072)
           (cons 40 0)
           (cons 41 0)
           (cons 42 0)
           (cons 91 0)
           (list 10 7.037336 0.51768)
           (cons 40 0)
           (cons 41 0)
           (cons 42 0)
           (cons 91 0)
           (list 10 6.232664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.0762 1.0731272)
           (cons 40 0)
           (cons 41 0)
           (cons 42 0)
           (cons 91 0)
           (list 10 6.0762 1.2474728)
           (cons 40 0)
           (cons 41 0)
           (cons 42 0)
           (cons 91 0)
           (list 10 6.232664 1.3)
           (cons 40 0)
           (cons 41 0)
           (cons 42 0)
           (cons 91 0)
           (list 10 7.037336 1.3)
           (cons 40 0)
           (cons 41 0)
           (cons 42 0)
           (cons 91 0)
           (list 10 7.1938 1.2474728)
           (cons 40 0)
           (cons 41 0)
           (cons 42 0)
           (cons 91 0)
           (list 10 7.1938 1.0731272)
           (cons 40 0)
           (cons 41 0)
           (cons 42 0)
           (cons 91 0)
           (list 10 7.037336 1.0206)
           (cons 40 0)
           (cons 41 0)
           (cons 42 0)
           (cons 91 0)
           (list 10 6.232664 1.0206)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelLeftM1")
           (list 10 0.7 -1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM1")
           (list 10 0.7 1.0206 0)
           (cons 41 1)
           (cons 42 1)
           (cons 43 1)
           (cons 50 0)
           (cons 70 0)
           (cons 71 0)
           (cons 44 0)
           (cons 45 0)
          )
         )
         (entmake
          (list
           (cons 0 "POINT")
           (cons 100 "AcDbEntity")
           (cons 67 0)
           (cons 8 "0")
           (cons 100 "AcDbPoint")
           (list 10 0.7 1.3 0)
           (cons 50 0)
          )
         )
         (entmake
          (list
           (cons 0 "POINT")
           (cons 100 "AcDbEntity")
           (cons 67 0)
           (cons 8 "0")
           (cons 100 "AcDbPoint")
           (list 10 0.7 -1.3 0)
           (cons 50 0)
          )
         )
         (entmake
          (list
           (cons 0 "POINT")
           (cons 100 "AcDbEntity")
           (cons 67 0)
           (cons 8 "0")
           (cons 100 "AcDbPoint")
           (list 10 0.7 0 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 6 0 0)
           (cons 50 0)
          )
         )
         (entmake
          (list
           (cons 0 "POINT")
           (cons 100 "AcDbEntity")
           (cons 67 0)
           (cons 8 "0")
           (cons 100 "AcDbPoint")
           (list 10 6 1.3 0)
           (cons 50 0)
          )
         )
         (entmake
          (list
           (cons 0 "POINT")
           (cons 100 "AcDbEntity")
           (cons 67 0)
           (cons 8 "0")
           (cons 100 "AcDbPoint")
           (list 10 6 -1.3 0)
           (cons 50 0)
          )
         )
         (entmake
          (list
           (cons 0 "ATTDEF")
           (cons 100 "AcDbEntity")
           (cons 67 0)
           (cons 8 "0")
           (cons 100 "AcDbText")
           (list 10 0 0.56666667 0)
           (cons 40 0.2)
           (cons 1 "0.700")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0 0.23333333 0)
           (cons 40 0.2)
           (cons 1 "0.700")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0 -0.1 0)
           (cons 40 0.2)
           (cons 1 "6.000")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0 -0.43333333 0)
           (cons 40 0.2)
           (cons 1 "6.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0 -0.76666667 0)
           (cons 40 0.2)
           (cons 1 "28.68")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-21-TRAILER"))
        (progn
         (entmake)
         (entmake
          (list
           (cons 0 "BLOCK")
           (cons 2 "AB_INF-WB-21-TRAILER")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 16.2 -1.3)
           (cons 40 0)
           (cons 41 0)
           (cons 42 0)
           (cons 91 0)
           (list 10 16.2 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 16.2 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 16.2 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.9412 -0.7445528)
           (cons 40 0)
           (cons 41 0)
           (cons 42 0)
           (cons 91 0)
           (list 10 11.9412 -0.5702072)
           (cons 40 0)
           (cons 41 0)
           (cons 42 0)
           (cons 91 0)
           (list 10 12.097664 -0.51768)
           (cons 40 0)
           (cons 41 0)
           (cons 42 0)
           (cons 91 0)
           (list 10 12.902336 -0.51768)
           (cons 40 0)
           (cons 41 0)
           (cons 42 0)
           (cons 91 0)
           (list 10 13.0588 -0.5702072)
           (cons 40 0)
           (cons 41 0)
           (cons 42 0)
           (cons 91 0)
           (list 10 13.0588 -0.7445528)
           (cons 40 0)
           (cons 41 0)
           (cons 42 0)
           (cons 91 0)
           (list 10 12.902336 -0.79708)
           (cons 40 0)
           (cons 41 0)
           (cons 42 0)
           (cons 91 0)
           (list 10 12.097664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.9412 -1.2474728)
           (cons 40 0)
           (cons 41 0)
           (cons 42 0)
           (cons 91 0)
           (list 10 11.9412 -1.0731272)
           (cons 40 0)
           (cons 41 0)
           (cons 42 0)
           (cons 91 0)
           (list 10 12.097664 -1.0206)
           (cons 40 0)
           (cons 41 0)
           (cons 42 0)
           (cons 91 0)
           (list 10 12.902336 -1.0206)
           (cons 40 0)
           (cons 41 0)
           (cons 42 0)
           (cons 91 0)
           (list 10 13.0588 -1.0731272)
           (cons 40 0)
           (cons 41 0)
           (cons 42 0)
           (cons 91 0)
           (list 10 13.0588 -1.2474728)
           (cons 40 0)
           (cons 41 0)
           (cons 42 0)
           (cons 91 0)
           (list 10 12.902336 -1.3)
           (cons 40 0)
           (cons 41 0)
           (cons 42 0)
           (cons 91 0)
           (list 10 12.097664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.9412 0.5702072)
           (cons 40 0)
           (cons 41 0)
           (cons 42 0)
           (cons 91 0)
           (list 10 11.9412 0.7445528)
           (cons 40 0)
           (cons 41 0)
           (cons 42 0)
           (cons 91 0)
           (list 10 12.097664 0.79708)
           (cons 40 0)
           (cons 41 0)
           (cons 42 0)
           (cons 91 0)
           (list 10 12.902336 0.79708)
           (cons 40 0)
           (cons 41 0)
           (cons 42 0)
           (cons 91 0)
           (list 10 13.0588 0.7445528)
           (cons 40 0)
           (cons 41 0)
           (cons 42 0)
           (cons 91 0)
           (list 10 13.0588 0.5702072)
           (cons 40 0)
           (cons 41 0)
           (cons 42 0)
           (cons 91 0)
           (list 10 12.902336 0.51768)
           (cons 40 0)
           (cons 41 0)
           (cons 42 0)
           (cons 91 0)
           (list 10 12.097664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.9412 1.0731272)
           (cons 40 0)
           (cons 41 0)
           (cons 42 0)
           (cons 91 0)
           (list 10 11.9412 1.2474728)
           (cons 40 0)
           (cons 41 0)
           (cons 42 0)
           (cons 91 0)
           (list 10 12.097664 1.3)
           (cons 40 0)
           (cons 41 0)
           (cons 42 0)
           (cons 91 0)
           (list 10 12.902336 1.3)
           (cons 40 0)
           (cons 41 0)
           (cons 42 0)
           (cons 91 0)
           (list 10 13.0588 1.2474728)
           (cons 40 0)
           (cons 41 0)
           (cons 42 0)
           (cons 91 0)
           (list 10 13.0588 1.0731272)
           (cons 40 0)
           (cons 41 0)
           (cons 42 0)
           (cons 91 0)
           (list 10 12.902336 1.0206)
           (cons 40 0)
           (cons 41 0)
           (cons 42 0)
           (cons 91 0)
           (list 10 12.097664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.2412 -0.7445528)
           (cons 40 0)
           (cons 41 0)
           (cons 42 0)
           (cons 91 0)
           (list 10 13.2412 -0.5702072)
           (cons 40 0)
           (cons 41 0)
           (cons 42 0)
           (cons 91 0)
           (list 10 13.397664 -0.51768)
           (cons 40 0)
           (cons 41 0)
           (cons 42 0)
           (cons 91 0)
           (list 10 14.202336 -0.51768)
           (cons 40 0)
           (cons 41 0)
           (cons 42 0)
           (cons 91 0)
           (list 10 14.3588 -0.5702072)
           (cons 40 0)
           (cons 41 0)
           (cons 42 0)
           (cons 91 0)
           (list 10 14.3588 -0.7445528)
           (cons 40 0)
           (cons 41 0)
           (cons 42 0)
           (cons 91 0)
           (list 10 14.202336 -0.79708)
           (cons 40 0)
           (cons 41 0)
           (cons 42 0)
           (cons 91 0)
           (list 10 13.397664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.2412 -1.2474728)
           (cons 40 0)
           (cons 41 0)
           (cons 42 0)
           (cons 91 0)
           (list 10 13.2412 -1.0731272)
           (cons 40 0)
           (cons 41 0)
           (cons 42 0)
           (cons 91 0)
           (list 10 13.397664 -1.0206)
           (cons 40 0)
           (cons 41 0)
           (cons 42 0)
           (cons 91 0)
           (list 10 14.202336 -1.0206)
           (cons 40 0)
           (cons 41 0)
           (cons 42 0)
           (cons 91 0)
           (list 10 14.3588 -1.0731272)
           (cons 40 0)
           (cons 41 0)
           (cons 42 0)
           (cons 91 0)
           (list 10 14.3588 -1.2474728)
           (cons 40 0)
           (cons 41 0)
           (cons 42 0)
           (cons 91 0)
           (list 10 14.202336 -1.3)
           (cons 40 0)
           (cons 41 0)
           (cons 42 0)
           (cons 91 0)
           (list 10 13.397664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.2412 0.5702072)
           (cons 40 0)
           (cons 41 0)
           (cons 42 0)
           (cons 91 0)
           (list 10 13.2412 0.7445528)
           (cons 40 0)
           (cons 41 0)
           (cons 42 0)
           (cons 91 0)
           (list 10 13.397664 0.79708)
           (cons 40 0)
           (cons 41 0)
           (cons 42 0)
           (cons 91 0)
           (list 10 14.202336 0.79708)
           (cons 40 0)
           (cons 41 0)
           (cons 42 0)
           (cons 91 0)
           (list 10 14.3588 0.7445528)
           (cons 40 0)
           (cons 41 0)
           (cons 42 0)
           (cons 91 0)
           (list 10 14.3588 0.5702072)
           (cons 40 0)
           (cons 41 0)
           (cons 42 0)
           (cons 91 0)
           (list 10 14.202336 0.51768)
           (cons 40 0)
           (cons 41 0)
           (cons 42 0)
           (cons 91 0)
           (list 10 13.397664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.2412 1.0731272)
           (cons 40 0)
           (cons 41 0)
           (cons 42 0)
           (cons 91 0)
           (list 10 13.2412 1.2474728)
           (cons 40 0)
           (cons 41 0)
           (cons 42 0)
           (cons 91 0)
           (list 10 13.397664 1.3)
           (cons 40 0)
           (cons 41 0)
           (cons 42 0)
           (cons 91 0)
           (list 10 14.202336 1.3)
           (cons 40 0)
           (cons 41 0)
           (cons 42 0)
           (cons 91 0)
           (list 10 14.3588 1.2474728)
           (cons 40 0)
           (cons 41 0)
           (cons 42 0)
           (cons 91 0)
           (list 10 14.3588 1.0731272)
           (cons 40 0)
           (cons 41 0)
           (cons 42 0)
           (cons 91 0)
           (list 10 14.202336 1.0206)
           (cons 40 0)
           (cons 41 0)
           (cons 42 0)
           (cons 91 0)
           (list 10 13.397664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.5412 -0.7445528)
           (cons 40 0)
           (cons 41 0)
           (cons 42 0)
           (cons 91 0)
           (list 10 14.5412 -0.5702072)
           (cons 40 0)
           (cons 41 0)
           (cons 42 0)
           (cons 91 0)
           (list 10 14.697664 -0.51768)
           (cons 40 0)
           (cons 41 0)
           (cons 42 0)
           (cons 91 0)
           (list 10 15.502336 -0.51768)
           (cons 40 0)
           (cons 41 0)
           (cons 42 0)
           (cons 91 0)
           (list 10 15.6588 -0.5702072)
           (cons 40 0)
           (cons 41 0)
           (cons 42 0)
           (cons 91 0)
           (list 10 15.6588 -0.7445528)
           (cons 40 0)
           (cons 41 0)
           (cons 42 0)
           (cons 91 0)
           (list 10 15.502336 -0.79708)
           (cons 40 0)
           (cons 41 0)
           (cons 42 0)
           (cons 91 0)
           (list 10 14.697664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.5412 -1.2474728)
           (cons 40 0)
           (cons 41 0)
           (cons 42 0)
           (cons 91 0)
           (list 10 14.5412 -1.0731272)
           (cons 40 0)
           (cons 41 0)
           (cons 42 0)
           (cons 91 0)
           (list 10 14.697664 -1.0206)
           (cons 40 0)
           (cons 41 0)
           (cons 42 0)
           (cons 91 0)
           (list 10 15.502336 -1.0206)
           (cons 40 0)
           (cons 41 0)
           (cons 42 0)
           (cons 91 0)
           (list 10 15.6588 -1.0731272)
           (cons 40 0)
           (cons 41 0)
           (cons 42 0)
           (cons 91 0)
           (list 10 15.6588 -1.2474728)
           (cons 40 0)
           (cons 41 0)
           (cons 42 0)
           (cons 91 0)
           (list 10 15.502336 -1.3)
           (cons 40 0)
           (cons 41 0)
           (cons 42 0)
           (cons 91 0)
           (list 10 14.697664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.5412 0.5702072)
           (cons 40 0)
           (cons 41 0)
           (cons 42 0)
           (cons 91 0)
           (list 10 14.5412 0.7445528)
           (cons 40 0)
           (cons 41 0)
           (cons 42 0)
           (cons 91 0)
           (list 10 14.697664 0.79708)
           (cons 40 0)
           (cons 41 0)
           (cons 42 0)
           (cons 91 0)
           (list 10 15.502336 0.79708)
           (cons 40 0)
           (cons 41 0)
           (cons 42 0)
           (cons 91 0)
           (list 10 15.6588 0.7445528)
           (cons 40 0)
           (cons 41 0)
           (cons 42 0)
           (cons 91 0)
           (list 10 15.6588 0.5702072)
           (cons 40 0)
           (cons 41 0)
           (cons 42 0)
           (cons 91 0)
           (list 10 15.502336 0.51768)
           (cons 40 0)
           (cons 41 0)
           (cons 42 0)
           (cons 91 0)
           (list 10 14.697664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.5412 1.0731272)
           (cons 40 0)
           (cons 41 0)
           (cons 42 0)
           (cons 91 0)
           (list 10 14.5412 1.2474728)
           (cons 40 0)
           (cons 41 0)
           (cons 42 0)
           (cons 91 0)
           (list 10 14.697664 1.3)
           (cons 40 0)
           (cons 41 0)
           (cons 42 0)
           (cons 91 0)
           (list 10 15.502336 1.3)
           (cons 40 0)
           (cons 41 0)
           (cons 42 0)
           (cons 91 0)
           (list 10 15.6588 1.2474728)
           (cons 40 0)
           (cons 41 0)
           (cons 42 0)
           (cons 91 0)
           (list 10 15.6588 1.0731272)
           (cons 40 0)
           (cons 41 0)
           (cons 42 0)
           (cons 91 0)
           (list 10 15.502336 1.0206)
           (cons 40 0)
           (cons 41 0)
           (cons 42 0)
           (cons 91 0)
           (list 10 14.697664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 13.8 1.3 0)
           (cons 50 0)
          )
         )
         (entmake
          (list
           (cons 0 "POINT")
           (cons 100 "AcDbEntity")
           (cons 67 0)
           (cons 8 "0")
           (cons 100 "AcDbPoint")
           (list 10 13.8 -1.3 0)
           (cons 50 0)
          )
         )
         (entmake
          (list
           (cons 0 "POINT")
           (cons 100 "AcDbEntity")
           (cons 67 0)
           (cons 8 "0")
           (cons 100 "AcDbPoint")
           (list 10 16.2 -1.3 0)
           (cons 50 0)
          )
         )
         (entmake
          (list
           (cons 0 "POINT")
           (cons 100 "AcDbEntity")
           (cons 67 0)
           (cons 8 "0")
           (cons 100 "AcDbPoint")
           (list 10 16.2 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 1.3 0 0)
           (cons 50 0)
          )
         )
         (entmake
          (list
           (cons 0 "ATTDEF")
           (cons 100 "AcDbEntity")
           (cons 67 0)
           (cons 8 "0")
           (cons 100 "AcDbText")
           (list 10 0.6 0.56666667 0)
           (cons 40 0.2)
           (cons 1 "1.300")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 0.23333333 0)
           (cons 40 0.2)
           (cons 1 "1.300")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.1 0)
           (cons 40 0.2)
           (cons 1 "13.800")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-21-TRUCK"))
        (progn
         (entmake)
         (entmake
          (list
           (cons 0 "BLOCK")
           (cons 2 "AB_INF-WB-21-TRUCK")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 8.75 -1.3)
           (cons 40 0)
           (cons 41 0)
           (cons 42 0)
           (cons 91 0)
           (list 10 8.75 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.2 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.2 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.75 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.75 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.2 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.2 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 8.1 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 8.36263966 -0.26263966 0)
           (list 11 8.36263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.8912 -0.7445528)
           (cons 40 0)
           (cons 41 0)
           (cons 42 0)
           (cons 91 0)
           (list 10 6.8912 -0.5702072)
           (cons 40 0)
           (cons 41 0)
           (cons 42 0)
           (cons 91 0)
           (list 10 7.047664 -0.51768)
           (cons 40 0)
           (cons 41 0)
           (cons 42 0)
           (cons 91 0)
           (list 10 7.852336 -0.51768)
           (cons 40 0)
           (cons 41 0)
           (cons 42 0)
           (cons 91 0)
           (list 10 8.0088 -0.5702072)
           (cons 40 0)
           (cons 41 0)
           (cons 42 0)
           (cons 91 0)
           (list 10 8.0088 -0.7445528)
           (cons 40 0)
           (cons 41 0)
           (cons 42 0)
           (cons 91 0)
           (list 10 7.852336 -0.79708)
           (cons 40 0)
           (cons 41 0)
           (cons 42 0)
           (cons 91 0)
           (list 10 7.047664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.8912 -1.2474728)
           (cons 40 0)
           (cons 41 0)
           (cons 42 0)
           (cons 91 0)
           (list 10 6.8912 -1.0731272)
           (cons 40 0)
           (cons 41 0)
           (cons 42 0)
           (cons 91 0)
           (list 10 7.047664 -1.0206)
           (cons 40 0)
           (cons 41 0)
           (cons 42 0)
           (cons 91 0)
           (list 10 7.852336 -1.0206)
           (cons 40 0)
           (cons 41 0)
           (cons 42 0)
           (cons 91 0)
           (list 10 8.0088 -1.0731272)
           (cons 40 0)
           (cons 41 0)
           (cons 42 0)
           (cons 91 0)
           (list 10 8.0088 -1.2474728)
           (cons 40 0)
           (cons 41 0)
           (cons 42 0)
           (cons 91 0)
           (list 10 7.852336 -1.3)
           (cons 40 0)
           (cons 41 0)
           (cons 42 0)
           (cons 91 0)
           (list 10 7.047664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.8912 0.5702072)
           (cons 40 0)
           (cons 41 0)
           (cons 42 0)
           (cons 91 0)
           (list 10 6.8912 0.7445528)
           (cons 40 0)
           (cons 41 0)
           (cons 42 0)
           (cons 91 0)
           (list 10 7.047664 0.79708)
           (cons 40 0)
           (cons 41 0)
           (cons 42 0)
           (cons 91 0)
           (list 10 7.852336 0.79708)
           (cons 40 0)
           (cons 41 0)
           (cons 42 0)
           (cons 91 0)
           (list 10 8.0088 0.7445528)
           (cons 40 0)
           (cons 41 0)
           (cons 42 0)
           (cons 91 0)
           (list 10 8.0088 0.5702072)
           (cons 40 0)
           (cons 41 0)
           (cons 42 0)
           (cons 91 0)
           (list 10 7.852336 0.51768)
           (cons 40 0)
           (cons 41 0)
           (cons 42 0)
           (cons 91 0)
           (list 10 7.047664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.8912 1.0731272)
           (cons 40 0)
           (cons 41 0)
           (cons 42 0)
           (cons 91 0)
           (list 10 6.8912 1.2474728)
           (cons 40 0)
           (cons 41 0)
           (cons 42 0)
           (cons 91 0)
           (list 10 7.047664 1.3)
           (cons 40 0)
           (cons 41 0)
           (cons 42 0)
           (cons 91 0)
           (list 10 7.852336 1.3)
           (cons 40 0)
           (cons 41 0)
           (cons 42 0)
           (cons 91 0)
           (list 10 8.0088 1.2474728)
           (cons 40 0)
           (cons 41 0)
           (cons 42 0)
           (cons 91 0)
           (list 10 8.0088 1.0731272)
           (cons 40 0)
           (cons 41 0)
           (cons 42 0)
           (cons 91 0)
           (list 10 7.852336 1.0206)
           (cons 40 0)
           (cons 41 0)
           (cons 42 0)
           (cons 91 0)
           (list 10 7.047664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.1912 -0.7445528)
           (cons 40 0)
           (cons 41 0)
           (cons 42 0)
           (cons 91 0)
           (list 10 8.1912 -0.5702072)
           (cons 40 0)
           (cons 41 0)
           (cons 42 0)
           (cons 91 0)
           (list 10 8.347664 -0.51768)
           (cons 40 0)
           (cons 41 0)
           (cons 42 0)
           (cons 91 0)
           (list 10 9.152336 -0.51768)
           (cons 40 0)
           (cons 41 0)
           (cons 42 0)
           (cons 91 0)
           (list 10 9.3088 -0.5702072)
           (cons 40 0)
           (cons 41 0)
           (cons 42 0)
           (cons 91 0)
           (list 10 9.3088 -0.7445528)
           (cons 40 0)
           (cons 41 0)
           (cons 42 0)
           (cons 91 0)
           (list 10 9.152336 -0.79708)
           (cons 40 0)
           (cons 41 0)
           (cons 42 0)
           (cons 91 0)
           (list 10 8.347664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.1912 -1.2474728)
           (cons 40 0)
           (cons 41 0)
           (cons 42 0)
           (cons 91 0)
           (list 10 8.1912 -1.0731272)
           (cons 40 0)
           (cons 41 0)
           (cons 42 0)
           (cons 91 0)
           (list 10 8.347664 -1.0206)
           (cons 40 0)
           (cons 41 0)
           (cons 42 0)
           (cons 91 0)
           (list 10 9.152336 -1.0206)
           (cons 40 0)
           (cons 41 0)
           (cons 42 0)
           (cons 91 0)
           (list 10 9.3088 -1.0731272)
           (cons 40 0)
           (cons 41 0)
           (cons 42 0)
           (cons 91 0)
           (list 10 9.3088 -1.2474728)
           (cons 40 0)
           (cons 41 0)
           (cons 42 0)
           (cons 91 0)
           (list 10 9.152336 -1.3)
           (cons 40 0)
           (cons 41 0)
           (cons 42 0)
           (cons 91 0)
           (list 10 8.347664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.1912 0.5702072)
           (cons 40 0)
           (cons 41 0)
           (cons 42 0)
           (cons 91 0)
           (list 10 8.1912 0.7445528)
           (cons 40 0)
           (cons 41 0)
           (cons 42 0)
           (cons 91 0)
           (list 10 8.347664 0.79708)
           (cons 40 0)
           (cons 41 0)
           (cons 42 0)
           (cons 91 0)
           (list 10 9.152336 0.79708)
           (cons 40 0)
           (cons 41 0)
           (cons 42 0)
           (cons 91 0)
           (list 10 9.3088 0.7445528)
           (cons 40 0)
           (cons 41 0)
           (cons 42 0)
           (cons 91 0)
           (list 10 9.3088 0.5702072)
           (cons 40 0)
           (cons 41 0)
           (cons 42 0)
           (cons 91 0)
           (list 10 9.152336 0.51768)
           (cons 40 0)
           (cons 41 0)
           (cons 42 0)
           (cons 91 0)
           (list 10 8.347664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.1912 1.0731272)
           (cons 40 0)
           (cons 41 0)
           (cons 42 0)
           (cons 91 0)
           (list 10 8.1912 1.2474728)
           (cons 40 0)
           (cons 41 0)
           (cons 42 0)
           (cons 91 0)
           (list 10 8.347664 1.3)
           (cons 40 0)
           (cons 41 0)
           (cons 42 0)
           (cons 91 0)
           (list 10 9.152336 1.3)
           (cons 40 0)
           (cons 41 0)
           (cons 42 0)
           (cons 91 0)
           (list 10 9.3088 1.2474728)
           (cons 40 0)
           (cons 41 0)
           (cons 42 0)
           (cons 91 0)
           (list 10 9.3088 1.0731272)
           (cons 40 0)
           (cons 41 0)
           (cons 42 0)
           (cons 91 0)
           (list 10 9.152336 1.0206)
           (cons 40 0)
           (cons 41 0)
           (cons 42 0)
           (cons 91 0)
           (list 10 8.347664 1.0206)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelRightM1")
           (list 10 1.9 1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM1")
           (list 10 1.9 -1.0206 0)
           (cons 41 1)
           (cons 42 1)
           (cons 43 1)
           (cons 50 0)
           (cons 70 0)
           (cons 71 0)
           (cons 44 0)
           (cons 45 0)
          )
         )
         (entmake
          (list
           (cons 0 "POINT")
           (cons 100 "AcDbEntity")
           (cons 67 0)
           (cons 8 "0")
           (cons 100 "AcDbPoint")
           (list 10 1.9 -1.3 0)
           (cons 50 0)
          )
         )
         (entmake
          (list
           (cons 0 "POINT")
           (cons 100 "AcDbEntity")
           (cons 67 0)
           (cons 8 "0")
           (cons 100 "AcDbPoint")
           (list 10 1.9 1.3 0)
           (cons 50 0)
          )
         )
         (entmake
          (list
           (cons 0 "POINT")
           (cons 100 "AcDbEntity")
           (cons 67 0)
           (cons 8 "0")
           (cons 100 "AcDbPoint")
           (list 10 1.9 0 0)
           (cons 50 0)
          )
         )
         (entmake
          (list
           (cons 0 "POINT")
           (cons 100 "AcDbEntity")
           (cons 67 0)
           (cons 8 "0")
           (cons 100 "AcDbPoint")
           (list 10 8.1 1.3 0)
           (cons 50 0)
          )
         )
         (entmake
          (list
           (cons 0 "POINT")
           (cons 100 "AcDbEntity")
           (cons 67 0)
           (cons 8 "0")
           (cons 100 "AcDbPoint")
           (list 10 8.1 0 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 8.1 -1.3 0)
           (cons 50 0)
          )
         )
         (entmake
          (list
           (cons 0 "ATTDEF")
           (cons 100 "AcDbEntity")
           (cons 67 0)
           (cons 8 "0")
           (cons 100 "AcDbText")
           (list 10 1.2 0.56666667 0)
           (cons 40 0.2)
           (cons 1 "1.300")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.2 0.23333333 0)
           (cons 40 0.2)
           (cons 1 "1.300")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.2 -0.1 0)
           (cons 40 0.2)
           (cons 1 "8.100")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.2 -0.43333333 0)
           (cons 40 0.2)
           (cons 1 "8.100")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.2 -0.76666667 0)
           (cons 40 0.2)
           (cons 1 "26.64")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-17-TRAILER"))
        (progn
         (entmake)
         (entmake
          (list
           (cons 0 "BLOCK")
           (cons 2 "AB_INF-WB-17-TRAILER")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 14.3 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 14.3 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.6062 -0.7445528)
           (cons 40 0)
           (cons 41 0)
           (cons 42 0)
           (cons 91 0)
           (list 10 11.6062 -0.5702072)
           (cons 40 0)
           (cons 41 0)
           (cons 42 0)
           (cons 91 0)
           (list 10 11.762664 -0.51768)
           (cons 40 0)
           (cons 41 0)
           (cons 42 0)
           (cons 91 0)
           (list 10 12.567336 -0.51768)
           (cons 40 0)
           (cons 41 0)
           (cons 42 0)
           (cons 91 0)
           (list 10 12.7238 -0.5702072)
           (cons 40 0)
           (cons 41 0)
           (cons 42 0)
           (cons 91 0)
           (list 10 12.7238 -0.7445528)
           (cons 40 0)
           (cons 41 0)
           (cons 42 0)
           (cons 91 0)
           (list 10 12.567336 -0.79708)
           (cons 40 0)
           (cons 41 0)
           (cons 42 0)
           (cons 91 0)
           (list 10 11.762664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.6062 -1.2474728)
           (cons 40 0)
           (cons 41 0)
           (cons 42 0)
           (cons 91 0)
           (list 10 11.6062 -1.0731272)
           (cons 40 0)
           (cons 41 0)
           (cons 42 0)
           (cons 91 0)
           (list 10 11.762664 -1.0206)
           (cons 40 0)
           (cons 41 0)
           (cons 42 0)
           (cons 91 0)
           (list 10 12.567336 -1.0206)
           (cons 40 0)
           (cons 41 0)
           (cons 42 0)
           (cons 91 0)
           (list 10 12.7238 -1.0731272)
           (cons 40 0)
           (cons 41 0)
           (cons 42 0)
           (cons 91 0)
           (list 10 12.7238 -1.2474728)
           (cons 40 0)
           (cons 41 0)
           (cons 42 0)
           (cons 91 0)
           (list 10 12.567336 -1.3)
           (cons 40 0)
           (cons 41 0)
           (cons 42 0)
           (cons 91 0)
           (list 10 11.762664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.6062 0.5702072)
           (cons 40 0)
           (cons 41 0)
           (cons 42 0)
           (cons 91 0)
           (list 10 11.6062 0.7445528)
           (cons 40 0)
           (cons 41 0)
           (cons 42 0)
           (cons 91 0)
           (list 10 11.762664 0.79708)
           (cons 40 0)
           (cons 41 0)
           (cons 42 0)
           (cons 91 0)
           (list 10 12.567336 0.79708)
           (cons 40 0)
           (cons 41 0)
           (cons 42 0)
           (cons 91 0)
           (list 10 12.7238 0.7445528)
           (cons 40 0)
           (cons 41 0)
           (cons 42 0)
           (cons 91 0)
           (list 10 12.7238 0.5702072)
           (cons 40 0)
           (cons 41 0)
           (cons 42 0)
           (cons 91 0)
           (list 10 12.567336 0.51768)
           (cons 40 0)
           (cons 41 0)
           (cons 42 0)
           (cons 91 0)
           (list 10 11.762664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.6062 1.0731272)
           (cons 40 0)
           (cons 41 0)
           (cons 42 0)
           (cons 91 0)
           (list 10 11.6062 1.2474728)
           (cons 40 0)
           (cons 41 0)
           (cons 42 0)
           (cons 91 0)
           (list 10 11.762664 1.3)
           (cons 40 0)
           (cons 41 0)
           (cons 42 0)
           (cons 91 0)
           (list 10 12.567336 1.3)
           (cons 40 0)
           (cons 41 0)
           (cons 42 0)
           (cons 91 0)
           (list 10 12.7238 1.2474728)
           (cons 40 0)
           (cons 41 0)
           (cons 42 0)
           (cons 91 0)
           (list 10 12.7238 1.0731272)
           (cons 40 0)
           (cons 41 0)
           (cons 42 0)
           (cons 91 0)
           (list 10 12.567336 1.0206)
           (cons 40 0)
           (cons 41 0)
           (cons 42 0)
           (cons 91 0)
           (list 10 11.762664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.8762 -0.7445528)
           (cons 40 0)
           (cons 41 0)
           (cons 42 0)
           (cons 91 0)
           (list 10 12.8762 -0.5702072)
           (cons 40 0)
           (cons 41 0)
           (cons 42 0)
           (cons 91 0)
           (list 10 13.032664 -0.51768)
           (cons 40 0)
           (cons 41 0)
           (cons 42 0)
           (cons 91 0)
           (list 10 13.837336 -0.51768)
           (cons 40 0)
           (cons 41 0)
           (cons 42 0)
           (cons 91 0)
           (list 10 13.9938 -0.5702072)
           (cons 40 0)
           (cons 41 0)
           (cons 42 0)
           (cons 91 0)
           (list 10 13.9938 -0.7445528)
           (cons 40 0)
           (cons 41 0)
           (cons 42 0)
           (cons 91 0)
           (list 10 13.837336 -0.79708)
           (cons 40 0)
           (cons 41 0)
           (cons 42 0)
           (cons 91 0)
           (list 10 13.032664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.8762 -1.2474728)
           (cons 40 0)
           (cons 41 0)
           (cons 42 0)
           (cons 91 0)
           (list 10 12.8762 -1.0731272)
           (cons 40 0)
           (cons 41 0)
           (cons 42 0)
           (cons 91 0)
           (list 10 13.032664 -1.0206)
           (cons 40 0)
           (cons 41 0)
           (cons 42 0)
           (cons 91 0)
           (list 10 13.837336 -1.0206)
           (cons 40 0)
           (cons 41 0)
           (cons 42 0)
           (cons 91 0)
           (list 10 13.9938 -1.0731272)
           (cons 40 0)
           (cons 41 0)
           (cons 42 0)
           (cons 91 0)
           (list 10 13.9938 -1.2474728)
           (cons 40 0)
           (cons 41 0)
           (cons 42 0)
           (cons 91 0)
           (list 10 13.837336 -1.3)
           (cons 40 0)
           (cons 41 0)
           (cons 42 0)
           (cons 91 0)
           (list 10 13.032664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.8762 0.5702072)
           (cons 40 0)
           (cons 41 0)
           (cons 42 0)
           (cons 91 0)
           (list 10 12.8762 0.7445528)
           (cons 40 0)
           (cons 41 0)
           (cons 42 0)
           (cons 91 0)
           (list 10 13.032664 0.79708)
           (cons 40 0)
           (cons 41 0)
           (cons 42 0)
           (cons 91 0)
           (list 10 13.837336 0.79708)
           (cons 40 0)
           (cons 41 0)
           (cons 42 0)
           (cons 91 0)
           (list 10 13.9938 0.7445528)
           (cons 40 0)
           (cons 41 0)
           (cons 42 0)
           (cons 91 0)
           (list 10 13.9938 0.5702072)
           (cons 40 0)
           (cons 41 0)
           (cons 42 0)
           (cons 91 0)
           (list 10 13.837336 0.51768)
           (cons 40 0)
           (cons 41 0)
           (cons 42 0)
           (cons 91 0)
           (list 10 13.032664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.8762 1.0731272)
           (cons 40 0)
           (cons 41 0)
           (cons 42 0)
           (cons 91 0)
           (list 10 12.8762 1.2474728)
           (cons 40 0)
           (cons 41 0)
           (cons 42 0)
           (cons 91 0)
           (list 10 13.032664 1.3)
           (cons 40 0)
           (cons 41 0)
           (cons 42 0)
           (cons 91 0)
           (list 10 13.837336 1.3)
           (cons 40 0)
           (cons 41 0)
           (cons 42 0)
           (cons 91 0)
           (list 10 13.9938 1.2474728)
           (cons 40 0)
           (cons 41 0)
           (cons 42 0)
           (cons 91 0)
           (list 10 13.9938 1.0731272)
           (cons 40 0)
           (cons 41 0)
           (cons 42 0)
           (cons 91 0)
           (list 10 13.837336 1.0206)
           (cons 40 0)
           (cons 41 0)
           (cons 42 0)
           (cons 91 0)
           (list 10 13.032664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 1.3 0 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 14.3 -1.3 0)
           (cons 50 0)
          )
         )
         (entmake
          (list
           (cons 0 "POINT")
           (cons 100 "AcDbEntity")
           (cons 67 0)
           (cons 8 "0")
           (cons 100 "AcDbPoint")
           (list 10 14.3 1.3 0)
           (cons 50 0)
          )
         )
         (entmake
          (list
           (cons 0 "POINT")
           (cons 100 "AcDbEntity")
           (cons 67 0)
           (cons 8 "0")
           (cons 100 "AcDbPoint")
           (list 10 12.8 1.3 0)
           (cons 50 0)
          )
         )
         (entmake
          (list
           (cons 0 "POINT")
           (cons 100 "AcDbEntity")
           (cons 67 0)
           (cons 8 "0")
           (cons 100 "AcDbPoint")
           (list 10 12.8 -1.3 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 14.3 -1.3)
           (cons 40 0)
           (cons 41 0)
           (cons 42 0)
           (cons 91 0)
           (list 10 14.3 1.3)
           (cons 40 0)
           (cons 41 0)
           (cons 42 0)
           (cons 91 0)
           (list 10 0 1.3)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.6 0.56666667 0)
           (cons 40 0.2)
           (cons 1 "1.300")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 0.23333333 0)
           (cons 40 0.2)
           (cons 1 "1.300")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.1 0)
           (cons 40 0.2)
           (cons 1 "12.800")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-17-TRUCK"))
        (progn
         (entmake)
         (entmake
          (list
           (cons 0 "BLOCK")
           (cons 2 "AB_INF-WB-17-TRUCK")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.2 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.2 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.135 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.135 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.2 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.2 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 6.5 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 6.76263966 -0.26263966 0)
           (list 11 6.76263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.3062 -0.7445528)
           (cons 40 0)
           (cons 41 0)
           (cons 42 0)
           (cons 91 0)
           (list 10 5.3062 -0.5702072)
           (cons 40 0)
           (cons 41 0)
           (cons 42 0)
           (cons 91 0)
           (list 10 5.462664 -0.51768)
           (cons 40 0)
           (cons 41 0)
           (cons 42 0)
           (cons 91 0)
           (list 10 6.267336 -0.51768)
           (cons 40 0)
           (cons 41 0)
           (cons 42 0)
           (cons 91 0)
           (list 10 6.4238 -0.5702072)
           (cons 40 0)
           (cons 41 0)
           (cons 42 0)
           (cons 91 0)
           (list 10 6.4238 -0.7445528)
           (cons 40 0)
           (cons 41 0)
           (cons 42 0)
           (cons 91 0)
           (list 10 6.267336 -0.79708)
           (cons 40 0)
           (cons 41 0)
           (cons 42 0)
           (cons 91 0)
           (list 10 5.462664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.3062 -1.2474728)
           (cons 40 0)
           (cons 41 0)
           (cons 42 0)
           (cons 91 0)
           (list 10 5.3062 -1.0731272)
           (cons 40 0)
           (cons 41 0)
           (cons 42 0)
           (cons 91 0)
           (list 10 5.462664 -1.0206)
           (cons 40 0)
           (cons 41 0)
           (cons 42 0)
           (cons 91 0)
           (list 10 6.267336 -1.0206)
           (cons 40 0)
           (cons 41 0)
           (cons 42 0)
           (cons 91 0)
           (list 10 6.4238 -1.0731272)
           (cons 40 0)
           (cons 41 0)
           (cons 42 0)
           (cons 91 0)
           (list 10 6.4238 -1.2474728)
           (cons 40 0)
           (cons 41 0)
           (cons 42 0)
           (cons 91 0)
           (list 10 6.267336 -1.3)
           (cons 40 0)
           (cons 41 0)
           (cons 42 0)
           (cons 91 0)
           (list 10 5.462664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.3062 0.5702072)
           (cons 40 0)
           (cons 41 0)
           (cons 42 0)
           (cons 91 0)
           (list 10 5.3062 0.7445528)
           (cons 40 0)
           (cons 41 0)
           (cons 42 0)
           (cons 91 0)
           (list 10 5.462664 0.79708)
           (cons 40 0)
           (cons 41 0)
           (cons 42 0)
           (cons 91 0)
           (list 10 6.267336 0.79708)
           (cons 40 0)
           (cons 41 0)
           (cons 42 0)
           (cons 91 0)
           (list 10 6.4238 0.7445528)
           (cons 40 0)
           (cons 41 0)
           (cons 42 0)
           (cons 91 0)
           (list 10 6.4238 0.5702072)
           (cons 40 0)
           (cons 41 0)
           (cons 42 0)
           (cons 91 0)
           (list 10 6.267336 0.51768)
           (cons 40 0)
           (cons 41 0)
           (cons 42 0)
           (cons 91 0)
           (list 10 5.462664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.3062 1.0731272)
           (cons 40 0)
           (cons 41 0)
           (cons 42 0)
           (cons 91 0)
           (list 10 5.3062 1.2474728)
           (cons 40 0)
           (cons 41 0)
           (cons 42 0)
           (cons 91 0)
           (list 10 5.462664 1.3)
           (cons 40 0)
           (cons 41 0)
           (cons 42 0)
           (cons 91 0)
           (list 10 6.267336 1.3)
           (cons 40 0)
           (cons 41 0)
           (cons 42 0)
           (cons 91 0)
           (list 10 6.4238 1.2474728)
           (cons 40 0)
           (cons 41 0)
           (cons 42 0)
           (cons 91 0)
           (list 10 6.4238 1.0731272)
           (cons 40 0)
           (cons 41 0)
           (cons 42 0)
           (cons 91 0)
           (list 10 6.267336 1.0206)
           (cons 40 0)
           (cons 41 0)
           (cons 42 0)
           (cons 91 0)
           (list 10 5.462664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.5762 -0.7445528)
           (cons 40 0)
           (cons 41 0)
           (cons 42 0)
           (cons 91 0)
           (list 10 6.5762 -0.5702072)
           (cons 40 0)
           (cons 41 0)
           (cons 42 0)
           (cons 91 0)
           (list 10 6.732664 -0.51768)
           (cons 40 0)
           (cons 41 0)
           (cons 42 0)
           (cons 91 0)
           (list 10 7.537336 -0.51768)
           (cons 40 0)
           (cons 41 0)
           (cons 42 0)
           (cons 91 0)
           (list 10 7.6938 -0.5702072)
           (cons 40 0)
           (cons 41 0)
           (cons 42 0)
           (cons 91 0)
           (list 10 7.6938 -0.7445528)
           (cons 40 0)
           (cons 41 0)
           (cons 42 0)
           (cons 91 0)
           (list 10 7.537336 -0.79708)
           (cons 40 0)
           (cons 41 0)
           (cons 42 0)
           (cons 91 0)
           (list 10 6.732664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.5762 -1.2474728)
           (cons 40 0)
           (cons 41 0)
           (cons 42 0)
           (cons 91 0)
           (list 10 6.5762 -1.0731272)
           (cons 40 0)
           (cons 41 0)
           (cons 42 0)
           (cons 91 0)
           (list 10 6.732664 -1.0206)
           (cons 40 0)
           (cons 41 0)
           (cons 42 0)
           (cons 91 0)
           (list 10 7.537336 -1.0206)
           (cons 40 0)
           (cons 41 0)
           (cons 42 0)
           (cons 91 0)
           (list 10 7.6938 -1.0731272)
           (cons 40 0)
           (cons 41 0)
           (cons 42 0)
           (cons 91 0)
           (list 10 7.6938 -1.2474728)
           (cons 40 0)
           (cons 41 0)
           (cons 42 0)
           (cons 91 0)
           (list 10 7.537336 -1.3)
           (cons 40 0)
           (cons 41 0)
           (cons 42 0)
           (cons 91 0)
           (list 10 6.732664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.5762 0.5702072)
           (cons 40 0)
           (cons 41 0)
           (cons 42 0)
           (cons 91 0)
           (list 10 6.5762 0.7445528)
           (cons 40 0)
           (cons 41 0)
           (cons 42 0)
           (cons 91 0)
           (list 10 6.732664 0.79708)
           (cons 40 0)
           (cons 41 0)
           (cons 42 0)
           (cons 91 0)
           (list 10 7.537336 0.79708)
           (cons 40 0)
           (cons 41 0)
           (cons 42 0)
           (cons 91 0)
           (list 10 7.6938 0.7445528)
           (cons 40 0)
           (cons 41 0)
           (cons 42 0)
           (cons 91 0)
           (list 10 7.6938 0.5702072)
           (cons 40 0)
           (cons 41 0)
           (cons 42 0)
           (cons 91 0)
           (list 10 7.537336 0.51768)
           (cons 40 0)
           (cons 41 0)
           (cons 42 0)
           (cons 91 0)
           (list 10 6.732664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.5762 1.0731272)
           (cons 40 0)
           (cons 41 0)
           (cons 42 0)
           (cons 91 0)
           (list 10 6.5762 1.2474728)
           (cons 40 0)
           (cons 41 0)
           (cons 42 0)
           (cons 91 0)
           (list 10 6.732664 1.3)
           (cons 40 0)
           (cons 41 0)
           (cons 42 0)
           (cons 91 0)
           (list 10 7.537336 1.3)
           (cons 40 0)
           (cons 41 0)
           (cons 42 0)
           (cons 91 0)
           (list 10 7.6938 1.2474728)
           (cons 40 0)
           (cons 41 0)
           (cons 42 0)
           (cons 91 0)
           (list 10 7.6938 1.0731272)
           (cons 40 0)
           (cons 41 0)
           (cons 42 0)
           (cons 91 0)
           (list 10 7.537336 1.0206)
           (cons 40 0)
           (cons 41 0)
           (cons 42 0)
           (cons 91 0)
           (list 10 6.732664 1.0206)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelLeftM1")
           (list 10 1 -1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM1")
           (list 10 1 1.0206 0)
           (cons 41 1)
           (cons 42 1)
           (cons 43 1)
           (cons 50 0)
           (cons 70 0)
           (cons 71 0)
           (cons 44 0)
           (cons 45 0)
          )
         )
         (entmake
          (list
           (cons 0 "POINT")
           (cons 100 "AcDbEntity")
           (cons 67 0)
           (cons 8 "0")
           (cons 100 "AcDbPoint")
           (list 10 1 0 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 6.5 0 0)
           (cons 50 0)
          )
         )
         (entmake
          (list
           (cons 0 "POINT")
           (cons 100 "AcDbEntity")
           (cons 67 0)
           (cons 8 "0")
           (cons 100 "AcDbPoint")
           (list 10 6.5 1.3 0)
           (cons 50 0)
          )
         )
         (entmake
          (list
           (cons 0 "POINT")
           (cons 100 "AcDbEntity")
           (cons 67 0)
           (cons 8 "0")
           (cons 100 "AcDbPoint")
           (list 10 6.5 -1.3 0)
           (cons 50 0)
          )
         )
         (entmake
          (list
           (cons 0 "POINT")
           (cons 100 "AcDbEntity")
           (cons 67 0)
           (cons 8 "0")
           (cons 100 "AcDbPoint")
           (list 10 1 1.3 0)
           (cons 50 0)
          )
         )
         (entmake
          (list
           (cons 0 "POINT")
           (cons 100 "AcDbEntity")
           (cons 67 0)
           (cons 8 "0")
           (cons 100 "AcDbPoint")
           (list 10 1 -1.3 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 7.135 -1.3)
           (cons 40 0)
           (cons 41 0)
           (cons 42 0)
           (cons 91 0)
           (list 10 7.135 1.3)
           (cons 40 0)
           (cons 41 0)
           (cons 42 0)
           (cons 91 0)
           (list 10 0 1.3)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.3 0.56666667 0)
           (cons 40 0.2)
           (cons 1 "1.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 0.23333333 0)
           (cons 40 0.2)
           (cons 1 "1.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.1 0)
           (cons 40 0.2)
           (cons 1 "6.500")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.43333333 0)
           (cons 40 0.2)
           (cons 1 "6.500")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.76666667 0)
           (cons 40 0.2)
           (cons 1 "24.22")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-15-TRAILER"))
        (progn
         (entmake)
         (entmake
          (list
           (cons 0 "BLOCK")
           (cons 2 "AB_INF-WB-15-TRAILER")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 11.6 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 11.6 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.2062 -0.7445528)
           (cons 40 0)
           (cons 41 0)
           (cons 42 0)
           (cons 91 0)
           (list 10 9.2062 -0.5702072)
           (cons 40 0)
           (cons 41 0)
           (cons 42 0)
           (cons 91 0)
           (list 10 9.362664 -0.51768)
           (cons 40 0)
           (cons 41 0)
           (cons 42 0)
           (cons 91 0)
           (list 10 10.167336 -0.51768)
           (cons 40 0)
           (cons 41 0)
           (cons 42 0)
           (cons 91 0)
           (list 10 10.3238 -0.5702072)
           (cons 40 0)
           (cons 41 0)
           (cons 42 0)
           (cons 91 0)
           (list 10 10.3238 -0.7445528)
           (cons 40 0)
           (cons 41 0)
           (cons 42 0)
           (cons 91 0)
           (list 10 10.167336 -0.79708)
           (cons 40 0)
           (cons 41 0)
           (cons 42 0)
           (cons 91 0)
           (list 10 9.362664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.2062 -1.2474728)
           (cons 40 0)
           (cons 41 0)
           (cons 42 0)
           (cons 91 0)
           (list 10 9.2062 -1.0731272)
           (cons 40 0)
           (cons 41 0)
           (cons 42 0)
           (cons 91 0)
           (list 10 9.362664 -1.0206)
           (cons 40 0)
           (cons 41 0)
           (cons 42 0)
           (cons 91 0)
           (list 10 10.167336 -1.0206)
           (cons 40 0)
           (cons 41 0)
           (cons 42 0)
           (cons 91 0)
           (list 10 10.3238 -1.0731272)
           (cons 40 0)
           (cons 41 0)
           (cons 42 0)
           (cons 91 0)
           (list 10 10.3238 -1.2474728)
           (cons 40 0)
           (cons 41 0)
           (cons 42 0)
           (cons 91 0)
           (list 10 10.167336 -1.3)
           (cons 40 0)
           (cons 41 0)
           (cons 42 0)
           (cons 91 0)
           (list 10 9.362664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.2062 0.5702072)
           (cons 40 0)
           (cons 41 0)
           (cons 42 0)
           (cons 91 0)
           (list 10 9.2062 0.7445528)
           (cons 40 0)
           (cons 41 0)
           (cons 42 0)
           (cons 91 0)
           (list 10 9.362664 0.79708)
           (cons 40 0)
           (cons 41 0)
           (cons 42 0)
           (cons 91 0)
           (list 10 10.167336 0.79708)
           (cons 40 0)
           (cons 41 0)
           (cons 42 0)
           (cons 91 0)
           (list 10 10.3238 0.7445528)
           (cons 40 0)
           (cons 41 0)
           (cons 42 0)
           (cons 91 0)
           (list 10 10.3238 0.5702072)
           (cons 40 0)
           (cons 41 0)
           (cons 42 0)
           (cons 91 0)
           (list 10 10.167336 0.51768)
           (cons 40 0)
           (cons 41 0)
           (cons 42 0)
           (cons 91 0)
           (list 10 9.362664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.2062 1.0731272)
           (cons 40 0)
           (cons 41 0)
           (cons 42 0)
           (cons 91 0)
           (list 10 9.2062 1.2474728)
           (cons 40 0)
           (cons 41 0)
           (cons 42 0)
           (cons 91 0)
           (list 10 9.362664 1.3)
           (cons 40 0)
           (cons 41 0)
           (cons 42 0)
           (cons 91 0)
           (list 10 10.167336 1.3)
           (cons 40 0)
           (cons 41 0)
           (cons 42 0)
           (cons 91 0)
           (list 10 10.3238 1.2474728)
           (cons 40 0)
           (cons 41 0)
           (cons 42 0)
           (cons 91 0)
           (list 10 10.3238 1.0731272)
           (cons 40 0)
           (cons 41 0)
           (cons 42 0)
           (cons 91 0)
           (list 10 10.167336 1.0206)
           (cons 40 0)
           (cons 41 0)
           (cons 42 0)
           (cons 91 0)
           (list 10 9.362664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.4762 -0.7445528)
           (cons 40 0)
           (cons 41 0)
           (cons 42 0)
           (cons 91 0)
           (list 10 10.4762 -0.5702072)
           (cons 40 0)
           (cons 41 0)
           (cons 42 0)
           (cons 91 0)
           (list 10 10.632664 -0.51768)
           (cons 40 0)
           (cons 41 0)
           (cons 42 0)
           (cons 91 0)
           (list 10 11.437336 -0.51768)
           (cons 40 0)
           (cons 41 0)
           (cons 42 0)
           (cons 91 0)
           (list 10 11.5938 -0.5702072)
           (cons 40 0)
           (cons 41 0)
           (cons 42 0)
           (cons 91 0)
           (list 10 11.5938 -0.7445528)
           (cons 40 0)
           (cons 41 0)
           (cons 42 0)
           (cons 91 0)
           (list 10 11.437336 -0.79708)
           (cons 40 0)
           (cons 41 0)
           (cons 42 0)
           (cons 91 0)
           (list 10 10.632664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.4762 -1.2474728)
           (cons 40 0)
           (cons 41 0)
           (cons 42 0)
           (cons 91 0)
           (list 10 10.4762 -1.0731272)
           (cons 40 0)
           (cons 41 0)
           (cons 42 0)
           (cons 91 0)
           (list 10 10.632664 -1.0206)
           (cons 40 0)
           (cons 41 0)
           (cons 42 0)
           (cons 91 0)
           (list 10 11.437336 -1.0206)
           (cons 40 0)
           (cons 41 0)
           (cons 42 0)
           (cons 91 0)
           (list 10 11.5938 -1.0731272)
           (cons 40 0)
           (cons 41 0)
           (cons 42 0)
           (cons 91 0)
           (list 10 11.5938 -1.2474728)
           (cons 40 0)
           (cons 41 0)
           (cons 42 0)
           (cons 91 0)
           (list 10 11.437336 -1.3)
           (cons 40 0)
           (cons 41 0)
           (cons 42 0)
           (cons 91 0)
           (list 10 10.632664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.4762 0.5702072)
           (cons 40 0)
           (cons 41 0)
           (cons 42 0)
           (cons 91 0)
           (list 10 10.4762 0.7445528)
           (cons 40 0)
           (cons 41 0)
           (cons 42 0)
           (cons 91 0)
           (list 10 10.632664 0.79708)
           (cons 40 0)
           (cons 41 0)
           (cons 42 0)
           (cons 91 0)
           (list 10 11.437336 0.79708)
           (cons 40 0)
           (cons 41 0)
           (cons 42 0)
           (cons 91 0)
           (list 10 11.5938 0.7445528)
           (cons 40 0)
           (cons 41 0)
           (cons 42 0)
           (cons 91 0)
           (list 10 11.5938 0.5702072)
           (cons 40 0)
           (cons 41 0)
           (cons 42 0)
           (cons 91 0)
           (list 10 11.437336 0.51768)
           (cons 40 0)
           (cons 41 0)
           (cons 42 0)
           (cons 91 0)
           (list 10 10.632664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.4762 1.0731272)
           (cons 40 0)
           (cons 41 0)
           (cons 42 0)
           (cons 91 0)
           (list 10 10.4762 1.2474728)
           (cons 40 0)
           (cons 41 0)
           (cons 42 0)
           (cons 91 0)
           (list 10 10.632664 1.3)
           (cons 40 0)
           (cons 41 0)
           (cons 42 0)
           (cons 91 0)
           (list 10 11.437336 1.3)
           (cons 40 0)
           (cons 41 0)
           (cons 42 0)
           (cons 91 0)
           (list 10 11.5938 1.2474728)
           (cons 40 0)
           (cons 41 0)
           (cons 42 0)
           (cons 91 0)
           (list 10 11.5938 1.0731272)
           (cons 40 0)
           (cons 41 0)
           (cons 42 0)
           (cons 91 0)
           (list 10 11.437336 1.0206)
           (cons 40 0)
           (cons 41 0)
           (cons 42 0)
           (cons 91 0)
           (list 10 10.632664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 1.3 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 11.6 -1.3)
           (cons 40 0)
           (cons 41 0)
           (cons 42 0)
           (cons 91 0)
           (list 10 11.6 1.3)
           (cons 40 0)
           (cons 41 0)
           (cons 42 0)
           (cons 91 0)
           (list 10 0 1.3)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 11.6 -1.3 0)
           (cons 50 0)
          )
         )
         (entmake
          (list
           (cons 0 "POINT")
           (cons 100 "AcDbEntity")
           (cons 67 0)
           (cons 8 "0")
           (cons 100 "AcDbPoint")
           (list 10 11.6 1.3 0)
           (cons 50 0)
          )
         )
         (entmake
          (list
           (cons 0 "POINT")
           (cons 100 "AcDbEntity")
           (cons 67 0)
           (cons 8 "0")
           (cons 100 "AcDbPoint")
           (list 10 10.4 1.3 0)
           (cons 50 0)
          )
         )
         (entmake
          (list
           (cons 0 "POINT")
           (cons 100 "AcDbEntity")
           (cons 67 0)
           (cons 8 "0")
           (cons 100 "AcDbPoint")
           (list 10 10.4 -1.3 0)
           (cons 50 0)
          )
         )
         (entmake
          (list
           (cons 0 "ATTDEF")
           (cons 100 "AcDbEntity")
           (cons 67 0)
           (cons 8 "0")
           (cons 100 "AcDbText")
           (list 10 0.6 0.56666667 0)
           (cons 40 0.2)
           (cons 1 "1.300")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 0.23333333 0)
           (cons 40 0.2)
           (cons 1 "1.300")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.1 0)
           (cons 40 0.2)
           (cons 1 "10.400")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-15-TRUCK"))
        (progn
         (entmake)
         (entmake
          (list
           (cons 0 "BLOCK")
           (cons 2 "AB_INF-WB-15-TRUCK")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.035 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.035 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 6.4 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 6.66263966 -0.26263966 0)
           (list 11 6.66263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.2062 -0.7445528)
           (cons 40 0)
           (cons 41 0)
           (cons 42 0)
           (cons 91 0)
           (list 10 5.2062 -0.5702072)
           (cons 40 0)
           (cons 41 0)
           (cons 42 0)
           (cons 91 0)
           (list 10 5.362664 -0.51768)
           (cons 40 0)
           (cons 41 0)
           (cons 42 0)
           (cons 91 0)
           (list 10 6.167336 -0.51768)
           (cons 40 0)
           (cons 41 0)
           (cons 42 0)
           (cons 91 0)
           (list 10 6.3238 -0.5702072)
           (cons 40 0)
           (cons 41 0)
           (cons 42 0)
           (cons 91 0)
           (list 10 6.3238 -0.7445528)
           (cons 40 0)
           (cons 41 0)
           (cons 42 0)
           (cons 91 0)
           (list 10 6.167336 -0.79708)
           (cons 40 0)
           (cons 41 0)
           (cons 42 0)
           (cons 91 0)
           (list 10 5.362664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.2062 -1.2474728)
           (cons 40 0)
           (cons 41 0)
           (cons 42 0)
           (cons 91 0)
           (list 10 5.2062 -1.0731272)
           (cons 40 0)
           (cons 41 0)
           (cons 42 0)
           (cons 91 0)
           (list 10 5.362664 -1.0206)
           (cons 40 0)
           (cons 41 0)
           (cons 42 0)
           (cons 91 0)
           (list 10 6.167336 -1.0206)
           (cons 40 0)
           (cons 41 0)
           (cons 42 0)
           (cons 91 0)
           (list 10 6.3238 -1.0731272)
           (cons 40 0)
           (cons 41 0)
           (cons 42 0)
           (cons 91 0)
           (list 10 6.3238 -1.2474728)
           (cons 40 0)
           (cons 41 0)
           (cons 42 0)
           (cons 91 0)
           (list 10 6.167336 -1.3)
           (cons 40 0)
           (cons 41 0)
           (cons 42 0)
           (cons 91 0)
           (list 10 5.362664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.2062 0.5702072)
           (cons 40 0)
           (cons 41 0)
           (cons 42 0)
           (cons 91 0)
           (list 10 5.2062 0.7445528)
           (cons 40 0)
           (cons 41 0)
           (cons 42 0)
           (cons 91 0)
           (list 10 5.362664 0.79708)
           (cons 40 0)
           (cons 41 0)
           (cons 42 0)
           (cons 91 0)
           (list 10 6.167336 0.79708)
           (cons 40 0)
           (cons 41 0)
           (cons 42 0)
           (cons 91 0)
           (list 10 6.3238 0.7445528)
           (cons 40 0)
           (cons 41 0)
           (cons 42 0)
           (cons 91 0)
           (list 10 6.3238 0.5702072)
           (cons 40 0)
           (cons 41 0)
           (cons 42 0)
           (cons 91 0)
           (list 10 6.167336 0.51768)
           (cons 40 0)
           (cons 41 0)
           (cons 42 0)
           (cons 91 0)
           (list 10 5.362664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.2062 1.0731272)
           (cons 40 0)
           (cons 41 0)
           (cons 42 0)
           (cons 91 0)
           (list 10 5.2062 1.2474728)
           (cons 40 0)
           (cons 41 0)
           (cons 42 0)
           (cons 91 0)
           (list 10 5.362664 1.3)
           (cons 40 0)
           (cons 41 0)
           (cons 42 0)
           (cons 91 0)
           (list 10 6.167336 1.3)
           (cons 40 0)
           (cons 41 0)
           (cons 42 0)
           (cons 91 0)
           (list 10 6.3238 1.2474728)
           (cons 40 0)
           (cons 41 0)
           (cons 42 0)
           (cons 91 0)
           (list 10 6.3238 1.0731272)
           (cons 40 0)
           (cons 41 0)
           (cons 42 0)
           (cons 91 0)
           (list 10 6.167336 1.0206)
           (cons 40 0)
           (cons 41 0)
           (cons 42 0)
           (cons 91 0)
           (list 10 5.362664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.4762 -0.7445528)
           (cons 40 0)
           (cons 41 0)
           (cons 42 0)
           (cons 91 0)
           (list 10 6.4762 -0.5702072)
           (cons 40 0)
           (cons 41 0)
           (cons 42 0)
           (cons 91 0)
           (list 10 6.632664 -0.51768)
           (cons 40 0)
           (cons 41 0)
           (cons 42 0)
           (cons 91 0)
           (list 10 7.437336 -0.51768)
           (cons 40 0)
           (cons 41 0)
           (cons 42 0)
           (cons 91 0)
           (list 10 7.5938 -0.5702072)
           (cons 40 0)
           (cons 41 0)
           (cons 42 0)
           (cons 91 0)
           (list 10 7.5938 -0.7445528)
           (cons 40 0)
           (cons 41 0)
           (cons 42 0)
           (cons 91 0)
           (list 10 7.437336 -0.79708)
           (cons 40 0)
           (cons 41 0)
           (cons 42 0)
           (cons 91 0)
           (list 10 6.632664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.4762 -1.2474728)
           (cons 40 0)
           (cons 41 0)
           (cons 42 0)
           (cons 91 0)
           (list 10 6.4762 -1.0731272)
           (cons 40 0)
           (cons 41 0)
           (cons 42 0)
           (cons 91 0)
           (list 10 6.632664 -1.0206)
           (cons 40 0)
           (cons 41 0)
           (cons 42 0)
           (cons 91 0)
           (list 10 7.437336 -1.0206)
           (cons 40 0)
           (cons 41 0)
           (cons 42 0)
           (cons 91 0)
           (list 10 7.5938 -1.0731272)
           (cons 40 0)
           (cons 41 0)
           (cons 42 0)
           (cons 91 0)
           (list 10 7.5938 -1.2474728)
           (cons 40 0)
           (cons 41 0)
           (cons 42 0)
           (cons 91 0)
           (list 10 7.437336 -1.3)
           (cons 40 0)
           (cons 41 0)
           (cons 42 0)
           (cons 91 0)
           (list 10 6.632664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.4762 0.5702072)
           (cons 40 0)
           (cons 41 0)
           (cons 42 0)
           (cons 91 0)
           (list 10 6.4762 0.7445528)
           (cons 40 0)
           (cons 41 0)
           (cons 42 0)
           (cons 91 0)
           (list 10 6.632664 0.79708)
           (cons 40 0)
           (cons 41 0)
           (cons 42 0)
           (cons 91 0)
           (list 10 7.437336 0.79708)
           (cons 40 0)
           (cons 41 0)
           (cons 42 0)
           (cons 91 0)
           (list 10 7.5938 0.7445528)
           (cons 40 0)
           (cons 41 0)
           (cons 42 0)
           (cons 91 0)
           (list 10 7.5938 0.5702072)
           (cons 40 0)
           (cons 41 0)
           (cons 42 0)
           (cons 91 0)
           (list 10 7.437336 0.51768)
           (cons 40 0)
           (cons 41 0)
           (cons 42 0)
           (cons 91 0)
           (list 10 6.632664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.4762 1.0731272)
           (cons 40 0)
           (cons 41 0)
           (cons 42 0)
           (cons 91 0)
           (list 10 6.4762 1.2474728)
           (cons 40 0)
           (cons 41 0)
           (cons 42 0)
           (cons 91 0)
           (list 10 6.632664 1.3)
           (cons 40 0)
           (cons 41 0)
           (cons 42 0)
           (cons 91 0)
           (list 10 7.437336 1.3)
           (cons 40 0)
           (cons 41 0)
           (cons 42 0)
           (cons 91 0)
           (list 10 7.5938 1.2474728)
           (cons 40 0)
           (cons 41 0)
           (cons 42 0)
           (cons 91 0)
           (list 10 7.5938 1.0731272)
           (cons 40 0)
           (cons 41 0)
           (cons 42 0)
           (cons 91 0)
           (list 10 7.437336 1.0206)
           (cons 40 0)
           (cons 41 0)
           (cons 42 0)
           (cons 91 0)
           (list 10 6.632664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0.9 0 0)
           (cons 50 0)
          )
         )
         (entmake
          (list
           (cons 0 "INSERT")
           (cons 100 "AcDbEntity")
           (cons 67 0)
           (cons 8 "0")
           (cons 100 "AcDbBlockReference")
           (cons 2 "WheelRightM1")
           (list 10 0.9 -1.3 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM1")
           (list 10 0.9 1.3 0)
           (cons 41 1)
           (cons 42 1)
           (cons 43 1)
           (cons 50 0)
           (cons 70 0)
           (cons 71 0)
           (cons 44 0)
           (cons 45 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 7.035 -1.3)
           (cons 40 0)
           (cons 41 0)
           (cons 42 0)
           (cons 91 0)
           (list 10 7.035 1.3)
           (cons 40 0)
           (cons 41 0)
           (cons 42 0)
           (cons 91 0)
           (list 10 0 1.3)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0.9 1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 6.4 1.3 0)
           (cons 50 0)
          )
         )
         (entmake
          (list
           (cons 0 "POINT")
           (cons 100 "AcDbEntity")
           (cons 67 0)
           (cons 8 "0")
           (cons 100 "AcDbPoint")
           (list 10 0.9 -1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 6.4 -1.3 0)
           (cons 50 0)
          )
         )
         (entmake
          (list
           (cons 0 "POINT")
           (cons 100 "AcDbEntity")
           (cons 67 0)
           (cons 8 "0")
           (cons 100 "AcDbPoint")
           (list 10 6.4 0 0)
           (cons 50 0)
          )
         )
         (entmake
          (list
           (cons 0 "ATTDEF")
           (cons 100 "AcDbEntity")
           (cons 67 0)
           (cons 8 "0")
           (cons 100 "AcDbText")
           (list 10 0.2 0.56666667 0)
           (cons 40 0.2)
           (cons 1 "0.900")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.2 0.23333333 0)
           (cons 40 0.2)
           (cons 1 "0.900")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.2 -0.1 0)
           (cons 40 0.2)
           (cons 1 "6.400")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.2 -0.43333333 0)
           (cons 40 0.2)
           (cons 1 "6.400")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.2 -0.76666667 0)
           (cons 40 0.2)
           (cons 1 "26.06")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-12-TRAILER"))
        (progn
         (entmake)
         (entmake
          (list
           (cons 0 "BLOCK")
           (cons 2 "AB_INF-WB-12-TRAILER")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 10.6 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 10.6 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.0412 -0.7445528)
           (cons 40 0)
           (cons 41 0)
           (cons 42 0)
           (cons 91 0)
           (list 10 7.0412 -0.5702072)
           (cons 40 0)
           (cons 41 0)
           (cons 42 0)
           (cons 91 0)
           (list 10 7.197664 -0.51768)
           (cons 40 0)
           (cons 41 0)
           (cons 42 0)
           (cons 91 0)
           (list 10 8.002336 -0.51768)
           (cons 40 0)
           (cons 41 0)
           (cons 42 0)
           (cons 91 0)
           (list 10 8.1588 -0.5702072)
           (cons 40 0)
           (cons 41 0)
           (cons 42 0)
           (cons 91 0)
           (list 10 8.1588 -0.7445528)
           (cons 40 0)
           (cons 41 0)
           (cons 42 0)
           (cons 91 0)
           (list 10 8.002336 -0.79708)
           (cons 40 0)
           (cons 41 0)
           (cons 42 0)
           (cons 91 0)
           (list 10 7.197664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.0412 -1.2474728)
           (cons 40 0)
           (cons 41 0)
           (cons 42 0)
           (cons 91 0)
           (list 10 7.0412 -1.0731272)
           (cons 40 0)
           (cons 41 0)
           (cons 42 0)
           (cons 91 0)
           (list 10 7.197664 -1.0206)
           (cons 40 0)
           (cons 41 0)
           (cons 42 0)
           (cons 91 0)
           (list 10 8.002336 -1.0206)
           (cons 40 0)
           (cons 41 0)
           (cons 42 0)
           (cons 91 0)
           (list 10 8.1588 -1.0731272)
           (cons 40 0)
           (cons 41 0)
           (cons 42 0)
           (cons 91 0)
           (list 10 8.1588 -1.2474728)
           (cons 40 0)
           (cons 41 0)
           (cons 42 0)
           (cons 91 0)
           (list 10 8.002336 -1.3)
           (cons 40 0)
           (cons 41 0)
           (cons 42 0)
           (cons 91 0)
           (list 10 7.197664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.0412 0.5702072)
           (cons 40 0)
           (cons 41 0)
           (cons 42 0)
           (cons 91 0)
           (list 10 7.0412 0.7445528)
           (cons 40 0)
           (cons 41 0)
           (cons 42 0)
           (cons 91 0)
           (list 10 7.197664 0.79708)
           (cons 40 0)
           (cons 41 0)
           (cons 42 0)
           (cons 91 0)
           (list 10 8.002336 0.79708)
           (cons 40 0)
           (cons 41 0)
           (cons 42 0)
           (cons 91 0)
           (list 10 8.1588 0.7445528)
           (cons 40 0)
           (cons 41 0)
           (cons 42 0)
           (cons 91 0)
           (list 10 8.1588 0.5702072)
           (cons 40 0)
           (cons 41 0)
           (cons 42 0)
           (cons 91 0)
           (list 10 8.002336 0.51768)
           (cons 40 0)
           (cons 41 0)
           (cons 42 0)
           (cons 91 0)
           (list 10 7.197664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.0412 1.0731272)
           (cons 40 0)
           (cons 41 0)
           (cons 42 0)
           (cons 91 0)
           (list 10 7.0412 1.2474728)
           (cons 40 0)
           (cons 41 0)
           (cons 42 0)
           (cons 91 0)
           (list 10 7.197664 1.3)
           (cons 40 0)
           (cons 41 0)
           (cons 42 0)
           (cons 91 0)
           (list 10 8.002336 1.3)
           (cons 40 0)
           (cons 41 0)
           (cons 42 0)
           (cons 91 0)
           (list 10 8.1588 1.2474728)
           (cons 40 0)
           (cons 41 0)
           (cons 42 0)
           (cons 91 0)
           (list 10 8.1588 1.0731272)
           (cons 40 0)
           (cons 41 0)
           (cons 42 0)
           (cons 91 0)
           (list 10 8.002336 1.0206)
           (cons 40 0)
           (cons 41 0)
           (cons 42 0)
           (cons 91 0)
           (list 10 7.197664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.2412 -0.7445528)
           (cons 40 0)
           (cons 41 0)
           (cons 42 0)
           (cons 91 0)
           (list 10 8.2412 -0.5702072)
           (cons 40 0)
           (cons 41 0)
           (cons 42 0)
           (cons 91 0)
           (list 10 8.397664 -0.51768)
           (cons 40 0)
           (cons 41 0)
           (cons 42 0)
           (cons 91 0)
           (list 10 9.202336 -0.51768)
           (cons 40 0)
           (cons 41 0)
           (cons 42 0)
           (cons 91 0)
           (list 10 9.3588 -0.5702072)
           (cons 40 0)
           (cons 41 0)
           (cons 42 0)
           (cons 91 0)
           (list 10 9.3588 -0.7445528)
           (cons 40 0)
           (cons 41 0)
           (cons 42 0)
           (cons 91 0)
           (list 10 9.202336 -0.79708)
           (cons 40 0)
           (cons 41 0)
           (cons 42 0)
           (cons 91 0)
           (list 10 8.397664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.2412 -1.2474728)
           (cons 40 0)
           (cons 41 0)
           (cons 42 0)
           (cons 91 0)
           (list 10 8.2412 -1.0731272)
           (cons 40 0)
           (cons 41 0)
           (cons 42 0)
           (cons 91 0)
           (list 10 8.397664 -1.0206)
           (cons 40 0)
           (cons 41 0)
           (cons 42 0)
           (cons 91 0)
           (list 10 9.202336 -1.0206)
           (cons 40 0)
           (cons 41 0)
           (cons 42 0)
           (cons 91 0)
           (list 10 9.3588 -1.0731272)
           (cons 40 0)
           (cons 41 0)
           (cons 42 0)
           (cons 91 0)
           (list 10 9.3588 -1.2474728)
           (cons 40 0)
           (cons 41 0)
           (cons 42 0)
           (cons 91 0)
           (list 10 9.202336 -1.3)
           (cons 40 0)
           (cons 41 0)
           (cons 42 0)
           (cons 91 0)
           (list 10 8.397664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.2412 0.5702072)
           (cons 40 0)
           (cons 41 0)
           (cons 42 0)
           (cons 91 0)
           (list 10 8.2412 0.7445528)
           (cons 40 0)
           (cons 41 0)
           (cons 42 0)
           (cons 91 0)
           (list 10 8.397664 0.79708)
           (cons 40 0)
           (cons 41 0)
           (cons 42 0)
           (cons 91 0)
           (list 10 9.202336 0.79708)
           (cons 40 0)
           (cons 41 0)
           (cons 42 0)
           (cons 91 0)
           (list 10 9.3588 0.7445528)
           (cons 40 0)
           (cons 41 0)
           (cons 42 0)
           (cons 91 0)
           (list 10 9.3588 0.5702072)
           (cons 40 0)
           (cons 41 0)
           (cons 42 0)
           (cons 91 0)
           (list 10 9.202336 0.51768)
           (cons 40 0)
           (cons 41 0)
           (cons 42 0)
           (cons 91 0)
           (list 10 8.397664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.2412 1.0731272)
           (cons 40 0)
           (cons 41 0)
           (cons 42 0)
           (cons 91 0)
           (list 10 8.2412 1.2474728)
           (cons 40 0)
           (cons 41 0)
           (cons 42 0)
           (cons 91 0)
           (list 10 8.397664 1.3)
           (cons 40 0)
           (cons 41 0)
           (cons 42 0)
           (cons 91 0)
           (list 10 9.202336 1.3)
           (cons 40 0)
           (cons 41 0)
           (cons 42 0)
           (cons 91 0)
           (list 10 9.3588 1.2474728)
           (cons 40 0)
           (cons 41 0)
           (cons 42 0)
           (cons 91 0)
           (list 10 9.3588 1.0731272)
           (cons 40 0)
           (cons 41 0)
           (cons 42 0)
           (cons 91 0)
           (list 10 9.202336 1.0206)
           (cons 40 0)
           (cons 41 0)
           (cons 42 0)
           (cons 91 0)
           (list 10 8.397664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0.6 0 0)
           (cons 50 0)
          )
         )
         (entmake
          (list
           (cons 0 "POINT")
           (cons 100 "AcDbEntity")
           (cons 67 0)
           (cons 8 "0")
           (cons 100 "AcDbPoint")
           (list 10 8.2 1.3 0)
           (cons 50 0)
          )
         )
         (entmake
          (list
           (cons 0 "POINT")
           (cons 100 "AcDbEntity")
           (cons 67 0)
           (cons 8 "0")
           (cons 100 "AcDbPoint")
           (list 10 8.2 -1.3 0)
           (cons 50 0)
          )
         )
         (entmake
          (list
           (cons 0 "POINT")
           (cons 100 "AcDbEntity")
           (cons 67 0)
           (cons 8 "0")
           (cons 100 "AcDbPoint")
           (list 10 10.6 -1.3 0)
           (cons 50 0)
          )
         )
         (entmake
          (list
           (cons 0 "POINT")
           (cons 100 "AcDbEntity")
           (cons 67 0)
           (cons 8 "0")
           (cons 100 "AcDbPoint")
           (list 10 10.6 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 10.6 -1.3)
           (cons 40 0)
           (cons 41 0)
           (cons 42 0)
           (cons 91 0)
           (list 10 10.6 1.3)
           (cons 40 0)
           (cons 41 0)
           (cons 42 0)
           (cons 91 0)
           (list 10 0 1.3)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 -0.1 0.56666667 0)
           (cons 40 0.2)
           (cons 1 "0.600")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 0.23333333 0)
           (cons 40 0.2)
           (cons 1 "0.600")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 -0.1 0)
           (cons 40 0.2)
           (cons 1 "8.200")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.1 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-WB-12-TRUCK"))
        (progn
         (entmake)
         (entmake
          (list
           (cons 0 "BLOCK")
           (cons 2 "AB_INF-WB-12-TRUCK")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.2 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.2 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 5.2 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 5.46263966 -0.26263966 0)
           (list 11 5.46263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.6412 -0.7445528)
           (cons 40 0)
           (cons 41 0)
           (cons 42 0)
           (cons 91 0)
           (list 10 4.6412 -0.5702072)
           (cons 40 0)
           (cons 41 0)
           (cons 42 0)
           (cons 91 0)
           (list 10 4.797664 -0.51768)
           (cons 40 0)
           (cons 41 0)
           (cons 42 0)
           (cons 91 0)
           (list 10 5.602336 -0.51768)
           (cons 40 0)
           (cons 41 0)
           (cons 42 0)
           (cons 91 0)
           (list 10 5.7588 -0.5702072)
           (cons 40 0)
           (cons 41 0)
           (cons 42 0)
           (cons 91 0)
           (list 10 5.7588 -0.7445528)
           (cons 40 0)
           (cons 41 0)
           (cons 42 0)
           (cons 91 0)
           (list 10 5.602336 -0.79708)
           (cons 40 0)
           (cons 41 0)
           (cons 42 0)
           (cons 91 0)
           (list 10 4.797664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.6412 -1.2474728)
           (cons 40 0)
           (cons 41 0)
           (cons 42 0)
           (cons 91 0)
           (list 10 4.6412 -1.0731272)
           (cons 40 0)
           (cons 41 0)
           (cons 42 0)
           (cons 91 0)
           (list 10 4.797664 -1.0206)
           (cons 40 0)
           (cons 41 0)
           (cons 42 0)
           (cons 91 0)
           (list 10 5.602336 -1.0206)
           (cons 40 0)
           (cons 41 0)
           (cons 42 0)
           (cons 91 0)
           (list 10 5.7588 -1.0731272)
           (cons 40 0)
           (cons 41 0)
           (cons 42 0)
           (cons 91 0)
           (list 10 5.7588 -1.2474728)
           (cons 40 0)
           (cons 41 0)
           (cons 42 0)
           (cons 91 0)
           (list 10 5.602336 -1.3)
           (cons 40 0)
           (cons 41 0)
           (cons 42 0)
           (cons 91 0)
           (list 10 4.797664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.6412 0.5702072)
           (cons 40 0)
           (cons 41 0)
           (cons 42 0)
           (cons 91 0)
           (list 10 4.6412 0.7445528)
           (cons 40 0)
           (cons 41 0)
           (cons 42 0)
           (cons 91 0)
           (list 10 4.797664 0.79708)
           (cons 40 0)
           (cons 41 0)
           (cons 42 0)
           (cons 91 0)
           (list 10 5.602336 0.79708)
           (cons 40 0)
           (cons 41 0)
           (cons 42 0)
           (cons 91 0)
           (list 10 5.7588 0.7445528)
           (cons 40 0)
           (cons 41 0)
           (cons 42 0)
           (cons 91 0)
           (list 10 5.7588 0.5702072)
           (cons 40 0)
           (cons 41 0)
           (cons 42 0)
           (cons 91 0)
           (list 10 5.602336 0.51768)
           (cons 40 0)
           (cons 41 0)
           (cons 42 0)
           (cons 91 0)
           (list 10 4.797664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.6412 1.0731272)
           (cons 40 0)
           (cons 41 0)
           (cons 42 0)
           (cons 91 0)
           (list 10 4.6412 1.2474728)
           (cons 40 0)
           (cons 41 0)
           (cons 42 0)
           (cons 91 0)
           (list 10 4.797664 1.3)
           (cons 40 0)
           (cons 41 0)
           (cons 42 0)
           (cons 91 0)
           (list 10 5.602336 1.3)
           (cons 40 0)
           (cons 41 0)
           (cons 42 0)
           (cons 91 0)
           (list 10 5.7588 1.2474728)
           (cons 40 0)
           (cons 41 0)
           (cons 42 0)
           (cons 91 0)
           (list 10 5.7588 1.0731272)
           (cons 40 0)
           (cons 41 0)
           (cons 42 0)
           (cons 91 0)
           (list 10 5.602336 1.0206)
           (cons 40 0)
           (cons 41 0)
           (cons 42 0)
           (cons 91 0)
           (list 10 4.797664 1.0206)
           (cons 40 0)
           (cons 41 0)
           (cons 42 0)
           (cons 91 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 5.2 -1.3)
           (cons 40 0)
           (cons 41 0)
           (cons 42 0)
           (cons 91 0)
           (list 10 5.2 1.3)
           (cons 40 0)
           (cons 41 0)
           (cons 42 0)
           (cons 91 0)
           (list 10 0 1.3)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 5.2 0 0)
           (cons 50 0)
          )
         )
         (entmake
          (list
           (cons 0 "POINT")
           (cons 100 "AcDbEntity")
           (cons 67 0)
           (cons 8 "0")
           (cons 100 "AcDbPoint")
           (list 10 5.2 1.3 0)
           (cons 50 0)
          )
         )
         (entmake
          (list
           (cons 0 "POINT")
           (cons 100 "AcDbEntity")
           (cons 67 0)
           (cons 8 "0")
           (cons 100 "AcDbPoint")
           (list 10 5.2 -1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 1.2 0 0)
           (cons 50 0)
          )
         )
         (entmake
          (list
           (cons 0 "INSERT")
           (cons 100 "AcDbEntity")
           (cons 67 0)
           (cons 8 "0")
           (cons 100 "AcDbBlockReference")
           (cons 2 "WheelRightM1")
           (list 10 1.2 1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM1")
           (list 10 1.2 -1.0206 0)
           (cons 41 1)
           (cons 42 1)
           (cons 43 1)
           (cons 50 0)
           (cons 70 0)
           (cons 71 0)
           (cons 44 0)
           (cons 45 0)
          )
         )
         (entmake
          (list
           (cons 0 "POINT")
           (cons 100 "AcDbEntity")
           (cons 67 0)
           (cons 8 "0")
           (cons 100 "AcDbPoint")
           (list 10 1.2 1.3 0)
           (cons 50 0)
          )
         )
         (entmake
          (list
           (cons 0 "POINT")
           (cons 100 "AcDbEntity")
           (cons 67 0)
           (cons 8 "0")
           (cons 100 "AcDbPoint")
           (list 10 1.2 -1.3 0)
           (cons 50 0)
          )
         )
         (entmake
          (list
           (cons 0 "ATTDEF")
           (cons 100 "AcDbEntity")
           (cons 67 0)
           (cons 8 "0")
           (cons 100 "AcDbText")
           (list 10 0.5 0.56666667 0)
           (cons 40 0.2)
           (cons 1 "1.200")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.5 0.23333333 0)
           (cons 40 0.2)
           (cons 1 "1.200")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.5 -0.1 0)
           (cons 40 0.2)
           (cons 1 "5.200")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.5 -0.43333333 0)
           (cons 40 0.2)
           (cons 1 "5.200")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.5 -0.76666667 0)
           (cons 40 0.2)
           (cons 1 "21.36")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-SU9"))
        (progn
         (entmake)
         (entmake
          (list
           (cons 0 "BLOCK")
           (cons 2 "AB_INF-SU9")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 9.1 -1.3)
           (cons 40 0)
           (cons 41 0)
           (cons 42 0)
           (cons 91 0)
           (list 10 9.1 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.1 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.1 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.792 -0.795048)
           (cons 40 0)
           (cons 41 0)
           (cons 42 0)
           (cons 91 0)
           (list 10 6.792 -0.636552)
           (cons 40 0)
           (cons 41 0)
           (cons 42 0)
           (cons 91 0)
           (list 10 6.93424 -0.5888)
           (cons 40 0)
           (cons 41 0)
           (cons 42 0)
           (cons 91 0)
           (list 10 7.66576 -0.5888)
           (cons 40 0)
           (cons 41 0)
           (cons 42 0)
           (cons 91 0)
           (list 10 7.808 -0.636552)
           (cons 40 0)
           (cons 41 0)
           (cons 42 0)
           (cons 91 0)
           (list 10 7.808 -0.795048)
           (cons 40 0)
           (cons 41 0)
           (cons 42 0)
           (cons 91 0)
           (list 10 7.66576 -0.8428)
           (cons 40 0)
           (cons 41 0)
           (cons 42 0)
           (cons 91 0)
           (list 10 6.93424 -0.8428)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.792 -1.252248)
           (cons 40 0)
           (cons 41 0)
           (cons 42 0)
           (cons 91 0)
           (list 10 6.792 -1.093752)
           (cons 40 0)
           (cons 41 0)
           (cons 42 0)
           (cons 91 0)
           (list 10 6.93424 -1.046)
           (cons 40 0)
           (cons 41 0)
           (cons 42 0)
           (cons 91 0)
           (list 10 7.66576 -1.046)
           (cons 40 0)
           (cons 41 0)
           (cons 42 0)
           (cons 91 0)
           (list 10 7.808 -1.093752)
           (cons 40 0)
           (cons 41 0)
           (cons 42 0)
           (cons 91 0)
           (list 10 7.808 -1.252248)
           (cons 40 0)
           (cons 41 0)
           (cons 42 0)
           (cons 91 0)
           (list 10 7.66576 -1.3)
           (cons 40 0)
           (cons 41 0)
           (cons 42 0)
           (cons 91 0)
           (list 10 6.93424 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.792 0.636552)
           (cons 40 0)
           (cons 41 0)
           (cons 42 0)
           (cons 91 0)
           (list 10 6.792 0.795048)
           (cons 40 0)
           (cons 41 0)
           (cons 42 0)
           (cons 91 0)
           (list 10 6.93424 0.8428)
           (cons 40 0)
           (cons 41 0)
           (cons 42 0)
           (cons 91 0)
           (list 10 7.66576 0.8428)
           (cons 40 0)
           (cons 41 0)
           (cons 42 0)
           (cons 91 0)
           (list 10 7.808 0.795048)
           (cons 40 0)
           (cons 41 0)
           (cons 42 0)
           (cons 91 0)
           (list 10 7.808 0.636552)
           (cons 40 0)
           (cons 41 0)
           (cons 42 0)
           (cons 91 0)
           (list 10 7.66576 0.5888)
           (cons 40 0)
           (cons 41 0)
           (cons 42 0)
           (cons 91 0)
           (list 10 6.93424 0.5888)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.792 1.093752)
           (cons 40 0)
           (cons 41 0)
           (cons 42 0)
           (cons 91 0)
           (list 10 6.792 1.252248)
           (cons 40 0)
           (cons 41 0)
           (cons 42 0)
           (cons 91 0)
           (list 10 6.93424 1.3)
           (cons 40 0)
           (cons 41 0)
           (cons 42 0)
           (cons 91 0)
           (list 10 7.66576 1.3)
           (cons 40 0)
           (cons 41 0)
           (cons 42 0)
           (cons 91 0)
           (list 10 7.808 1.252248)
           (cons 40 0)
           (cons 41 0)
           (cons 42 0)
           (cons 91 0)
           (list 10 7.808 1.093752)
           (cons 40 0)
           (cons 41 0)
           (cons 42 0)
           (cons 91 0)
           (list 10 7.66576 1.046)
           (cons 40 0)
           (cons 41 0)
           (cons 42 0)
           (cons 91 0)
           (list 10 6.93424 1.046)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelRightM2")
           (list 10 1.2 1.046 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM2")
           (list 10 1.2 -1.046 0)
           (cons 41 1)
           (cons 42 1)
           (cons 43 1)
           (cons 50 0)
           (cons 70 0)
           (cons 71 0)
           (cons 44 0)
           (cons 45 0)
          )
         )
         (entmake
          (list
           (cons 0 "POINT")
           (cons 100 "AcDbEntity")
           (cons 67 0)
           (cons 8 "0")
           (cons 100 "AcDbPoint")
           (list 10 1.2 0 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 9.1 1.3 0)
           (cons 50 0)
          )
         )
         (entmake
          (list
           (cons 0 "POINT")
           (cons 100 "AcDbEntity")
           (cons 67 0)
           (cons 8 "0")
           (cons 100 "AcDbPoint")
           (list 10 9.1 -1.3 0)
           (cons 50 0)
          )
         )
         (entmake
          (list
           (cons 0 "POINT")
           (cons 100 "AcDbEntity")
           (cons 67 0)
           (cons 8 "0")
           (cons 100 "AcDbPoint")
           (list 10 1.2 -1.3 0)
           (cons 50 0)
          )
         )
         (entmake
          (list
           (cons 0 "POINT")
           (cons 100 "AcDbEntity")
           (cons 67 0)
           (cons 8 "0")
           (cons 100 "AcDbPoint")
           (list 10 1.2 1.3 0)
           (cons 50 0)
          )
         )
         (entmake
          (list
           (cons 0 "POINT")
           (cons 100 "AcDbEntity")
           (cons 67 0)
           (cons 8 "0")
           (cons 100 "AcDbPoint")
           (list 10 7.3 1.3 0)
           (cons 50 0)
          )
         )
         (entmake
          (list
           (cons 0 "POINT")
           (cons 100 "AcDbEntity")
           (cons 67 0)
           (cons 8 "0")
           (cons 100 "AcDbPoint")
           (list 10 7.3 -1.3 0)
           (cons 50 0)
          )
         )
         (entmake
          (list
           (cons 0 "ATTDEF")
           (cons 100 "AcDbEntity")
           (cons 67 0)
           (cons 8 "0")
           (cons 100 "AcDbText")
           (list 10 0.5 0.56666667 0)
           (cons 40 0.2)
           (cons 1 "1.200")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.5 0.23333333 0)
           (cons 40 0.2)
           (cons 1 "1.200")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.5 -0.1 0)
           (cons 40 0.2)
           (cons 1 "7.300")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.5 -0.43333333 0)
           (cons 40 0.2)
           (cons 1 "5.800")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.5 -0.76666667 0)
           (cons 40 0.2)
           (cons 1 "31.50")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-CAMPER"))
        (progn
         (entmake)
         (entmake
          (list
           (cons 0 "BLOCK")
           (cons 2 "AB_INF-CAMPER")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 5)
           (cons 70 129)
           (cons 43 0)
           (cons 38 0)
           (cons 39 0)
           (list 10 0 0)
           (cons 40 0)
           (cons 41 0)
           (cons 42 0)
           (cons 91 0)
           (list 10 0.9 -1.2)
           (cons 40 0)
           (cons 41 0)
           (cons 42 0)
           (cons 91 0)
           (list 10 9.1 -1.2)
           (cons 40 0)
           (cons 41 0)
           (cons 42 0)
           (cons 91 0)
           (list 10 9.1 1.2)
           (cons 40 0)
           (cons 41 0)
           (cons 42 0)
           (cons 91 0)
           (list 10 0.9 1.2)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0.9 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.1 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.1 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0.9 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0.9 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0.9 -1.2 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 0.9 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.16)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.63 -1.170155)
           (cons 40 0)
           (cons 41 0)
           (cons 42 0)
           (cons 91 0)
           (list 10 4.63 -1.071095)
           (cons 40 0)
           (cons 41 0)
           (cons 42 0)
           (cons 91 0)
           (list 10 4.7189 -1.04125)
           (cons 40 0)
           (cons 41 0)
           (cons 42 0)
           (cons 91 0)
           (list 10 5.1761 -1.04125)
           (cons 40 0)
           (cons 41 0)
           (cons 42 0)
           (cons 91 0)
           (list 10 5.265 -1.071095)
           (cons 40 0)
           (cons 41 0)
           (cons 42 0)
           (cons 91 0)
           (list 10 5.265 -1.170155)
           (cons 40 0)
           (cons 41 0)
           (cons 42 0)
           (cons 91 0)
           (list 10 5.1761 -1.2)
           (cons 40 0)
           (cons 41 0)
           (cons 42 0)
           (cons 91 0)
           (list 10 4.7189 -1.2)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.63 1.071095)
           (cons 40 0)
           (cons 41 0)
           (cons 42 0)
           (cons 91 0)
           (list 10 4.63 1.170155)
           (cons 40 0)
           (cons 41 0)
           (cons 42 0)
           (cons 91 0)
           (list 10 4.7189 1.2)
           (cons 40 0)
           (cons 41 0)
           (cons 42 0)
           (cons 91 0)
           (list 10 5.1761 1.2)
           (cons 40 0)
           (cons 41 0)
           (cons 42 0)
           (cons 91 0)
           (list 10 5.265 1.170155)
           (cons 40 0)
           (cons 41 0)
           (cons 42 0)
           (cons 91 0)
           (list 10 5.265 1.071095)
           (cons 40 0)
           (cons 41 0)
           (cons 42 0)
           (cons 91 0)
           (list 10 5.1761 1.04125)
           (cons 40 0)
           (cons 41 0)
           (cons 42 0)
           (cons 91 0)
           (list 10 4.7189 1.04125)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9 -1.170155)
           (cons 40 0)
           (cons 41 0)
           (cons 42 0)
           (cons 91 0)
           (list 10 5.9 -1.071095)
           (cons 40 0)
           (cons 41 0)
           (cons 42 0)
           (cons 91 0)
           (list 10 5.9889 -1.04125)
           (cons 40 0)
           (cons 41 0)
           (cons 42 0)
           (cons 91 0)
           (list 10 6.4461 -1.04125)
           (cons 40 0)
           (cons 41 0)
           (cons 42 0)
           (cons 91 0)
           (list 10 6.535 -1.071095)
           (cons 40 0)
           (cons 41 0)
           (cons 42 0)
           (cons 91 0)
           (list 10 6.535 -1.170155)
           (cons 40 0)
           (cons 41 0)
           (cons 42 0)
           (cons 91 0)
           (list 10 6.4461 -1.2)
           (cons 40 0)
           (cons 41 0)
           (cons 42 0)
           (cons 91 0)
           (list 10 5.9889 -1.2)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9 1.071095)
           (cons 40 0)
           (cons 41 0)
           (cons 42 0)
           (cons 91 0)
           (list 10 5.9 1.170155)
           (cons 40 0)
           (cons 41 0)
           (cons 42 0)
           (cons 91 0)
           (list 10 5.9889 1.2)
           (cons 40 0)
           (cons 41 0)
           (cons 42 0)
           (cons 91 0)
           (list 10 6.4461 1.2)
           (cons 40 0)
           (cons 41 0)
           (cons 42 0)
           (cons 91 0)
           (list 10 6.535 1.170155)
           (cons 40 0)
           (cons 41 0)
           (cons 42 0)
           (cons 91 0)
           (list 10 6.535 1.071095)
           (cons 40 0)
           (cons 41 0)
           (cons 42 0)
           (cons 91 0)
           (list 10 6.4461 1.04125)
           (cons 40 0)
           (cons 41 0)
           (cons 42 0)
           (cons 91 0)
           (list 10 5.9889 1.04125)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 0.9 1.2 0)
           (cons 50 0)
          )
         )
         (entmake
          (list
           (cons 0 "POINT")
           (cons 100 "AcDbEntity")
           (cons 67 0)
           (cons 8 "0")
           (cons 100 "AcDbPoint")
           (list 10 0.9 -1.2 0)
           (cons 50 0)
          )
         )
         (entmake
          (list
           (cons 0 "POINT")
           (cons 100 "AcDbEntity")
           (cons 67 0)
           (cons 8 "0")
           (cons 100 "AcDbPoint")
           (list 10 9.1 -1.2 0)
           (cons 50 0)
          )
         )
         (entmake
          (list
           (cons 0 "POINT")
           (cons 100 "AcDbEntity")
           (cons 67 0)
           (cons 8 "0")
           (cons 100 "AcDbPoint")
           (list 10 9.1 1.2 0)
           (cons 50 0)
          )
         )
         (entmake
          (list
           (cons 0 "POINT")
           (cons 100 "AcDbEntity")
           (cons 67 0)
           (cons 8 "0")
           (cons 100 "AcDbPoint")
           (list 10 5.6 1.2 0)
           (cons 50 0)
          )
         )
         (entmake
          (list
           (cons 0 "POINT")
           (cons 100 "AcDbEntity")
           (cons 67 0)
           (cons 8 "0")
           (cons 100 "AcDbPoint")
           (list 10 5.6 -1.2 0)
           (cons 50 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "5.600")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-P"))
        (progn
         (entmake)
         (entmake
          (list
           (cons 0 "BLOCK")
           (cons 2 "AB_INF-P")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.05)
           (cons 40 0)
           (cons 41 0)
           (cons 42 0)
           (cons 91 0)
           (list 10 5.8 -1.05)
           (cons 40 0)
           (cons 41 0)
           (cons 42 0)
           (cons 91 0)
           (list 10 5.8 1.05)
           (cons 40 0)
           (cons 41 0)
           (cons 42 0)
           (cons 91 0)
           (list 10 0 1.05)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.05 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.8 -1.05 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.8 1.05 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.05 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.05 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.05 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.9571 -1.0177674)
           (cons 40 0)
           (cons 41 0)
           (cons 42 0)
           (cons 91 0)
           (list 10 3.9571 -0.9107826)
           (cons 40 0)
           (cons 41 0)
           (cons 42 0)
           (cons 91 0)
           (list 10 4.053112 -0.87855)
           (cons 40 0)
           (cons 41 0)
           (cons 42 0)
           (cons 91 0)
           (list 10 4.546888 -0.87855)
           (cons 40 0)
           (cons 41 0)
           (cons 42 0)
           (cons 91 0)
           (list 10 4.6429 -0.9107826)
           (cons 40 0)
           (cons 41 0)
           (cons 42 0)
           (cons 91 0)
           (list 10 4.6429 -1.0177674)
           (cons 40 0)
           (cons 41 0)
           (cons 42 0)
           (cons 91 0)
           (list 10 4.546888 -1.05)
           (cons 40 0)
           (cons 41 0)
           (cons 42 0)
           (cons 91 0)
           (list 10 4.053112 -1.05)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.9571 0.9107826)
           (cons 40 0)
           (cons 41 0)
           (cons 42 0)
           (cons 91 0)
           (list 10 3.9571 1.0177674)
           (cons 40 0)
           (cons 41 0)
           (cons 42 0)
           (cons 91 0)
           (list 10 4.053112 1.05)
           (cons 40 0)
           (cons 41 0)
           (cons 42 0)
           (cons 91 0)
           (list 10 4.546888 1.05)
           (cons 40 0)
           (cons 41 0)
           (cons 42 0)
           (cons 91 0)
           (list 10 4.6429 1.0177674)
           (cons 40 0)
           (cons 41 0)
           (cons 42 0)
           (cons 91 0)
           (list 10 4.6429 0.9107826)
           (cons 40 0)
           (cons 41 0)
           (cons 42 0)
           (cons 91 0)
           (list 10 4.546888 0.87855)
           (cons 40 0)
           (cons 41 0)
           (cons 42 0)
           (cons 91 0)
           (list 10 4.053112 0.87855)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelRightM3")
           (list 10 0.9 0.87855 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM3")
           (list 10 0.9 -0.87855 0)
           (cons 41 1)
           (cons 42 1)
           (cons 43 1)
           (cons 50 0)
           (cons 70 0)
           (cons 71 0)
           (cons 44 0)
           (cons 45 0)
          )
         )
         (entmake
          (list
           (cons 0 "POINT")
           (cons 100 "AcDbEntity")
           (cons 67 0)
           (cons 8 "0")
           (cons 100 "AcDbPoint")
           (list 10 0 -1.05 0)
           (cons 50 0)
          )
         )
         (entmake
          (list
           (cons 0 "POINT")
           (cons 100 "AcDbEntity")
           (cons 67 0)
           (cons 8 "0")
           (cons 100 "AcDbPoint")
           (list 10 5.8 -1.05 0)
           (cons 50 0)
          )
         )
         (entmake
          (list
           (cons 0 "POINT")
           (cons 100 "AcDbEntity")
           (cons 67 0)
           (cons 8 "0")
           (cons 100 "AcDbPoint")
           (list 10 5.8 1.05 0)
           (cons 50 0)
          )
         )
         (entmake
          (list
           (cons 0 "POINT")
           (cons 100 "AcDbEntity")
           (cons 67 0)
           (cons 8 "0")
           (cons 100 "AcDbPoint")
           (list 10 0 1.05 0)
           (cons 50 0)
          )
         )
         (entmake
          (list
           (cons 0 "POINT")
           (cons 100 "AcDbEntity")
           (cons 67 0)
           (cons 8 "0")
           (cons 100 "AcDbPoint")
           (list 10 0.9 1.05 0)
           (cons 50 0)
          )
         )
         (entmake
          (list
           (cons 0 "POINT")
           (cons 100 "AcDbEntity")
           (cons 67 0)
           (cons 8 "0")
           (cons 100 "AcDbPoint")
           (list 10 4.3 1.05 0)
           (cons 50 0)
          )
         )
         (entmake
          (list
           (cons 0 "POINT")
           (cons 100 "AcDbEntity")
           (cons 67 0)
           (cons 8 "0")
           (cons 100 "AcDbPoint")
           (list 10 0.9 -1.05 0)
           (cons 50 0)
          )
         )
         (entmake
          (list
           (cons 0 "POINT")
           (cons 100 "AcDbEntity")
           (cons 67 0)
           (cons 8 "0")
           (cons 100 "AcDbPoint")
           (list 10 4.3 -1.05 0)
           (cons 50 0)
          )
         )
         (entmake
          (list
           (cons 0 "POINT")
           (cons 100 "AcDbEntity")
           (cons 67 0)
           (cons 8 "0")
           (cons 100 "AcDbPoint")
           (list 10 0.9 0 0)
           (cons 50 0)
          )
         )
         (entmake
          (list
           (cons 0 "ATTDEF")
           (cons 100 "AcDbEntity")
           (cons 67 0)
           (cons 8 "0")
           (cons 100 "AcDbText")
           (list 10 0.2 0.56666667 0)
           (cons 40 0.2)
           (cons 1 "0.900")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.2 0.23333333 0)
           (cons 40 0.2)
           (cons 1 "0.900")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.2 -0.1 0)
           (cons 40 0.2)
           (cons 1 "4.300")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.2 -0.43333333 0)
           (cons 40 0.2)
           (cons 1 "5.800")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.2 -0.76666667 0)
           (cons 40 0.2)
           (cons 1 "32.1")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "POINT")
           (cons 100 "AcDbEntity")
           (cons 67 0)
           (cons 8 "0")
           (cons 100 "AcDbPoint")
           (list 10 5.8 0 0)
           (cons 50 0)
          )
         )
         (entmake (list (cons 0 "ENDBLK")))
        )
       )
       ((= (strcase BLKNAME) (strcase "AB_INF-P"))
        (progn
         (entmake)
         (entmake
          (list
           (cons 0 "BLOCK")
           (cons 2 "AB_INF-P")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.05)
           (cons 40 0)
           (cons 41 0)
           (cons 42 0)
           (cons 91 0)
           (list 10 5.8 -1.05)
           (cons 40 0)
           (cons 41 0)
           (cons 42 0)
           (cons 91 0)
           (list 10 5.8 1.05)
           (cons 40 0)
           (cons 41 0)
           (cons 42 0)
           (cons 91 0)
           (list 10 0 1.05)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.05 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.8 -1.05 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.8 1.05 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.05 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.05 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.05 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.9571 -1.0177674)
           (cons 40 0)
           (cons 41 0)
           (cons 42 0)
           (cons 91 0)
           (list 10 3.9571 -0.9107826)
           (cons 40 0)
           (cons 41 0)
           (cons 42 0)
           (cons 91 0)
           (list 10 4.053112 -0.87855)
           (cons 40 0)
           (cons 41 0)
           (cons 42 0)
           (cons 91 0)
           (list 10 4.546888 -0.87855)
           (cons 40 0)
           (cons 41 0)
           (cons 42 0)
           (cons 91 0)
           (list 10 4.6429 -0.9107826)
           (cons 40 0)
           (cons 41 0)
           (cons 42 0)
           (cons 91 0)
           (list 10 4.6429 -1.0177674)
           (cons 40 0)
           (cons 41 0)
           (cons 42 0)
           (cons 91 0)
           (list 10 4.546888 -1.05)
           (cons 40 0)
           (cons 41 0)
           (cons 42 0)
           (cons 91 0)
           (list 10 4.053112 -1.05)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.9571 0.9107826)
           (cons 40 0)
           (cons 41 0)
           (cons 42 0)
           (cons 91 0)
           (list 10 3.9571 1.0177674)
           (cons 40 0)
           (cons 41 0)
           (cons 42 0)
           (cons 91 0)
           (list 10 4.053112 1.05)
           (cons 40 0)
           (cons 41 0)
           (cons 42 0)
           (cons 91 0)
           (list 10 4.546888 1.05)
           (cons 40 0)
           (cons 41 0)
           (cons 42 0)
           (cons 91 0)
           (list 10 4.6429 1.0177674)
           (cons 40 0)
           (cons 41 0)
           (cons 42 0)
           (cons 91 0)
           (list 10 4.6429 0.9107826)
           (cons 40 0)
           (cons 41 0)
           (cons 42 0)
           (cons 91 0)
           (list 10 4.546888 0.87855)
           (cons 40 0)
           (cons 41 0)
           (cons 42 0)
           (cons 91 0)
           (list 10 4.053112 0.87855)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelRightM3")
           (list 10 0.9 0.87855 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM3")
           (list 10 0.9 -0.87855 0)
           (cons 41 1)
           (cons 42 1)
           (cons 43 1)
           (cons 50 0)
           (cons 70 0)
           (cons 71 0)
           (cons 44 0)
           (cons 45 0)
          )
         )
         (entmake
          (list
           (cons 0 "POINT")
           (cons 100 "AcDbEntity")
           (cons 67 0)
           (cons 8 "0")
           (cons 100 "AcDbPoint")
           (list 10 0 -1.05 0)
           (cons 50 0)
          )
         )
         (entmake
          (list
           (cons 0 "POINT")
           (cons 100 "AcDbEntity")
           (cons 67 0)
           (cons 8 "0")
           (cons 100 "AcDbPoint")
           (list 10 5.8 -1.05 0)
           (cons 50 0)
          )
         )
         (entmake
          (list
           (cons 0 "POINT")
           (cons 100 "AcDbEntity")
           (cons 67 0)
           (cons 8 "0")
           (cons 100 "AcDbPoint")
           (list 10 5.8 1.05 0)
           (cons 50 0)
          )
         )
         (entmake
          (list
           (cons 0 "POINT")
           (cons 100 "AcDbEntity")
           (cons 67 0)
           (cons 8 "0")
           (cons 100 "AcDbPoint")
           (list 10 0 1.05 0)
           (cons 50 0)
          )
         )
         (entmake
          (list
           (cons 0 "POINT")
           (cons 100 "AcDbEntity")
           (cons 67 0)
           (cons 8 "0")
           (cons 100 "AcDbPoint")
           (list 10 0.9 1.05 0)
           (cons 50 0)
          )
         )
         (entmake
          (list
           (cons 0 "POINT")
           (cons 100 "AcDbEntity")
           (cons 67 0)
           (cons 8 "0")
           (cons 100 "AcDbPoint")
           (list 10 4.3 1.05 0)
           (cons 50 0)
          )
         )
         (entmake
          (list
           (cons 0 "POINT")
           (cons 100 "AcDbEntity")
           (cons 67 0)
           (cons 8 "0")
           (cons 100 "AcDbPoint")
           (list 10 0.9 -1.05 0)
           (cons 50 0)
          )
         )
         (entmake
          (list
           (cons 0 "POINT")
           (cons 100 "AcDbEntity")
           (cons 67 0)
           (cons 8 "0")
           (cons 100 "AcDbPoint")
           (list 10 4.3 -1.05 0)
           (cons 50 0)
          )
         )
         (entmake
          (list
           (cons 0 "POINT")
           (cons 100 "AcDbEntity")
           (cons 67 0)
           (cons 8 "0")
           (cons 100 "AcDbPoint")
           (list 10 0.9 0 0)
           (cons 50 0)
          )
         )
         (entmake
          (list
           (cons 0 "ATTDEF")
           (cons 100 "AcDbEntity")
           (cons 67 0)
           (cons 8 "0")
           (cons 100 "AcDbText")
           (list 10 0.2 0.56666667 0)
           (cons 40 0.2)
           (cons 1 "0.900")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.2 0.23333333 0)
           (cons 40 0.2)
           (cons 1 "0.900")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.2 -0.1 0)
           (cons 40 0.2)
           (cons 1 "4.300")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.2 -0.43333333 0)
           (cons 40 0.2)
           (cons 1 "5.800")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.2 -0.76666667 0)
           (cons 40 0.2)
           (cons 1 "32.1")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "POINT")
           (cons 100 "AcDbEntity")
           (cons 67 0)
           (cons 8 "0")
           (cons 100 "AcDbPoint")
           (list 10 5.8 0 0)
           (cons 50 0)
          )
         )
         (entmake (list (cons 0 "ENDBLK")))
        )
       )
       ((= (strcase BLKNAME) (strcase "AB_INF-LogHaul-Load"))
        (progn
         (entmake)
         (entmake
          (list
           (cons 0 "BLOCK")
           (cons 2 "AB_INF-LogHaul-Load")
           (cons 70 2)
           (cons 4 "")
           (list 10 0 0 0)
          )
         )
         (entmake
          (list
           (cons 0 "ATTDEF")
           (cons 100 "AcDbEntity")
           (cons 67 0)
           (cons 8 "0")
           (cons 100 "AcDbText")
           (list 10 2.4 -0.1 0)
           (cons 40 0.2)
           (cons 1 "13.650")
           (cons 50 0)
           (cons 41 1)
           (cons 51 0)
           (cons 7 "Standard")
           (cons 71 0)
           (cons 72 0)
           (list 11 0 0 0)
           (cons 100 "AcDbAttributeDefinition")
           (cons 3 "Load Base Point (LB)")
           (cons 2 "LB")
           (cons 70 9)
           (cons 73 0)
           (cons 74 0)
          )
         )
         (entmake
          (list
           (cons 0 "ATTDEF")
           (cons 100 "AcDbEntity")
           (cons 67 0)
           (cons 8 "0")
           (cons 100 "AcDbText")
           (list 10 2.4 -0.43333333 0)
           (cons 40 0.2)
           (cons 1 "3.100")
           (cons 50 0)
           (cons 41 1)
           (cons 51 0)
           (cons 7 "Standard")
           (cons 71 0)
           (cons 72 0)
           (list 11 0 0 0)
           (cons 100 "AcDbAttributeDefinition")
           (cons 3 "Load Angle Point (LA)")
           (cons 2 "LA")
           (cons 70 9)
           (cons 73 0)
           (cons 74 0)
          )
         )
         (entmake
          (list
           (cons 0 "POINT")
           (cons 100 "AcDbEntity")
           (cons 67 0)
           (cons 8 "0")
           (cons 100 "AcDbPoint")
           (list 10 23.35 1.6 0)
           (cons 50 0)
          )
         )
         (entmake
          (list
           (cons 0 "POINT")
           (cons 100 "AcDbEntity")
           (cons 67 0)
           (cons 8 "0")
           (cons 100 "AcDbPoint")
           (list 10 23.35 -1.6 0)
           (cons 50 0)
          )
         )
         (entmake
          (list
           (cons 0 "POINT")
           (cons 100 "AcDbEntity")
           (cons 67 0)
           (cons 8 "0")
           (cons 100 "AcDbPoint")
           (list 10 0 -1.6 0)
           (cons 50 0)
          )
         )
         (entmake
          (list
           (cons 0 "POINT")
           (cons 100 "AcDbEntity")
           (cons 67 0)
           (cons 8 "0")
           (cons 100 "AcDbPoint")
           (list 10 0 1.6 0)
           (cons 50 0)
          )
         )
         (entmake
          (list
           (cons 0 "POINT")
           (cons 100 "AcDbEntity")
           (cons 67 0)
           (cons 8 "0")
           (cons 62 3)
           (cons 100 "AcDbPoint")
           (list 10 13.65 0 0)
           (cons 50 0)
          )
         )
         (entmake
          (list
           (cons 0 "POINT")
           (cons 100 "AcDbEntity")
           (cons 67 0)
           (cons 8 "0")
           (cons 62 3)
           (cons 100 "AcDbPoint")
           (list 10 3.1 0 0)
           (cons 50 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 3.1 0 0)
           (cons 40 0.1524)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.6 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 23.35 -1.6 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 23.35 1.6 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.6 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.6 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 13.65 0 0)
           (cons 40 0.1524)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.6)
           (cons 40 0)
           (cons 41 0)
           (cons 42 0)
           (cons 91 0)
           (list 10 23.35 -1.6)
           (cons 40 0)
           (cons 41 0)
           (cons 42 0)
           (cons 91 0)
           (list 10 23.35 1.6)
           (cons 40 0)
           (cons 41 0)
           (cons 42 0)
           (cons 91 0)
           (list 10 0 1.6)
           (cons 40 0)
           (cons 41 0)
           (cons 42 0)
           (cons 91 0)
          )
         )
         (entmake
          (list
           (cons 0 "TEXT")
           (cons 100 "AcDbEntity")
           (cons 67 0)
           (cons 8 "0")
           (cons 100 "AcDbText")
           (list 10 3.92142857 -0.25 0)
           (cons 40 0.5)
           (cons 1 "4")
           (cons 50 0)
           (cons 41 1)
           (cons 51 0)
           (cons 7 "Standard")
           (cons 71 0)
           (cons 72 4)
           (list 11 4.1 0 0)
           (cons 100 "AcDbText")
           (cons 73 0)
          )
         )
         (entmake (list (cons 0 "ENDBLK")))
        )
       )
       ((= (strcase BLKNAME) (strcase "AB_INF-LogHaul-Trailer2"))
        (progn
         (entmake)
         (entmake
          (list
           (cons 0 "BLOCK")
           (cons 2 "AB_INF-LogHaul-Trailer2")
           (cons 70 2)
           (cons 4 "")
           (list 10 0 0 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "4.850")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -1.1 0)
           (cons 40 0.2)
           (cons 1 "4.850")
           (cons 50 0)
           (cons 41 1)
           (cons 51 0)
           (cons 7 "Standard")
           (cons 71 0)
           (cons 72 0)
           (list 11 0 0 0)
           (cons 100 "AcDbAttributeDefinition")
           (cons 3 "Load Base Point (LB)")
           (cons 2 "LB")
           (cons 70 9)
           (cons 73 0)
           (cons 74 0)
          )
         )
         (entmake
          (list
           (cons 0 "POINT")
           (cons 100 "AcDbEntity")
           (cons 67 0)
           (cons 8 "0")
           (cons 100 "AcDbPoint")
           (list 10 4.85 -1.3 0)
           (cons 50 0)
          )
         )
         (entmake
          (list
           (cons 0 "POINT")
           (cons 100 "AcDbEntity")
           (cons 67 0)
           (cons 8 "0")
           (cons 100 "AcDbPoint")
           (list 10 4.85 1.3 0)
           (cons 50 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 4.85 0 0)
           (cons 40 0.1524)
          )
         )
         (entmake
          (list
           (cons 0 "POINT")
           (cons 100 "AcDbEntity")
           (cons 67 0)
           (cons 8 "0")
           (cons 62 1)
           (cons 6 "Continuous")
           (cons 48 1.524)
           (cons 100 "AcDbPoint")
           (list 10 4.85 0 0)
           (cons 50 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.991 0.570452)
           (cons 40 0)
           (cons 41 0)
           (cons 42 0)
           (cons 91 0)
           (list 10 4.991 0.744548)
           (cons 40 0)
           (cons 41 0)
           (cons 42 0)
           (cons 91 0)
           (list 10 5.14752 0.797)
           (cons 40 0)
           (cons 41 0)
           (cons 42 0)
           (cons 91 0)
           (list 10 5.95248 0.797)
           (cons 40 0)
           (cons 41 0)
           (cons 42 0)
           (cons 91 0)
           (list 10 6.109 0.744548)
           (cons 40 0)
           (cons 41 0)
           (cons 42 0)
           (cons 91 0)
           (list 10 6.109 0.570452)
           (cons 40 0)
           (cons 41 0)
           (cons 42 0)
           (cons 91 0)
           (list 10 5.95248 0.518)
           (cons 40 0)
           (cons 41 0)
           (cons 42 0)
           (cons 91 0)
           (list 10 5.14752 0.518)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.591 -0.744548)
           (cons 40 0)
           (cons 41 0)
           (cons 42 0)
           (cons 91 0)
           (list 10 3.591 -0.570452)
           (cons 40 0)
           (cons 41 0)
           (cons 42 0)
           (cons 91 0)
           (list 10 3.74752 -0.518)
           (cons 40 0)
           (cons 41 0)
           (cons 42 0)
           (cons 91 0)
           (list 10 4.55248 -0.518)
           (cons 40 0)
           (cons 41 0)
           (cons 42 0)
           (cons 91 0)
           (list 10 4.709 -0.570452)
           (cons 40 0)
           (cons 41 0)
           (cons 42 0)
           (cons 91 0)
           (list 10 4.709 -0.744548)
           (cons 40 0)
           (cons 41 0)
           (cons 42 0)
           (cons 91 0)
           (list 10 4.55248 -0.797)
           (cons 40 0)
           (cons 41 0)
           (cons 42 0)
           (cons 91 0)
           (list 10 3.74752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.591 -1.247548)
           (cons 40 0)
           (cons 41 0)
           (cons 42 0)
           (cons 91 0)
           (list 10 3.591 -1.073452)
           (cons 40 0)
           (cons 41 0)
           (cons 42 0)
           (cons 91 0)
           (list 10 3.74752 -1.021)
           (cons 40 0)
           (cons 41 0)
           (cons 42 0)
           (cons 91 0)
           (list 10 4.55248 -1.021)
           (cons 40 0)
           (cons 41 0)
           (cons 42 0)
           (cons 91 0)
           (list 10 4.709 -1.073452)
           (cons 40 0)
           (cons 41 0)
           (cons 42 0)
           (cons 91 0)
           (list 10 4.709 -1.247548)
           (cons 40 0)
           (cons 41 0)
           (cons 42 0)
           (cons 91 0)
           (list 10 4.55248 -1.3)
           (cons 40 0)
           (cons 41 0)
           (cons 42 0)
           (cons 91 0)
           (list 10 3.74752 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.991 -0.744548)
           (cons 40 0)
           (cons 41 0)
           (cons 42 0)
           (cons 91 0)
           (list 10 4.991 -0.570452)
           (cons 40 0)
           (cons 41 0)
           (cons 42 0)
           (cons 91 0)
           (list 10 5.14752 -0.518)
           (cons 40 0)
           (cons 41 0)
           (cons 42 0)
           (cons 91 0)
           (list 10 5.95248 -0.518)
           (cons 40 0)
           (cons 41 0)
           (cons 42 0)
           (cons 91 0)
           (list 10 6.109 -0.570452)
           (cons 40 0)
           (cons 41 0)
           (cons 42 0)
           (cons 91 0)
           (list 10 6.109 -0.744548)
           (cons 40 0)
           (cons 41 0)
           (cons 42 0)
           (cons 91 0)
           (list 10 5.95248 -0.797)
           (cons 40 0)
           (cons 41 0)
           (cons 42 0)
           (cons 91 0)
           (list 10 5.14752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.991 -1.247548)
           (cons 40 0)
           (cons 41 0)
           (cons 42 0)
           (cons 91 0)
           (list 10 4.991 -1.073452)
           (cons 40 0)
           (cons 41 0)
           (cons 42 0)
           (cons 91 0)
           (list 10 5.14752 -1.021)
           (cons 40 0)
           (cons 41 0)
           (cons 42 0)
           (cons 91 0)
           (list 10 5.95248 -1.021)
           (cons 40 0)
           (cons 41 0)
           (cons 42 0)
           (cons 91 0)
           (list 10 6.109 -1.073452)
           (cons 40 0)
           (cons 41 0)
           (cons 42 0)
           (cons 91 0)
           (list 10 6.109 -1.247548)
           (cons 40 0)
           (cons 41 0)
           (cons 42 0)
           (cons 91 0)
           (list 10 5.95248 -1.3)
           (cons 40 0)
           (cons 41 0)
           (cons 42 0)
           (cons 91 0)
           (list 10 5.14752 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.991 1.073452)
           (cons 40 0)
           (cons 41 0)
           (cons 42 0)
           (cons 91 0)
           (list 10 4.991 1.247548)
           (cons 40 0)
           (cons 41 0)
           (cons 42 0)
           (cons 91 0)
           (list 10 5.14752 1.3)
           (cons 40 0)
           (cons 41 0)
           (cons 42 0)
           (cons 91 0)
           (list 10 5.95248 1.3)
           (cons 40 0)
           (cons 41 0)
           (cons 42 0)
           (cons 91 0)
           (list 10 6.109 1.247548)
           (cons 40 0)
           (cons 41 0)
           (cons 42 0)
           (cons 91 0)
           (list 10 6.109 1.073452)
           (cons 40 0)
           (cons 41 0)
           (cons 42 0)
           (cons 91 0)
           (list 10 5.95248 1.021)
           (cons 40 0)
           (cons 41 0)
           (cons 42 0)
           (cons 91 0)
           (list 10 5.14752 1.021)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.591 1.073452)
           (cons 40 0)
           (cons 41 0)
           (cons 42 0)
           (cons 91 0)
           (list 10 3.591 1.247548)
           (cons 40 0)
           (cons 41 0)
           (cons 42 0)
           (cons 91 0)
           (list 10 3.74752 1.3)
           (cons 40 0)
           (cons 41 0)
           (cons 42 0)
           (cons 91 0)
           (list 10 4.55248 1.3)
           (cons 40 0)
           (cons 41 0)
           (cons 42 0)
           (cons 91 0)
           (list 10 4.709 1.247548)
           (cons 40 0)
           (cons 41 0)
           (cons 42 0)
           (cons 91 0)
           (list 10 4.709 1.073452)
           (cons 40 0)
           (cons 41 0)
           (cons 42 0)
           (cons 91 0)
           (list 10 4.55248 1.021)
           (cons 40 0)
           (cons 41 0)
           (cons 42 0)
           (cons 91 0)
           (list 10 3.74752 1.021)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.591 0.570452)
           (cons 40 0)
           (cons 41 0)
           (cons 42 0)
           (cons 91 0)
           (list 10 3.591 0.744548)
           (cons 40 0)
           (cons 41 0)
           (cons 42 0)
           (cons 91 0)
           (list 10 3.74752 0.797)
           (cons 40 0)
           (cons 41 0)
           (cons 42 0)
           (cons 91 0)
           (list 10 4.55248 0.797)
           (cons 40 0)
           (cons 41 0)
           (cons 42 0)
           (cons 91 0)
           (list 10 4.709 0.744548)
           (cons 40 0)
           (cons 41 0)
           (cons 42 0)
           (cons 91 0)
           (list 10 4.709 0.570452)
           (cons 40 0)
           (cons 41 0)
           (cons 42 0)
           (cons 91 0)
           (list 10 4.55248 0.518)
           (cons 40 0)
           (cons 41 0)
           (cons 42 0)
           (cons 91 0)
           (list 10 3.74752 0.518)
           (cons 40 0)
           (cons 41 0)
           (cons 42 0)
           (cons 91 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.1016)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.55 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.55 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "POLYLINE")
           (cons 100 "AcDbEntity")
           (cons 67 0)
           (cons 8 "Defpoints")
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "Defpoints")
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 3.591 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 3.591 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.109 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.109 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.55 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.55 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.109 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.109 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 3.591 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 3.591 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 0 0.5 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "Defpoints")
          )
         )
         (entmake
          (list
           (cons 0 "TEXT")
           (cons 100 "AcDbEntity")
           (cons 67 0)
           (cons 8 "0")
           (cons 100 "AcDbText")
           (list 10 0.83333333 -0.25 0)
           (cons 40 0.5)
           (cons 1 "3")
           (cons 50 0)
           (cons 41 1)
           (cons 51 0)
           (cons 7 "Standard")
           (cons 71 0)
           (cons 72 4)
           (list 11 1 0 0)
           (cons 100 "AcDbText")
           (cons 73 0)
          )
         )
         (entmake (list (cons 0 "ENDBLK")))
        )
       )
       ((= (strcase BLKNAME) (strcase "AB_INF-LogHaul-Trailer1"))
        (progn
         (entmake)
         (entmake
          (list
           (cons 0 "BLOCK")
           (cons 2 "AB_INF-LogHaul-Trailer1")
           (cons 70 2)
           (cons 4 "")
           (list 10 0 0 0)
          )
         )
         (entmake
          (list
           (cons 0 "ATTDEF")
           (cons 100 "AcDbEntity")
           (cons 67 0)
           (cons 8 "0")
           (cons 100 "AcDbText")
           (list 10 -0.3 0.56666667 0)
           (cons 40 0.2)
           (cons 1 "0.400")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 0.23333333 0)
           (cons 40 0.2)
           (cons 1 "0.400")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.1 0)
           (cons 40 0.2)
           (cons 1 "7.300")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.43333333 0)
           (cons 40 0.2)
           (cons 1 "9.200")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -1.1 0)
           (cons 40 0.2)
           (cons 1 "3.500")
           (cons 50 0)
           (cons 41 1)
           (cons 51 0)
           (cons 7 "Standard")
           (cons 71 0)
           (cons 72 0)
           (list 11 0 0 0)
           (cons 100 "AcDbAttributeDefinition")
           (cons 3 "Load Angle Point (LA)")
           (cons 2 "LA")
           (cons 70 9)
           (cons 73 0)
           (cons 74 0)
          )
         )
         (entmake
          (list
           (cons 0 "POINT")
           (cons 100 "AcDbEntity")
           (cons 67 0)
           (cons 8 "0")
           (cons 62 1)
           (cons 100 "AcDbPoint")
           (list 10 3.5 0 0)
           (cons 50 0)
          )
         )
         (entmake
          (list
           (cons 0 "POINT")
           (cons 100 "AcDbEntity")
           (cons 67 0)
           (cons 8 "0")
           (cons 100 "AcDbPoint")
           (list 10 7.3 -1.3 0)
           (cons 50 0)
          )
         )
         (entmake
          (list
           (cons 0 "POINT")
           (cons 100 "AcDbEntity")
           (cons 67 0)
           (cons 8 "0")
           (cons 100 "AcDbPoint")
           (list 10 7.3 1.3 0)
           (cons 50 0)
          )
         )
         (entmake
          (list
           (cons 0 "POINT")
           (cons 100 "AcDbEntity")
           (cons 67 0)
           (cons 8 "0")
           (cons 100 "AcDbPoint")
           (list 10 0.4 0 0)
           (cons 50 0)
          )
         )
         (entmake
          (list
           (cons 0 "POINT")
           (cons 100 "AcDbEntity")
           (cons 67 0)
           (cons 8 "0")
           (cons 100 "AcDbPoint")
           (list 10 9.2 0 0)
           (cons 50 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 3.5 0 0)
           (cons 40 0.1524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 9.2 0 0)
           (cons 40 0.17333333)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.441 1.073452)
           (cons 40 0)
           (cons 41 0)
           (cons 42 0)
           (cons 91 0)
           (list 10 7.441 1.247548)
           (cons 40 0)
           (cons 41 0)
           (cons 42 0)
           (cons 91 0)
           (list 10 7.59752 1.3)
           (cons 40 0)
           (cons 41 0)
           (cons 42 0)
           (cons 91 0)
           (list 10 8.40248 1.3)
           (cons 40 0)
           (cons 41 0)
           (cons 42 0)
           (cons 91 0)
           (list 10 8.559 1.247548)
           (cons 40 0)
           (cons 41 0)
           (cons 42 0)
           (cons 91 0)
           (list 10 8.559 1.073452)
           (cons 40 0)
           (cons 41 0)
           (cons 42 0)
           (cons 91 0)
           (list 10 8.40248 1.021)
           (cons 40 0)
           (cons 41 0)
           (cons 42 0)
           (cons 91 0)
           (list 10 7.59752 1.021)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.441 0.570452)
           (cons 40 0)
           (cons 41 0)
           (cons 42 0)
           (cons 91 0)
           (list 10 7.441 0.744548)
           (cons 40 0)
           (cons 41 0)
           (cons 42 0)
           (cons 91 0)
           (list 10 7.59752 0.797)
           (cons 40 0)
           (cons 41 0)
           (cons 42 0)
           (cons 91 0)
           (list 10 8.40248 0.797)
           (cons 40 0)
           (cons 41 0)
           (cons 42 0)
           (cons 91 0)
           (list 10 8.559 0.744548)
           (cons 40 0)
           (cons 41 0)
           (cons 42 0)
           (cons 91 0)
           (list 10 8.559 0.570452)
           (cons 40 0)
           (cons 41 0)
           (cons 42 0)
           (cons 91 0)
           (list 10 8.40248 0.518)
           (cons 40 0)
           (cons 41 0)
           (cons 42 0)
           (cons 91 0)
           (list 10 7.59752 0.518)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.441 -0.744548)
           (cons 40 0)
           (cons 41 0)
           (cons 42 0)
           (cons 91 0)
           (list 10 7.441 -0.570452)
           (cons 40 0)
           (cons 41 0)
           (cons 42 0)
           (cons 91 0)
           (list 10 7.59752 -0.518)
           (cons 40 0)
           (cons 41 0)
           (cons 42 0)
           (cons 91 0)
           (list 10 8.40248 -0.518)
           (cons 40 0)
           (cons 41 0)
           (cons 42 0)
           (cons 91 0)
           (list 10 8.559 -0.570452)
           (cons 40 0)
           (cons 41 0)
           (cons 42 0)
           (cons 91 0)
           (list 10 8.559 -0.744548)
           (cons 40 0)
           (cons 41 0)
           (cons 42 0)
           (cons 91 0)
           (list 10 8.40248 -0.797)
           (cons 40 0)
           (cons 41 0)
           (cons 42 0)
           (cons 91 0)
           (list 10 7.59752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.441 -1.247548)
           (cons 40 0)
           (cons 41 0)
           (cons 42 0)
           (cons 91 0)
           (list 10 7.441 -1.073452)
           (cons 40 0)
           (cons 41 0)
           (cons 42 0)
           (cons 91 0)
           (list 10 7.59752 -1.021)
           (cons 40 0)
           (cons 41 0)
           (cons 42 0)
           (cons 91 0)
           (list 10 8.40248 -1.021)
           (cons 40 0)
           (cons 41 0)
           (cons 42 0)
           (cons 91 0)
           (list 10 8.559 -1.073452)
           (cons 40 0)
           (cons 41 0)
           (cons 42 0)
           (cons 91 0)
           (list 10 8.559 -1.247548)
           (cons 40 0)
           (cons 41 0)
           (cons 42 0)
           (cons 91 0)
           (list 10 8.40248 -1.3)
           (cons 40 0)
           (cons 41 0)
           (cons 42 0)
           (cons 91 0)
           (list 10 7.59752 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.041 -1.247548)
           (cons 40 0)
           (cons 41 0)
           (cons 42 0)
           (cons 91 0)
           (list 10 6.041 -1.073452)
           (cons 40 0)
           (cons 41 0)
           (cons 42 0)
           (cons 91 0)
           (list 10 6.19752 -1.021)
           (cons 40 0)
           (cons 41 0)
           (cons 42 0)
           (cons 91 0)
           (list 10 7.00248 -1.021)
           (cons 40 0)
           (cons 41 0)
           (cons 42 0)
           (cons 91 0)
           (list 10 7.159 -1.073452)
           (cons 40 0)
           (cons 41 0)
           (cons 42 0)
           (cons 91 0)
           (list 10 7.159 -1.247548)
           (cons 40 0)
           (cons 41 0)
           (cons 42 0)
           (cons 91 0)
           (list 10 7.00248 -1.3)
           (cons 40 0)
           (cons 41 0)
           (cons 42 0)
           (cons 91 0)
           (list 10 6.19752 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.041 -0.744548)
           (cons 40 0)
           (cons 41 0)
           (cons 42 0)
           (cons 91 0)
           (list 10 6.041 -0.570452)
           (cons 40 0)
           (cons 41 0)
           (cons 42 0)
           (cons 91 0)
           (list 10 6.19752 -0.518)
           (cons 40 0)
           (cons 41 0)
           (cons 42 0)
           (cons 91 0)
           (list 10 7.00248 -0.518)
           (cons 40 0)
           (cons 41 0)
           (cons 42 0)
           (cons 91 0)
           (list 10 7.159 -0.570452)
           (cons 40 0)
           (cons 41 0)
           (cons 42 0)
           (cons 91 0)
           (list 10 7.159 -0.744548)
           (cons 40 0)
           (cons 41 0)
           (cons 42 0)
           (cons 91 0)
           (list 10 7.00248 -0.797)
           (cons 40 0)
           (cons 41 0)
           (cons 42 0)
           (cons 91 0)
           (list 10 6.19752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.041 1.073452)
           (cons 40 0)
           (cons 41 0)
           (cons 42 0)
           (cons 91 0)
           (list 10 6.041 1.247548)
           (cons 40 0)
           (cons 41 0)
           (cons 42 0)
           (cons 91 0)
           (list 10 6.19752 1.3)
           (cons 40 0)
           (cons 41 0)
           (cons 42 0)
           (cons 91 0)
           (list 10 7.00248 1.3)
           (cons 40 0)
           (cons 41 0)
           (cons 42 0)
           (cons 91 0)
           (list 10 7.159 1.247548)
           (cons 40 0)
           (cons 41 0)
           (cons 42 0)
           (cons 91 0)
           (list 10 7.159 1.073452)
           (cons 40 0)
           (cons 41 0)
           (cons 42 0)
           (cons 91 0)
           (list 10 7.00248 1.021)
           (cons 40 0)
           (cons 41 0)
           (cons 42 0)
           (cons 91 0)
           (list 10 6.19752 1.021)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.041 0.570452)
           (cons 40 0)
           (cons 41 0)
           (cons 42 0)
           (cons 91 0)
           (list 10 6.041 0.744548)
           (cons 40 0)
           (cons 41 0)
           (cons 42 0)
           (cons 91 0)
           (list 10 6.19752 0.797)
           (cons 40 0)
           (cons 41 0)
           (cons 42 0)
           (cons 91 0)
           (list 10 7.00248 0.797)
           (cons 40 0)
           (cons 41 0)
           (cons 42 0)
           (cons 91 0)
           (list 10 7.159 0.744548)
           (cons 40 0)
           (cons 41 0)
           (cons 42 0)
           (cons 91 0)
           (list 10 7.159 0.570452)
           (cons 40 0)
           (cons 41 0)
           (cons 42 0)
           (cons 91 0)
           (list 10 7.00248 0.518)
           (cons 40 0)
           (cons 41 0)
           (cons 42 0)
           (cons 91 0)
           (list 10 6.19752 0.518)
           (cons 40 0)
           (cons 41 0)
           (cons 42 0)
           (cons 91 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0.4 0 0)
           (cons 40 0.104)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.2 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.2 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "POLYLINE")
           (cons 100 "AcDbEntity")
           (cons 67 0)
           (cons 8 "Defpoints")
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "Defpoints")
           (cons 100 "AcDbVertex")
           (cons 100 "AcDb2dVertex")
           (list 10 0 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.041 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.041 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 8.559 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 8.559 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 9.2 -0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 9.2 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 8.559 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 8.559 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.041 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 6.041 0.5 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 0 0.5 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "Defpoints")
          )
         )
         (entmake
          (list
           (cons 0 "TEXT")
           (cons 100 "AcDbEntity")
           (cons 67 0)
           (cons 8 "0")
           (cons 100 "AcDbText")
           (list 10 1.23333333 -0.25 0)
           (cons 40 0.5)
           (cons 1 "2")
           (cons 50 0)
           (cons 41 1)
           (cons 51 0)
           (cons 7 "Standard")
           (cons 71 0)
           (cons 72 4)
           (list 11 1.4 0 0)
           (cons 100 "AcDbText")
           (cons 73 0)
          )
         )
         (entmake (list (cons 0 "ENDBLK")))
        )
       )
       ((= (strcase BLKNAME) (strcase "AB_INF-LogHaul-Truck"))
        (progn
         (entmake)
         (entmake
          (list
           (cons 0 "BLOCK")
           (cons 2 "AB_INF-LogHaul-Truck")
           (cons 70 2)
           (cons 4 "")
           (list 10 0 0 0)
          )
         )
         (entmake
          (list
           (cons 0 "ATTDEF")
           (cons 100 "AcDbEntity")
           (cons 67 0)
           (cons 8 "0")
           (cons 100 "AcDbText")
           (list 10 0.3 0.56666667 0)
           (cons 40 0.2)
           (cons 1 "1.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 0.23333333 0)
           (cons 40 0.2)
           (cons 1 "1.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.1 0)
           (cons 40 0.2)
           (cons 1 "7.150")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.43333333 0)
           (cons 40 0.2)
           (cons 1 "7.150")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.76666667 0)
           (cons 40 0.2)
           (cons 1 "26.4")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 7.15 -1.3 0)
           (cons 50 0)
          )
         )
         (entmake
          (list
           (cons 0 "POINT")
           (cons 100 "AcDbEntity")
           (cons 67 0)
           (cons 8 "0")
           (cons 100 "AcDbPoint")
           (list 10 7.15 1.3 0)
           (cons 50 0)
          )
         )
         (entmake
          (list
           (cons 0 "POINT")
           (cons 100 "AcDbEntity")
           (cons 67 0)
           (cons 8 "0")
           (cons 100 "AcDbPoint")
           (list 10 1 -1.3 0)
           (cons 50 0)
          )
         )
         (entmake
          (list
           (cons 0 "POINT")
           (cons 100 "AcDbEntity")
           (cons 67 0)
           (cons 8 "0")
           (cons 100 "AcDbPoint")
           (list 10 1 1.3 0)
           (cons 50 0)
          )
         )
         (entmake
          (list
           (cons 0 "POINT")
           (cons 100 "AcDbEntity")
           (cons 67 0)
           (cons 8 "0")
           (cons 100 "AcDbPoint")
           (list 10 1 0 0)
           (cons 50 0)
          )
         )
         (entmake
          (list
           (cons 0 "INSERT")
           (cons 100 "AcDbEntity")
           (cons 67 0)
           (cons 8 "0")
           (cons 100 "AcDbBlockReference")
           (cons 2 "WheelLeftM1")
           (list 10 1 -1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM1")
           (list 10 1 1.0206 0)
           (cons 41 1)
           (cons 42 1)
           (cons 43 1)
           (cons 50 0)
           (cons 70 0)
           (cons 71 0)
           (cons 44 0)
           (cons 45 0)
          )
         )
         (entmake
          (list
           (cons 0 "POINT")
           (cons 100 "AcDbEntity")
           (cons 67 0)
           (cons 8 "0")
           (cons 100 "AcDbPoint")
           (list 10 7.15 0 0)
           (cons 50 0)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 7.41263966 -0.26263966 0)
           (list 11 7.41263966 0.26263966 0)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 7.15 0 0)
           (cons 40 0.37142857)
           (cons 100 "AcDbArc")
           (cons 50 0.78539816)
           (cons 51 5.49778714)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.291 1.073452)
           (cons 40 0)
           (cons 41 0)
           (cons 42 0)
           (cons 91 0)
           (list 10 7.291 1.247548)
           (cons 40 0)
           (cons 41 0)
           (cons 42 0)
           (cons 91 0)
           (list 10 7.44752 1.3)
           (cons 40 0)
           (cons 41 0)
           (cons 42 0)
           (cons 91 0)
           (list 10 8.25248 1.3)
           (cons 40 0)
           (cons 41 0)
           (cons 42 0)
           (cons 91 0)
           (list 10 8.409 1.247548)
           (cons 40 0)
           (cons 41 0)
           (cons 42 0)
           (cons 91 0)
           (list 10 8.409 1.073452)
           (cons 40 0)
           (cons 41 0)
           (cons 42 0)
           (cons 91 0)
           (list 10 8.25248 1.021)
           (cons 40 0)
           (cons 41 0)
           (cons 42 0)
           (cons 91 0)
           (list 10 7.44752 1.021)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.291 0.570452)
           (cons 40 0)
           (cons 41 0)
           (cons 42 0)
           (cons 91 0)
           (list 10 7.291 0.744548)
           (cons 40 0)
           (cons 41 0)
           (cons 42 0)
           (cons 91 0)
           (list 10 7.44752 0.797)
           (cons 40 0)
           (cons 41 0)
           (cons 42 0)
           (cons 91 0)
           (list 10 8.25248 0.797)
           (cons 40 0)
           (cons 41 0)
           (cons 42 0)
           (cons 91 0)
           (list 10 8.409 0.744548)
           (cons 40 0)
           (cons 41 0)
           (cons 42 0)
           (cons 91 0)
           (list 10 8.409 0.570452)
           (cons 40 0)
           (cons 41 0)
           (cons 42 0)
           (cons 91 0)
           (list 10 8.25248 0.518)
           (cons 40 0)
           (cons 41 0)
           (cons 42 0)
           (cons 91 0)
           (list 10 7.44752 0.518)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.891 1.073452)
           (cons 40 0)
           (cons 41 0)
           (cons 42 0)
           (cons 91 0)
           (list 10 5.891 1.247548)
           (cons 40 0)
           (cons 41 0)
           (cons 42 0)
           (cons 91 0)
           (list 10 6.04752 1.3)
           (cons 40 0)
           (cons 41 0)
           (cons 42 0)
           (cons 91 0)
           (list 10 6.85248 1.3)
           (cons 40 0)
           (cons 41 0)
           (cons 42 0)
           (cons 91 0)
           (list 10 7.009 1.247548)
           (cons 40 0)
           (cons 41 0)
           (cons 42 0)
           (cons 91 0)
           (list 10 7.009 1.073452)
           (cons 40 0)
           (cons 41 0)
           (cons 42 0)
           (cons 91 0)
           (list 10 6.85248 1.021)
           (cons 40 0)
           (cons 41 0)
           (cons 42 0)
           (cons 91 0)
           (list 10 6.04752 1.021)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.891 0.570452)
           (cons 40 0)
           (cons 41 0)
           (cons 42 0)
           (cons 91 0)
           (list 10 5.891 0.744548)
           (cons 40 0)
           (cons 41 0)
           (cons 42 0)
           (cons 91 0)
           (list 10 6.04752 0.797)
           (cons 40 0)
           (cons 41 0)
           (cons 42 0)
           (cons 91 0)
           (list 10 6.85248 0.797)
           (cons 40 0)
           (cons 41 0)
           (cons 42 0)
           (cons 91 0)
           (list 10 7.009 0.744548)
           (cons 40 0)
           (cons 41 0)
           (cons 42 0)
           (cons 91 0)
           (list 10 7.009 0.570452)
           (cons 40 0)
           (cons 41 0)
           (cons 42 0)
           (cons 91 0)
           (list 10 6.85248 0.518)
           (cons 40 0)
           (cons 41 0)
           (cons 42 0)
           (cons 91 0)
           (list 10 6.04752 0.518)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.291 -0.744548)
           (cons 40 0)
           (cons 41 0)
           (cons 42 0)
           (cons 91 0)
           (list 10 7.291 -0.570452)
           (cons 40 0)
           (cons 41 0)
           (cons 42 0)
           (cons 91 0)
           (list 10 7.44752 -0.518)
           (cons 40 0)
           (cons 41 0)
           (cons 42 0)
           (cons 91 0)
           (list 10 8.25248 -0.518)
           (cons 40 0)
           (cons 41 0)
           (cons 42 0)
           (cons 91 0)
           (list 10 8.409 -0.570452)
           (cons 40 0)
           (cons 41 0)
           (cons 42 0)
           (cons 91 0)
           (list 10 8.409 -0.744548)
           (cons 40 0)
           (cons 41 0)
           (cons 42 0)
           (cons 91 0)
           (list 10 8.25248 -0.797)
           (cons 40 0)
           (cons 41 0)
           (cons 42 0)
           (cons 91 0)
           (list 10 7.44752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.291 -1.247548)
           (cons 40 0)
           (cons 41 0)
           (cons 42 0)
           (cons 91 0)
           (list 10 7.291 -1.073452)
           (cons 40 0)
           (cons 41 0)
           (cons 42 0)
           (cons 91 0)
           (list 10 7.44752 -1.021)
           (cons 40 0)
           (cons 41 0)
           (cons 42 0)
           (cons 91 0)
           (list 10 8.25248 -1.021)
           (cons 40 0)
           (cons 41 0)
           (cons 42 0)
           (cons 91 0)
           (list 10 8.409 -1.073452)
           (cons 40 0)
           (cons 41 0)
           (cons 42 0)
           (cons 91 0)
           (list 10 8.409 -1.247548)
           (cons 40 0)
           (cons 41 0)
           (cons 42 0)
           (cons 91 0)
           (list 10 8.25248 -1.3)
           (cons 40 0)
           (cons 41 0)
           (cons 42 0)
           (cons 91 0)
           (list 10 7.44752 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.891 -0.744548)
           (cons 40 0)
           (cons 41 0)
           (cons 42 0)
           (cons 91 0)
           (list 10 5.891 -0.570452)
           (cons 40 0)
           (cons 41 0)
           (cons 42 0)
           (cons 91 0)
           (list 10 6.04752 -0.518)
           (cons 40 0)
           (cons 41 0)
           (cons 42 0)
           (cons 91 0)
           (list 10 6.85248 -0.518)
           (cons 40 0)
           (cons 41 0)
           (cons 42 0)
           (cons 91 0)
           (list 10 7.009 -0.570452)
           (cons 40 0)
           (cons 41 0)
           (cons 42 0)
           (cons 91 0)
           (list 10 7.009 -0.744548)
           (cons 40 0)
           (cons 41 0)
           (cons 42 0)
           (cons 91 0)
           (list 10 6.85248 -0.797)
           (cons 40 0)
           (cons 41 0)
           (cons 42 0)
           (cons 91 0)
           (list 10 6.04752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.891 -1.247548)
           (cons 40 0)
           (cons 41 0)
           (cons 42 0)
           (cons 91 0)
           (list 10 5.891 -1.073452)
           (cons 40 0)
           (cons 41 0)
           (cons 42 0)
           (cons 91 0)
           (list 10 6.04752 -1.021)
           (cons 40 0)
           (cons 41 0)
           (cons 42 0)
           (cons 91 0)
           (list 10 6.85248 -1.021)
           (cons 40 0)
           (cons 41 0)
           (cons 42 0)
           (cons 91 0)
           (list 10 7.009 -1.073452)
           (cons 40 0)
           (cons 41 0)
           (cons 42 0)
           (cons 91 0)
           (list 10 7.009 -1.247548)
           (cons 40 0)
           (cons 41 0)
           (cons 42 0)
           (cons 91 0)
           (list 10 6.85248 -1.3)
           (cons 40 0)
           (cons 41 0)
           (cons 42 0)
           (cons 91 0)
           (list 10 6.04752 -1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.2 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.2 -0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.85 -0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.85 0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.2 0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.2 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 7.85 -1.3)
           (cons 40 0)
           (cons 41 0)
           (cons 42 0)
           (cons 91 0)
           (list 10 7.85 1.3)
           (cons 40 0)
           (cons 41 0)
           (cons 42 0)
           (cons 91 0)
           (list 10 0 1.3)
           (cons 40 0)
           (cons 41 0)
           (cons 42 0)
           (cons 91 0)
          )
         )
         (entmake
          (list
           (cons 0 "TEXT")
           (cons 100 "AcDbEntity")
           (cons 67 0)
           (cons 8 "0")
           (cons 100 "AcDbText")
           (list 10 1.94047619 -0.25 0)
           (cons 40 0.5)
           (cons 1 "1")
           (cons 50 0)
           (cons 41 1)
           (cons 51 0)
           (cons 7 "Standard")
           (cons 71 0)
           (cons 72 4)
           (list 11 2 0 0)
           (cons 100 "AcDbText")
           (cons 73 0)
          )
         )
         (entmake (list (cons 0 "ENDBLK")))
        )
       )
       ((= (strcase BLKNAME) (strcase "AB_INF-I-BUS"))
        (progn
         (entmake)
         (entmake
          (list
           (cons 0 "BLOCK")
           (cons 2 "AB_INF-I-BUS")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 12.2 -1.3)
           (cons 40 0)
           (cons 41 0)
           (cons 42 0)
           (cons 91 0)
           (list 10 12.2 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 12.2 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 12.2 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.942 -0.795048)
           (cons 40 0)
           (cons 41 0)
           (cons 42 0)
           (cons 91 0)
           (list 10 7.942 -0.636552)
           (cons 40 0)
           (cons 41 0)
           (cons 42 0)
           (cons 91 0)
           (list 10 8.08424 -0.5888)
           (cons 40 0)
           (cons 41 0)
           (cons 42 0)
           (cons 91 0)
           (list 10 8.81576 -0.5888)
           (cons 40 0)
           (cons 41 0)
           (cons 42 0)
           (cons 91 0)
           (list 10 8.958 -0.636552)
           (cons 40 0)
           (cons 41 0)
           (cons 42 0)
           (cons 91 0)
           (list 10 8.958 -0.795048)
           (cons 40 0)
           (cons 41 0)
           (cons 42 0)
           (cons 91 0)
           (list 10 8.81576 -0.8428)
           (cons 40 0)
           (cons 41 0)
           (cons 42 0)
           (cons 91 0)
           (list 10 8.08424 -0.8428)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.942 -1.252248)
           (cons 40 0)
           (cons 41 0)
           (cons 42 0)
           (cons 91 0)
           (list 10 7.942 -1.093752)
           (cons 40 0)
           (cons 41 0)
           (cons 42 0)
           (cons 91 0)
           (list 10 8.08424 -1.046)
           (cons 40 0)
           (cons 41 0)
           (cons 42 0)
           (cons 91 0)
           (list 10 8.81576 -1.046)
           (cons 40 0)
           (cons 41 0)
           (cons 42 0)
           (cons 91 0)
           (list 10 8.958 -1.093752)
           (cons 40 0)
           (cons 41 0)
           (cons 42 0)
           (cons 91 0)
           (list 10 8.958 -1.252248)
           (cons 40 0)
           (cons 41 0)
           (cons 42 0)
           (cons 91 0)
           (list 10 8.81576 -1.3)
           (cons 40 0)
           (cons 41 0)
           (cons 42 0)
           (cons 91 0)
           (list 10 8.08424 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.942 0.636552)
           (cons 40 0)
           (cons 41 0)
           (cons 42 0)
           (cons 91 0)
           (list 10 7.942 0.795048)
           (cons 40 0)
           (cons 41 0)
           (cons 42 0)
           (cons 91 0)
           (list 10 8.08424 0.8428)
           (cons 40 0)
           (cons 41 0)
           (cons 42 0)
           (cons 91 0)
           (list 10 8.81576 0.8428)
           (cons 40 0)
           (cons 41 0)
           (cons 42 0)
           (cons 91 0)
           (list 10 8.958 0.795048)
           (cons 40 0)
           (cons 41 0)
           (cons 42 0)
           (cons 91 0)
           (list 10 8.958 0.636552)
           (cons 40 0)
           (cons 41 0)
           (cons 42 0)
           (cons 91 0)
           (list 10 8.81576 0.5888)
           (cons 40 0)
           (cons 41 0)
           (cons 42 0)
           (cons 91 0)
           (list 10 8.08424 0.5888)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.942 1.093752)
           (cons 40 0)
           (cons 41 0)
           (cons 42 0)
           (cons 91 0)
           (list 10 7.942 1.252248)
           (cons 40 0)
           (cons 41 0)
           (cons 42 0)
           (cons 91 0)
           (list 10 8.08424 1.3)
           (cons 40 0)
           (cons 41 0)
           (cons 42 0)
           (cons 91 0)
           (list 10 8.81576 1.3)
           (cons 40 0)
           (cons 41 0)
           (cons 42 0)
           (cons 91 0)
           (list 10 8.958 1.252248)
           (cons 40 0)
           (cons 41 0)
           (cons 42 0)
           (cons 91 0)
           (list 10 8.958 1.093752)
           (cons 40 0)
           (cons 41 0)
           (cons 42 0)
           (cons 91 0)
           (list 10 8.81576 1.046)
           (cons 40 0)
           (cons 41 0)
           (cons 42 0)
           (cons 91 0)
           (list 10 8.08424 1.046)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.242 -0.795048)
           (cons 40 0)
           (cons 41 0)
           (cons 42 0)
           (cons 91 0)
           (list 10 9.242 -0.636552)
           (cons 40 0)
           (cons 41 0)
           (cons 42 0)
           (cons 91 0)
           (list 10 9.38424 -0.5888)
           (cons 40 0)
           (cons 41 0)
           (cons 42 0)
           (cons 91 0)
           (list 10 10.11576 -0.5888)
           (cons 40 0)
           (cons 41 0)
           (cons 42 0)
           (cons 91 0)
           (list 10 10.258 -0.636552)
           (cons 40 0)
           (cons 41 0)
           (cons 42 0)
           (cons 91 0)
           (list 10 10.258 -0.795048)
           (cons 40 0)
           (cons 41 0)
           (cons 42 0)
           (cons 91 0)
           (list 10 10.11576 -0.8428)
           (cons 40 0)
           (cons 41 0)
           (cons 42 0)
           (cons 91 0)
           (list 10 9.38424 -0.8428)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.242 -1.252248)
           (cons 40 0)
           (cons 41 0)
           (cons 42 0)
           (cons 91 0)
           (list 10 9.242 -1.093752)
           (cons 40 0)
           (cons 41 0)
           (cons 42 0)
           (cons 91 0)
           (list 10 9.38424 -1.046)
           (cons 40 0)
           (cons 41 0)
           (cons 42 0)
           (cons 91 0)
           (list 10 10.11576 -1.046)
           (cons 40 0)
           (cons 41 0)
           (cons 42 0)
           (cons 91 0)
           (list 10 10.258 -1.093752)
           (cons 40 0)
           (cons 41 0)
           (cons 42 0)
           (cons 91 0)
           (list 10 10.258 -1.252248)
           (cons 40 0)
           (cons 41 0)
           (cons 42 0)
           (cons 91 0)
           (list 10 10.11576 -1.3)
           (cons 40 0)
           (cons 41 0)
           (cons 42 0)
           (cons 91 0)
           (list 10 9.38424 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.242 0.636552)
           (cons 40 0)
           (cons 41 0)
           (cons 42 0)
           (cons 91 0)
           (list 10 9.242 0.795048)
           (cons 40 0)
           (cons 41 0)
           (cons 42 0)
           (cons 91 0)
           (list 10 9.38424 0.8428)
           (cons 40 0)
           (cons 41 0)
           (cons 42 0)
           (cons 91 0)
           (list 10 10.11576 0.8428)
           (cons 40 0)
           (cons 41 0)
           (cons 42 0)
           (cons 91 0)
           (list 10 10.258 0.795048)
           (cons 40 0)
           (cons 41 0)
           (cons 42 0)
           (cons 91 0)
           (list 10 10.258 0.636552)
           (cons 40 0)
           (cons 41 0)
           (cons 42 0)
           (cons 91 0)
           (list 10 10.11576 0.5888)
           (cons 40 0)
           (cons 41 0)
           (cons 42 0)
           (cons 91 0)
           (list 10 9.38424 0.5888)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.242 1.093752)
           (cons 40 0)
           (cons 41 0)
           (cons 42 0)
           (cons 91 0)
           (list 10 9.242 1.252248)
           (cons 40 0)
           (cons 41 0)
           (cons 42 0)
           (cons 91 0)
           (list 10 9.38424 1.3)
           (cons 40 0)
           (cons 41 0)
           (cons 42 0)
           (cons 91 0)
           (list 10 10.11576 1.3)
           (cons 40 0)
           (cons 41 0)
           (cons 42 0)
           (cons 91 0)
           (list 10 10.258 1.252248)
           (cons 40 0)
           (cons 41 0)
           (cons 42 0)
           (cons 91 0)
           (list 10 10.258 1.093752)
           (cons 40 0)
           (cons 41 0)
           (cons 42 0)
           (cons 91 0)
           (list 10 10.11576 1.046)
           (cons 40 0)
           (cons 41 0)
           (cons 42 0)
           (cons 91 0)
           (list 10 9.38424 1.046)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelRightM2")
           (list 10 1.8 1.046 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM2")
           (list 10 1.8 -1.046 0)
           (cons 41 1)
           (cons 42 1)
           (cons 43 1)
           (cons 50 0)
           (cons 70 0)
           (cons 71 0)
           (cons 44 0)
           (cons 45 0)
          )
         )
         (entmake
          (list
           (cons 0 "POINT")
           (cons 100 "AcDbEntity")
           (cons 67 0)
           (cons 8 "0")
           (cons 100 "AcDbPoint")
           (list 10 1.8 0 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 12.2 -1.3 0)
           (cons 50 0)
          )
         )
         (entmake
          (list
           (cons 0 "POINT")
           (cons 100 "AcDbEntity")
           (cons 67 0)
           (cons 8 "0")
           (cons 100 "AcDbPoint")
           (list 10 12.2 1.3 0)
           (cons 50 0)
          )
         )
         (entmake
          (list
           (cons 0 "POINT")
           (cons 100 "AcDbEntity")
           (cons 67 0)
           (cons 8 "0")
           (cons 100 "AcDbPoint")
           (list 10 1.8 -1.3 0)
           (cons 50 0)
          )
         )
         (entmake
          (list
           (cons 0 "POINT")
           (cons 100 "AcDbEntity")
           (cons 67 0)
           (cons 8 "0")
           (cons 100 "AcDbPoint")
           (list 10 1.8 1.3 0)
           (cons 50 0)
          )
         )
         (entmake
          (list
           (cons 0 "POINT")
           (cons 100 "AcDbEntity")
           (cons 67 0)
           (cons 8 "0")
           (cons 100 "AcDbPoint")
           (list 10 9.1 1.3 0)
           (cons 50 0)
          )
         )
         (entmake
          (list
           (cons 0 "POINT")
           (cons 100 "AcDbEntity")
           (cons 67 0)
           (cons 8 "0")
           (cons 100 "AcDbPoint")
           (list 10 9.1 -1.3 0)
           (cons 50 0)
          )
         )
         (entmake
          (list
           (cons 0 "ATTDEF")
           (cons 100 "AcDbEntity")
           (cons 67 0)
           (cons 8 "0")
           (cons 100 "AcDbText")
           (list 10 1.1 0.56666667 0)
           (cons 40 0.2)
           (cons 1 "1.800")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.1 0.23333333 0)
           (cons 40 0.2)
           (cons 1 "1.800")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.1 -0.1 0)
           (cons 40 0.2)
           (cons 1 "9.100")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.1 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.1 -0.76666667 0)
           (cons 40 0.2)
           (cons 1 "31.2")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-HeavyHaul-Pup3"))
        (progn
         (entmake)
         (entmake
          (list
           (cons 0 "BLOCK")
           (cons 2 "AB_INF-HeavyHaul-Pup3")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.762 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.059936 -0.762 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.059936 -0.32766 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.6388 -0.32766 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.6388 0.32766 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.059936 0.32766 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.059936 0.762 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 0.762 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.762 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.762 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 2.4384 0 0)
           (cons 40 0.3452368)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.6576 -0.55256176)
           (cons 40 0)
           (cons 41 0)
           (cons 42 0)
           (cons 91 0)
           (list 10 3.6576 -0.21655024)
           (cons 40 0)
           (cons 41 0)
           (cons 42 0)
           (cons 91 0)
           (list 10 3.785616 -0.115316)
           (cons 40 0)
           (cons 41 0)
           (cons 42 0)
           (cons 91 0)
           (list 10 4.443984 -0.115316)
           (cons 40 0)
           (cons 41 0)
           (cons 42 0)
           (cons 91 0)
           (list 10 4.572 -0.21655024)
           (cons 40 0)
           (cons 41 0)
           (cons 42 0)
           (cons 91 0)
           (list 10 4.572 -0.55256176)
           (cons 40 0)
           (cons 41 0)
           (cons 42 0)
           (cons 91 0)
           (list 10 4.443984 -0.653796)
           (cons 40 0)
           (cons 41 0)
           (cons 42 0)
           (cons 91 0)
           (list 10 3.785616 -0.653796)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.6576 -1.52030176)
           (cons 40 0)
           (cons 41 0)
           (cons 42 0)
           (cons 91 0)
           (list 10 3.6576 -1.18429024)
           (cons 40 0)
           (cons 41 0)
           (cons 42 0)
           (cons 91 0)
           (list 10 3.785616 -1.083056)
           (cons 40 0)
           (cons 41 0)
           (cons 42 0)
           (cons 91 0)
           (list 10 4.443984 -1.083056)
           (cons 40 0)
           (cons 41 0)
           (cons 42 0)
           (cons 91 0)
           (list 10 4.572 -1.18429024)
           (cons 40 0)
           (cons 41 0)
           (cons 42 0)
           (cons 91 0)
           (list 10 4.572 -1.52030176)
           (cons 40 0)
           (cons 41 0)
           (cons 42 0)
           (cons 91 0)
           (list 10 4.443984 -1.621536)
           (cons 40 0)
           (cons 41 0)
           (cons 42 0)
           (cons 91 0)
           (list 10 3.785616 -1.621536)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.6576 -2.48804176)
           (cons 40 0)
           (cons 41 0)
           (cons 42 0)
           (cons 91 0)
           (list 10 3.6576 -2.15203024)
           (cons 40 0)
           (cons 41 0)
           (cons 42 0)
           (cons 91 0)
           (list 10 3.785616 -2.050796)
           (cons 40 0)
           (cons 41 0)
           (cons 42 0)
           (cons 91 0)
           (list 10 4.443984 -2.050796)
           (cons 40 0)
           (cons 41 0)
           (cons 42 0)
           (cons 91 0)
           (list 10 4.572 -2.15203024)
           (cons 40 0)
           (cons 41 0)
           (cons 42 0)
           (cons 91 0)
           (list 10 4.572 -2.48804176)
           (cons 40 0)
           (cons 41 0)
           (cons 42 0)
           (cons 91 0)
           (list 10 4.443984 -2.589276)
           (cons 40 0)
           (cons 41 0)
           (cons 42 0)
           (cons 91 0)
           (list 10 3.785616 -2.589276)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.6576 0.21655024)
           (cons 40 0)
           (cons 41 0)
           (cons 42 0)
           (cons 91 0)
           (list 10 3.6576 0.55256176)
           (cons 40 0)
           (cons 41 0)
           (cons 42 0)
           (cons 91 0)
           (list 10 3.785616 0.653796)
           (cons 40 0)
           (cons 41 0)
           (cons 42 0)
           (cons 91 0)
           (list 10 4.443984 0.653796)
           (cons 40 0)
           (cons 41 0)
           (cons 42 0)
           (cons 91 0)
           (list 10 4.572 0.55256176)
           (cons 40 0)
           (cons 41 0)
           (cons 42 0)
           (cons 91 0)
           (list 10 4.572 0.21655024)
           (cons 40 0)
           (cons 41 0)
           (cons 42 0)
           (cons 91 0)
           (list 10 4.443984 0.115316)
           (cons 40 0)
           (cons 41 0)
           (cons 42 0)
           (cons 91 0)
           (list 10 3.785616 0.115316)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.6576 1.18429024)
           (cons 40 0)
           (cons 41 0)
           (cons 42 0)
           (cons 91 0)
           (list 10 3.6576 1.52030176)
           (cons 40 0)
           (cons 41 0)
           (cons 42 0)
           (cons 91 0)
           (list 10 3.785616 1.621536)
           (cons 40 0)
           (cons 41 0)
           (cons 42 0)
           (cons 91 0)
           (list 10 4.443984 1.621536)
           (cons 40 0)
           (cons 41 0)
           (cons 42 0)
           (cons 91 0)
           (list 10 4.572 1.52030176)
           (cons 40 0)
           (cons 41 0)
           (cons 42 0)
           (cons 91 0)
           (list 10 4.572 1.18429024)
           (cons 40 0)
           (cons 41 0)
           (cons 42 0)
           (cons 91 0)
           (list 10 4.443984 1.083056)
           (cons 40 0)
           (cons 41 0)
           (cons 42 0)
           (cons 91 0)
           (list 10 3.785616 1.083056)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.6576 2.15203024)
           (cons 40 0)
           (cons 41 0)
           (cons 42 0)
           (cons 91 0)
           (list 10 3.6576 2.48804176)
           (cons 40 0)
           (cons 41 0)
           (cons 42 0)
           (cons 91 0)
           (list 10 3.785616 2.589276)
           (cons 40 0)
           (cons 41 0)
           (cons 42 0)
           (cons 91 0)
           (list 10 4.443984 2.589276)
           (cons 40 0)
           (cons 41 0)
           (cons 42 0)
           (cons 91 0)
           (list 10 4.572 2.48804176)
           (cons 40 0)
           (cons 41 0)
           (cons 42 0)
           (cons 91 0)
           (list 10 4.572 2.15203024)
           (cons 40 0)
           (cons 41 0)
           (cons 42 0)
           (cons 91 0)
           (list 10 4.443984 2.050796)
           (cons 40 0)
           (cons 41 0)
           (cons 42 0)
           (cons 91 0)
           (list 10 3.785616 2.050796)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.1816 -0.55256176)
           (cons 40 0)
           (cons 41 0)
           (cons 42 0)
           (cons 91 0)
           (list 10 5.1816 -0.21655024)
           (cons 40 0)
           (cons 41 0)
           (cons 42 0)
           (cons 91 0)
           (list 10 5.309616 -0.115316)
           (cons 40 0)
           (cons 41 0)
           (cons 42 0)
           (cons 91 0)
           (list 10 5.967984 -0.115316)
           (cons 40 0)
           (cons 41 0)
           (cons 42 0)
           (cons 91 0)
           (list 10 6.096 -0.21655024)
           (cons 40 0)
           (cons 41 0)
           (cons 42 0)
           (cons 91 0)
           (list 10 6.096 -0.55256176)
           (cons 40 0)
           (cons 41 0)
           (cons 42 0)
           (cons 91 0)
           (list 10 5.967984 -0.653796)
           (cons 40 0)
           (cons 41 0)
           (cons 42 0)
           (cons 91 0)
           (list 10 5.309616 -0.653796)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.1816 -1.52030176)
           (cons 40 0)
           (cons 41 0)
           (cons 42 0)
           (cons 91 0)
           (list 10 5.1816 -1.18429024)
           (cons 40 0)
           (cons 41 0)
           (cons 42 0)
           (cons 91 0)
           (list 10 5.309616 -1.083056)
           (cons 40 0)
           (cons 41 0)
           (cons 42 0)
           (cons 91 0)
           (list 10 5.967984 -1.083056)
           (cons 40 0)
           (cons 41 0)
           (cons 42 0)
           (cons 91 0)
           (list 10 6.096 -1.18429024)
           (cons 40 0)
           (cons 41 0)
           (cons 42 0)
           (cons 91 0)
           (list 10 6.096 -1.52030176)
           (cons 40 0)
           (cons 41 0)
           (cons 42 0)
           (cons 91 0)
           (list 10 5.967984 -1.621536)
           (cons 40 0)
           (cons 41 0)
           (cons 42 0)
           (cons 91 0)
           (list 10 5.309616 -1.621536)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.1816 -2.48804176)
           (cons 40 0)
           (cons 41 0)
           (cons 42 0)
           (cons 91 0)
           (list 10 5.1816 -2.15203024)
           (cons 40 0)
           (cons 41 0)
           (cons 42 0)
           (cons 91 0)
           (list 10 5.309616 -2.050796)
           (cons 40 0)
           (cons 41 0)
           (cons 42 0)
           (cons 91 0)
           (list 10 5.967984 -2.050796)
           (cons 40 0)
           (cons 41 0)
           (cons 42 0)
           (cons 91 0)
           (list 10 6.096 -2.15203024)
           (cons 40 0)
           (cons 41 0)
           (cons 42 0)
           (cons 91 0)
           (list 10 6.096 -2.48804176)
           (cons 40 0)
           (cons 41 0)
           (cons 42 0)
           (cons 91 0)
           (list 10 5.967984 -2.589276)
           (cons 40 0)
           (cons 41 0)
           (cons 42 0)
           (cons 91 0)
           (list 10 5.309616 -2.589276)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.1816 0.21655024)
           (cons 40 0)
           (cons 41 0)
           (cons 42 0)
           (cons 91 0)
           (list 10 5.1816 0.55256176)
           (cons 40 0)
           (cons 41 0)
           (cons 42 0)
           (cons 91 0)
           (list 10 5.309616 0.653796)
           (cons 40 0)
           (cons 41 0)
           (cons 42 0)
           (cons 91 0)
           (list 10 5.967984 0.653796)
           (cons 40 0)
           (cons 41 0)
           (cons 42 0)
           (cons 91 0)
           (list 10 6.096 0.55256176)
           (cons 40 0)
           (cons 41 0)
           (cons 42 0)
           (cons 91 0)
           (list 10 6.096 0.21655024)
           (cons 40 0)
           (cons 41 0)
           (cons 42 0)
           (cons 91 0)
           (list 10 5.967984 0.115316)
           (cons 40 0)
           (cons 41 0)
           (cons 42 0)
           (cons 91 0)
           (list 10 5.309616 0.115316)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.1816 1.18429024)
           (cons 40 0)
           (cons 41 0)
           (cons 42 0)
           (cons 91 0)
           (list 10 5.1816 1.52030176)
           (cons 40 0)
           (cons 41 0)
           (cons 42 0)
           (cons 91 0)
           (list 10 5.309616 1.621536)
           (cons 40 0)
           (cons 41 0)
           (cons 42 0)
           (cons 91 0)
           (list 10 5.967984 1.621536)
           (cons 40 0)
           (cons 41 0)
           (cons 42 0)
           (cons 91 0)
           (list 10 6.096 1.52030176)
           (cons 40 0)
           (cons 41 0)
           (cons 42 0)
           (cons 91 0)
           (list 10 6.096 1.18429024)
           (cons 40 0)
           (cons 41 0)
           (cons 42 0)
           (cons 91 0)
           (list 10 5.967984 1.083056)
           (cons 40 0)
           (cons 41 0)
           (cons 42 0)
           (cons 91 0)
           (list 10 5.309616 1.083056)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.1816 2.15203024)
           (cons 40 0)
           (cons 41 0)
           (cons 42 0)
           (cons 91 0)
           (list 10 5.1816 2.48804176)
           (cons 40 0)
           (cons 41 0)
           (cons 42 0)
           (cons 91 0)
           (list 10 5.309616 2.589276)
           (cons 40 0)
           (cons 41 0)
           (cons 42 0)
           (cons 91 0)
           (list 10 5.967984 2.589276)
           (cons 40 0)
           (cons 41 0)
           (cons 42 0)
           (cons 91 0)
           (list 10 6.096 2.48804176)
           (cons 40 0)
           (cons 41 0)
           (cons 42 0)
           (cons 91 0)
           (list 10 6.096 2.15203024)
           (cons 40 0)
           (cons 41 0)
           (cons 42 0)
           (cons 91 0)
           (list 10 5.967984 2.050796)
           (cons 40 0)
           (cons 41 0)
           (cons 42 0)
           (cons 91 0)
           (list 10 5.309616 2.050796)
           (cons 40 0)
           (cons 41 0)
           (cons 42 0)
           (cons 91 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 -1.2192 2.589276)
           (cons 40 0)
           (cons 41 0)
           (cons 42 0)
           (cons 91 0)
           (list 10 6.096 2.589276)
           (cons 40 0)
           (cons 41 0)
           (cons 42 0)
           (cons 91 0)
           (list 10 6.096 -2.589276)
           (cons 40 0)
           (cons 41 0)
           (cons 42 0)
           (cons 91 0)
           (list 10 -1.2192 -2.589276)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 4.8768 2.589276 0)
           (cons 50 0)
          )
         )
         (entmake
          (list
           (cons 0 "POINT")
           (cons 100 "AcDbEntity")
           (cons 67 0)
           (cons 8 "0")
           (cons 100 "AcDbPoint")
           (list 10 0 2.589276 0)
           (cons 50 0)
          )
         )
         (entmake
          (list
           (cons 0 "POINT")
           (cons 100 "AcDbEntity")
           (cons 67 0)
           (cons 8 "0")
           (cons 100 "AcDbPoint")
           (list 10 4.8768 -2.589276 0)
           (cons 50 0)
          )
         )
         (entmake
          (list
           (cons 0 "POINT")
           (cons 100 "AcDbEntity")
           (cons 67 0)
           (cons 8 "0")
           (cons 100 "AcDbPoint")
           (list 10 0 -2.589276 0)
           (cons 50 0)
          )
         )
         (entmake
          (list
           (cons 0 "ATTDEF")
           (cons 100 "AcDbEntity")
           (cons 67 0)
           (cons 8 "0")
           (cons 100 "AcDbText")
           (list 10 -0.3 0.56666667 0)
           (cons 40 0.2)
           (cons 1 "2.44")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 0.23333333 0)
           (cons 40 0.2)
           (cons 1 "0.00")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.1 0)
           (cons 40 0.2)
           (cons 1 "4.88")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.43333333 0)
           (cons 40 0.2)
           (cons 1 "0.0")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "POINT")
           (cons 100 "AcDbEntity")
           (cons 67 0)
           (cons 8 "0")
           (cons 100 "AcDbPoint")
           (list 10 2.4384 0 0)
           (cons 50 0)
          )
         )
         (entmake
          (list
           (cons 0 "ATTDEF")
           (cons 100 "AcDbEntity")
           (cons 67 0)
           (cons 8 "0")
           (cons 100 "AcDbText")
           (list 10 -0.3 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "Wheel5")
           (list 10 -0.762 0 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "Wheel5")
           (list 10 0.762 0 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "AB_INF-HeavyHaul-Trailer"))
        (progn
         (entmake)
         (entmake
          (list
           (cons 0 "BLOCK")
           (cons 2 "AB_INF-HeavyHaul-Trailer")
           (cons 70 2)
           (cons 4 "")
           (list 10 0 0 0)
          )
         )
         (entmake
          (list
           (cons 0 "POLYLINE")
           (cons 100 "AcDbEntity")
           (cons 67 0)
           (cons 8 "0")
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 100 "AcDbVertex")
           (cons 100 "AcDb2dVertex")
           (list 10 0 -1.830324 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 100 "AcDbVertex")
           (cons 100 "AcDb2dVertex")
           (list 10 28.6512 -1.830324 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 100 "AcDbVertex")
           (cons 100 "AcDb2dVertex")
           (list 10 28.6512 1.830324 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 100 "AcDbVertex")
           (cons 100 "AcDb2dVertex")
           (list 10 0 1.830324 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 100 "AcDbVertex")
           (cons 100 "AcDb2dVertex")
           (list 10 0 -1.830324 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 100 "AcDbVertex")
           (cons 100 "AcDb2dVertex")
           (list 10 0 -1.830324 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 0 1.830324 0)
           (cons 50 0)
          )
         )
         (entmake
          (list
           (cons 0 "POINT")
           (cons 100 "AcDbEntity")
           (cons 67 0)
           (cons 8 "0")
           (cons 100 "AcDbPoint")
           (list 10 0 -1.830324 0)
           (cons 50 0)
          )
         )
         (entmake
          (list
           (cons 0 "POINT")
           (cons 100 "AcDbEntity")
           (cons 67 0)
           (cons 8 "0")
           (cons 100 "AcDbPoint")
           (list 10 27.1272 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 1.830324)
           (cons 40 0)
           (cons 41 0)
           (cons 42 0)
           (cons 91 0)
           (list 10 28.6512 1.830324)
           (cons 40 0)
           (cons 41 0)
           (cons 42 0)
           (cons 91 0)
           (list 10 28.6512 -1.830324)
           (cons 40 0)
           (cons 41 0)
           (cons 42 0)
           (cons 91 0)
           (list 10 0 -1.830324)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 28.6512 -1.830324 0)
           (cons 50 0)
          )
         )
         (entmake
          (list
           (cons 0 "POINT")
           (cons 100 "AcDbEntity")
           (cons 67 0)
           (cons 8 "0")
           (cons 100 "AcDbPoint")
           (list 10 28.6512 1.830324 0)
           (cons 50 0)
          )
         )
         (entmake
          (list
           (cons 0 "POINT")
           (cons 100 "AcDbEntity")
           (cons 67 0)
           (cons 8 "0")
           (cons 100 "AcDbPoint")
           (list 10 14.33 0 0)
           (cons 50 0)
          )
         )
         (entmake
          (list
           (cons 0 "ATTDEF")
           (cons 100 "AcDbEntity")
           (cons 67 0)
           (cons 8 "0")
           (cons 100 "AcDbText")
           (list 10 -0.3 0.56666667 0)
           (cons 40 0.2)
           (cons 1 "0.0")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 0.23333333 0)
           (cons 40 0.2)
           (cons 1 "0.0")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.1 0)
           (cons 40 0.2)
           (cons 1 "14.33")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.43333333 0)
           (cons 40 0.2)
           (cons 1 "27.13")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-HeavyHaul-Pup2"))
        (progn
         (entmake)
         (entmake
          (list
           (cons 0 "BLOCK")
           (cons 2 "AB_INF-HeavyHaul-Pup2")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.762 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.059936 -0.762 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.059936 -0.338328 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.6388 -0.338328 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.6388 0.338328 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.059936 0.338328 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.059936 0.762 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 0.762 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.762 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.762 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.20714208)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 2.4384 0 0)
           (cons 40 0.73979314)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 2.96151275 -0.52311275 0)
           (list 11 2.96151275 0.52311275 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.6576 -0.55811928)
           (cons 40 0)
           (cons 41 0)
           (cons 42 0)
           (cons 91 0)
           (list 10 3.6576 -0.22369272)
           (cons 40 0)
           (cons 41 0)
           (cons 42 0)
           (cons 91 0)
           (list 10 3.785616 -0.122936)
           (cons 40 0)
           (cons 41 0)
           (cons 42 0)
           (cons 91 0)
           (list 10 4.443984 -0.122936)
           (cons 40 0)
           (cons 41 0)
           (cons 42 0)
           (cons 91 0)
           (list 10 4.572 -0.22369272)
           (cons 40 0)
           (cons 41 0)
           (cons 42 0)
           (cons 91 0)
           (list 10 4.572 -0.55811928)
           (cons 40 0)
           (cons 41 0)
           (cons 42 0)
           (cons 91 0)
           (list 10 4.443984 -0.658876)
           (cons 40 0)
           (cons 41 0)
           (cons 42 0)
           (cons 91 0)
           (list 10 3.785616 -0.658876)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.6576 -1.52331928)
           (cons 40 0)
           (cons 41 0)
           (cons 42 0)
           (cons 91 0)
           (list 10 3.6576 -1.18889272)
           (cons 40 0)
           (cons 41 0)
           (cons 42 0)
           (cons 91 0)
           (list 10 3.785616 -1.088136)
           (cons 40 0)
           (cons 41 0)
           (cons 42 0)
           (cons 91 0)
           (list 10 4.443984 -1.088136)
           (cons 40 0)
           (cons 41 0)
           (cons 42 0)
           (cons 91 0)
           (list 10 4.572 -1.18889272)
           (cons 40 0)
           (cons 41 0)
           (cons 42 0)
           (cons 91 0)
           (list 10 4.572 -1.52331928)
           (cons 40 0)
           (cons 41 0)
           (cons 42 0)
           (cons 91 0)
           (list 10 4.443984 -1.624076)
           (cons 40 0)
           (cons 41 0)
           (cons 42 0)
           (cons 91 0)
           (list 10 3.785616 -1.624076)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.6576 -2.48851928)
           (cons 40 0)
           (cons 41 0)
           (cons 42 0)
           (cons 91 0)
           (list 10 3.6576 -2.15409272)
           (cons 40 0)
           (cons 41 0)
           (cons 42 0)
           (cons 91 0)
           (list 10 3.785616 -2.053336)
           (cons 40 0)
           (cons 41 0)
           (cons 42 0)
           (cons 91 0)
           (list 10 4.443984 -2.053336)
           (cons 40 0)
           (cons 41 0)
           (cons 42 0)
           (cons 91 0)
           (list 10 4.572 -2.15409272)
           (cons 40 0)
           (cons 41 0)
           (cons 42 0)
           (cons 91 0)
           (list 10 4.572 -2.48851928)
           (cons 40 0)
           (cons 41 0)
           (cons 42 0)
           (cons 91 0)
           (list 10 4.443984 -2.589276)
           (cons 40 0)
           (cons 41 0)
           (cons 42 0)
           (cons 91 0)
           (list 10 3.785616 -2.589276)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.6576 0.22369272)
           (cons 40 0)
           (cons 41 0)
           (cons 42 0)
           (cons 91 0)
           (list 10 3.6576 0.55811928)
           (cons 40 0)
           (cons 41 0)
           (cons 42 0)
           (cons 91 0)
           (list 10 3.785616 0.658876)
           (cons 40 0)
           (cons 41 0)
           (cons 42 0)
           (cons 91 0)
           (list 10 4.443984 0.658876)
           (cons 40 0)
           (cons 41 0)
           (cons 42 0)
           (cons 91 0)
           (list 10 4.572 0.55811928)
           (cons 40 0)
           (cons 41 0)
           (cons 42 0)
           (cons 91 0)
           (list 10 4.572 0.22369272)
           (cons 40 0)
           (cons 41 0)
           (cons 42 0)
           (cons 91 0)
           (list 10 4.443984 0.122936)
           (cons 40 0)
           (cons 41 0)
           (cons 42 0)
           (cons 91 0)
           (list 10 3.785616 0.122936)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.6576 1.18889272)
           (cons 40 0)
           (cons 41 0)
           (cons 42 0)
           (cons 91 0)
           (list 10 3.6576 1.52331928)
           (cons 40 0)
           (cons 41 0)
           (cons 42 0)
           (cons 91 0)
           (list 10 3.785616 1.624076)
           (cons 40 0)
           (cons 41 0)
           (cons 42 0)
           (cons 91 0)
           (list 10 4.443984 1.624076)
           (cons 40 0)
           (cons 41 0)
           (cons 42 0)
           (cons 91 0)
           (list 10 4.572 1.52331928)
           (cons 40 0)
           (cons 41 0)
           (cons 42 0)
           (cons 91 0)
           (list 10 4.572 1.18889272)
           (cons 40 0)
           (cons 41 0)
           (cons 42 0)
           (cons 91 0)
           (list 10 4.443984 1.088136)
           (cons 40 0)
           (cons 41 0)
           (cons 42 0)
           (cons 91 0)
           (list 10 3.785616 1.088136)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.6576 2.15409272)
           (cons 40 0)
           (cons 41 0)
           (cons 42 0)
           (cons 91 0)
           (list 10 3.6576 2.48851928)
           (cons 40 0)
           (cons 41 0)
           (cons 42 0)
           (cons 91 0)
           (list 10 3.785616 2.589276)
           (cons 40 0)
           (cons 41 0)
           (cons 42 0)
           (cons 91 0)
           (list 10 4.443984 2.589276)
           (cons 40 0)
           (cons 41 0)
           (cons 42 0)
           (cons 91 0)
           (list 10 4.572 2.48851928)
           (cons 40 0)
           (cons 41 0)
           (cons 42 0)
           (cons 91 0)
           (list 10 4.572 2.15409272)
           (cons 40 0)
           (cons 41 0)
           (cons 42 0)
           (cons 91 0)
           (list 10 4.443984 2.053336)
           (cons 40 0)
           (cons 41 0)
           (cons 42 0)
           (cons 91 0)
           (list 10 3.785616 2.053336)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.1816 -0.55811928)
           (cons 40 0)
           (cons 41 0)
           (cons 42 0)
           (cons 91 0)
           (list 10 5.1816 -0.22369272)
           (cons 40 0)
           (cons 41 0)
           (cons 42 0)
           (cons 91 0)
           (list 10 5.309616 -0.122936)
           (cons 40 0)
           (cons 41 0)
           (cons 42 0)
           (cons 91 0)
           (list 10 5.967984 -0.122936)
           (cons 40 0)
           (cons 41 0)
           (cons 42 0)
           (cons 91 0)
           (list 10 6.096 -0.22369272)
           (cons 40 0)
           (cons 41 0)
           (cons 42 0)
           (cons 91 0)
           (list 10 6.096 -0.55811928)
           (cons 40 0)
           (cons 41 0)
           (cons 42 0)
           (cons 91 0)
           (list 10 5.967984 -0.658876)
           (cons 40 0)
           (cons 41 0)
           (cons 42 0)
           (cons 91 0)
           (list 10 5.309616 -0.658876)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.1816 -1.52331928)
           (cons 40 0)
           (cons 41 0)
           (cons 42 0)
           (cons 91 0)
           (list 10 5.1816 -1.18889272)
           (cons 40 0)
           (cons 41 0)
           (cons 42 0)
           (cons 91 0)
           (list 10 5.309616 -1.088136)
           (cons 40 0)
           (cons 41 0)
           (cons 42 0)
           (cons 91 0)
           (list 10 5.967984 -1.088136)
           (cons 40 0)
           (cons 41 0)
           (cons 42 0)
           (cons 91 0)
           (list 10 6.096 -1.18889272)
           (cons 40 0)
           (cons 41 0)
           (cons 42 0)
           (cons 91 0)
           (list 10 6.096 -1.52331928)
           (cons 40 0)
           (cons 41 0)
           (cons 42 0)
           (cons 91 0)
           (list 10 5.967984 -1.624076)
           (cons 40 0)
           (cons 41 0)
           (cons 42 0)
           (cons 91 0)
           (list 10 5.309616 -1.624076)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.1816 -2.48851928)
           (cons 40 0)
           (cons 41 0)
           (cons 42 0)
           (cons 91 0)
           (list 10 5.1816 -2.15409272)
           (cons 40 0)
           (cons 41 0)
           (cons 42 0)
           (cons 91 0)
           (list 10 5.309616 -2.053336)
           (cons 40 0)
           (cons 41 0)
           (cons 42 0)
           (cons 91 0)
           (list 10 5.967984 -2.053336)
           (cons 40 0)
           (cons 41 0)
           (cons 42 0)
           (cons 91 0)
           (list 10 6.096 -2.15409272)
           (cons 40 0)
           (cons 41 0)
           (cons 42 0)
           (cons 91 0)
           (list 10 6.096 -2.48851928)
           (cons 40 0)
           (cons 41 0)
           (cons 42 0)
           (cons 91 0)
           (list 10 5.967984 -2.589276)
           (cons 40 0)
           (cons 41 0)
           (cons 42 0)
           (cons 91 0)
           (list 10 5.309616 -2.589276)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.1816 0.22369272)
           (cons 40 0)
           (cons 41 0)
           (cons 42 0)
           (cons 91 0)
           (list 10 5.1816 0.55811928)
           (cons 40 0)
           (cons 41 0)
           (cons 42 0)
           (cons 91 0)
           (list 10 5.309616 0.658876)
           (cons 40 0)
           (cons 41 0)
           (cons 42 0)
           (cons 91 0)
           (list 10 5.967984 0.658876)
           (cons 40 0)
           (cons 41 0)
           (cons 42 0)
           (cons 91 0)
           (list 10 6.096 0.55811928)
           (cons 40 0)
           (cons 41 0)
           (cons 42 0)
           (cons 91 0)
           (list 10 6.096 0.22369272)
           (cons 40 0)
           (cons 41 0)
           (cons 42 0)
           (cons 91 0)
           (list 10 5.967984 0.122936)
           (cons 40 0)
           (cons 41 0)
           (cons 42 0)
           (cons 91 0)
           (list 10 5.309616 0.122936)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.1816 1.18889272)
           (cons 40 0)
           (cons 41 0)
           (cons 42 0)
           (cons 91 0)
           (list 10 5.1816 1.52331928)
           (cons 40 0)
           (cons 41 0)
           (cons 42 0)
           (cons 91 0)
           (list 10 5.309616 1.624076)
           (cons 40 0)
           (cons 41 0)
           (cons 42 0)
           (cons 91 0)
           (list 10 5.967984 1.624076)
           (cons 40 0)
           (cons 41 0)
           (cons 42 0)
           (cons 91 0)
           (list 10 6.096 1.52331928)
           (cons 40 0)
           (cons 41 0)
           (cons 42 0)
           (cons 91 0)
           (list 10 6.096 1.18889272)
           (cons 40 0)
           (cons 41 0)
           (cons 42 0)
           (cons 91 0)
           (list 10 5.967984 1.088136)
           (cons 40 0)
           (cons 41 0)
           (cons 42 0)
           (cons 91 0)
           (list 10 5.309616 1.088136)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.1816 2.15409272)
           (cons 40 0)
           (cons 41 0)
           (cons 42 0)
           (cons 91 0)
           (list 10 5.1816 2.48851928)
           (cons 40 0)
           (cons 41 0)
           (cons 42 0)
           (cons 91 0)
           (list 10 5.309616 2.589276)
           (cons 40 0)
           (cons 41 0)
           (cons 42 0)
           (cons 91 0)
           (list 10 5.967984 2.589276)
           (cons 40 0)
           (cons 41 0)
           (cons 42 0)
           (cons 91 0)
           (list 10 6.096 2.48851928)
           (cons 40 0)
           (cons 41 0)
           (cons 42 0)
           (cons 91 0)
           (list 10 6.096 2.15409272)
           (cons 40 0)
           (cons 41 0)
           (cons 42 0)
           (cons 91 0)
           (list 10 5.967984 2.053336)
           (cons 40 0)
           (cons 41 0)
           (cons 42 0)
           (cons 91 0)
           (list 10 5.309616 2.053336)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 2.4384 0 0)
           (cons 50 0)
          )
         )
         (entmake
          (list
           (cons 0 "POINT")
           (cons 100 "AcDbEntity")
           (cons 67 0)
           (cons 8 "0")
           (cons 100 "AcDbPoint")
           (list 10 4.8768 -2.589276 0)
           (cons 50 0)
          )
         )
         (entmake
          (list
           (cons 0 "POINT")
           (cons 100 "AcDbEntity")
           (cons 67 0)
           (cons 8 "0")
           (cons 100 "AcDbPoint")
           (list 10 4.8768 2.589276 0)
           (cons 50 0)
          )
         )
         (entmake
          (list
           (cons 0 "POINT")
           (cons 100 "AcDbEntity")
           (cons 67 0)
           (cons 8 "0")
           (cons 100 "AcDbPoint")
           (list 10 4.8768 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 3.6576 2.589276)
           (cons 40 0)
           (cons 41 0)
           (cons 42 0)
           (cons 91 0)
           (list 10 6.099048 2.589276)
           (cons 40 0)
           (cons 41 0)
           (cons 42 0)
           (cons 91 0)
           (list 10 6.099048 -2.589276)
           (cons 40 0)
           (cons 41 0)
           (cons 42 0)
           (cons 91 0)
           (list 10 3.6576 -2.589276)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 -0.3 0.56666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 0.23333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.1 0)
           (cons 40 0.2)
           (cons 1 "4.88")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.43333333 0)
           (cons 40 0.2)
           (cons 1 "2.44")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-HeavyHaul-Pup1"))
        (progn
         (entmake)
         (entmake
          (list
           (cons 0 "BLOCK")
           (cons 2 "AB_INF-HeavyHaul-Pup1")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.762 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.059936 -0.762 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.059936 -0.370332 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.641848 -0.370332 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.641848 0.370332 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.059936 0.370332 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 4.059936 0.762 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 0.762 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.762 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.762 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.20714208)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 4.879848 0 0)
           (cons 40 0.73979314)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 5.40296075 -0.52311275 0)
           (list 11 5.40296075 0.52311275 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.660648 -0.57479184)
           (cons 40 0)
           (cons 41 0)
           (cons 42 0)
           (cons 91 0)
           (list 10 3.660648 -0.24512016)
           (cons 40 0)
           (cons 41 0)
           (cons 42 0)
           (cons 91 0)
           (list 10 3.788664 -0.145796)
           (cons 40 0)
           (cons 41 0)
           (cons 42 0)
           (cons 91 0)
           (list 10 4.447032 -0.145796)
           (cons 40 0)
           (cons 41 0)
           (cons 42 0)
           (cons 91 0)
           (list 10 4.575048 -0.24512016)
           (cons 40 0)
           (cons 41 0)
           (cons 42 0)
           (cons 91 0)
           (list 10 4.575048 -0.57479184)
           (cons 40 0)
           (cons 41 0)
           (cons 42 0)
           (cons 91 0)
           (list 10 4.447032 -0.674116)
           (cons 40 0)
           (cons 41 0)
           (cons 42 0)
           (cons 91 0)
           (list 10 3.788664 -0.674116)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.660648 -1.53237184)
           (cons 40 0)
           (cons 41 0)
           (cons 42 0)
           (cons 91 0)
           (list 10 3.660648 -1.20270016)
           (cons 40 0)
           (cons 41 0)
           (cons 42 0)
           (cons 91 0)
           (list 10 3.788664 -1.103376)
           (cons 40 0)
           (cons 41 0)
           (cons 42 0)
           (cons 91 0)
           (list 10 4.447032 -1.103376)
           (cons 40 0)
           (cons 41 0)
           (cons 42 0)
           (cons 91 0)
           (list 10 4.575048 -1.20270016)
           (cons 40 0)
           (cons 41 0)
           (cons 42 0)
           (cons 91 0)
           (list 10 4.575048 -1.53237184)
           (cons 40 0)
           (cons 41 0)
           (cons 42 0)
           (cons 91 0)
           (list 10 4.447032 -1.631696)
           (cons 40 0)
           (cons 41 0)
           (cons 42 0)
           (cons 91 0)
           (list 10 3.788664 -1.631696)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.660648 -2.48995184)
           (cons 40 0)
           (cons 41 0)
           (cons 42 0)
           (cons 91 0)
           (list 10 3.660648 -2.16028016)
           (cons 40 0)
           (cons 41 0)
           (cons 42 0)
           (cons 91 0)
           (list 10 3.788664 -2.060956)
           (cons 40 0)
           (cons 41 0)
           (cons 42 0)
           (cons 91 0)
           (list 10 4.447032 -2.060956)
           (cons 40 0)
           (cons 41 0)
           (cons 42 0)
           (cons 91 0)
           (list 10 4.575048 -2.16028016)
           (cons 40 0)
           (cons 41 0)
           (cons 42 0)
           (cons 91 0)
           (list 10 4.575048 -2.48995184)
           (cons 40 0)
           (cons 41 0)
           (cons 42 0)
           (cons 91 0)
           (list 10 4.447032 -2.589276)
           (cons 40 0)
           (cons 41 0)
           (cons 42 0)
           (cons 91 0)
           (list 10 3.788664 -2.589276)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.660648 0.24512016)
           (cons 40 0)
           (cons 41 0)
           (cons 42 0)
           (cons 91 0)
           (list 10 3.660648 0.57479184)
           (cons 40 0)
           (cons 41 0)
           (cons 42 0)
           (cons 91 0)
           (list 10 3.788664 0.674116)
           (cons 40 0)
           (cons 41 0)
           (cons 42 0)
           (cons 91 0)
           (list 10 4.447032 0.674116)
           (cons 40 0)
           (cons 41 0)
           (cons 42 0)
           (cons 91 0)
           (list 10 4.575048 0.57479184)
           (cons 40 0)
           (cons 41 0)
           (cons 42 0)
           (cons 91 0)
           (list 10 4.575048 0.24512016)
           (cons 40 0)
           (cons 41 0)
           (cons 42 0)
           (cons 91 0)
           (list 10 4.447032 0.145796)
           (cons 40 0)
           (cons 41 0)
           (cons 42 0)
           (cons 91 0)
           (list 10 3.788664 0.145796)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.660648 1.20270016)
           (cons 40 0)
           (cons 41 0)
           (cons 42 0)
           (cons 91 0)
           (list 10 3.660648 1.53237184)
           (cons 40 0)
           (cons 41 0)
           (cons 42 0)
           (cons 91 0)
           (list 10 3.788664 1.631696)
           (cons 40 0)
           (cons 41 0)
           (cons 42 0)
           (cons 91 0)
           (list 10 4.447032 1.631696)
           (cons 40 0)
           (cons 41 0)
           (cons 42 0)
           (cons 91 0)
           (list 10 4.575048 1.53237184)
           (cons 40 0)
           (cons 41 0)
           (cons 42 0)
           (cons 91 0)
           (list 10 4.575048 1.20270016)
           (cons 40 0)
           (cons 41 0)
           (cons 42 0)
           (cons 91 0)
           (list 10 4.447032 1.103376)
           (cons 40 0)
           (cons 41 0)
           (cons 42 0)
           (cons 91 0)
           (list 10 3.788664 1.103376)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.660648 2.16028016)
           (cons 40 0)
           (cons 41 0)
           (cons 42 0)
           (cons 91 0)
           (list 10 3.660648 2.48995184)
           (cons 40 0)
           (cons 41 0)
           (cons 42 0)
           (cons 91 0)
           (list 10 3.788664 2.589276)
           (cons 40 0)
           (cons 41 0)
           (cons 42 0)
           (cons 91 0)
           (list 10 4.447032 2.589276)
           (cons 40 0)
           (cons 41 0)
           (cons 42 0)
           (cons 91 0)
           (list 10 4.575048 2.48995184)
           (cons 40 0)
           (cons 41 0)
           (cons 42 0)
           (cons 91 0)
           (list 10 4.575048 2.16028016)
           (cons 40 0)
           (cons 41 0)
           (cons 42 0)
           (cons 91 0)
           (list 10 4.447032 2.060956)
           (cons 40 0)
           (cons 41 0)
           (cons 42 0)
           (cons 91 0)
           (list 10 3.788664 2.060956)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.184648 -0.57479184)
           (cons 40 0)
           (cons 41 0)
           (cons 42 0)
           (cons 91 0)
           (list 10 5.184648 -0.24512016)
           (cons 40 0)
           (cons 41 0)
           (cons 42 0)
           (cons 91 0)
           (list 10 5.312664 -0.145796)
           (cons 40 0)
           (cons 41 0)
           (cons 42 0)
           (cons 91 0)
           (list 10 5.971032 -0.145796)
           (cons 40 0)
           (cons 41 0)
           (cons 42 0)
           (cons 91 0)
           (list 10 6.099048 -0.24512016)
           (cons 40 0)
           (cons 41 0)
           (cons 42 0)
           (cons 91 0)
           (list 10 6.099048 -0.57479184)
           (cons 40 0)
           (cons 41 0)
           (cons 42 0)
           (cons 91 0)
           (list 10 5.971032 -0.674116)
           (cons 40 0)
           (cons 41 0)
           (cons 42 0)
           (cons 91 0)
           (list 10 5.312664 -0.674116)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.184648 -1.53237184)
           (cons 40 0)
           (cons 41 0)
           (cons 42 0)
           (cons 91 0)
           (list 10 5.184648 -1.20270016)
           (cons 40 0)
           (cons 41 0)
           (cons 42 0)
           (cons 91 0)
           (list 10 5.312664 -1.103376)
           (cons 40 0)
           (cons 41 0)
           (cons 42 0)
           (cons 91 0)
           (list 10 5.971032 -1.103376)
           (cons 40 0)
           (cons 41 0)
           (cons 42 0)
           (cons 91 0)
           (list 10 6.099048 -1.20270016)
           (cons 40 0)
           (cons 41 0)
           (cons 42 0)
           (cons 91 0)
           (list 10 6.099048 -1.53237184)
           (cons 40 0)
           (cons 41 0)
           (cons 42 0)
           (cons 91 0)
           (list 10 5.971032 -1.631696)
           (cons 40 0)
           (cons 41 0)
           (cons 42 0)
           (cons 91 0)
           (list 10 5.312664 -1.631696)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.184648 -2.48995184)
           (cons 40 0)
           (cons 41 0)
           (cons 42 0)
           (cons 91 0)
           (list 10 5.184648 -2.16028016)
           (cons 40 0)
           (cons 41 0)
           (cons 42 0)
           (cons 91 0)
           (list 10 5.312664 -2.060956)
           (cons 40 0)
           (cons 41 0)
           (cons 42 0)
           (cons 91 0)
           (list 10 5.971032 -2.060956)
           (cons 40 0)
           (cons 41 0)
           (cons 42 0)
           (cons 91 0)
           (list 10 6.099048 -2.16028016)
           (cons 40 0)
           (cons 41 0)
           (cons 42 0)
           (cons 91 0)
           (list 10 6.099048 -2.48995184)
           (cons 40 0)
           (cons 41 0)
           (cons 42 0)
           (cons 91 0)
           (list 10 5.971032 -2.589276)
           (cons 40 0)
           (cons 41 0)
           (cons 42 0)
           (cons 91 0)
           (list 10 5.312664 -2.589276)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.184648 0.24512016)
           (cons 40 0)
           (cons 41 0)
           (cons 42 0)
           (cons 91 0)
           (list 10 5.184648 0.57479184)
           (cons 40 0)
           (cons 41 0)
           (cons 42 0)
           (cons 91 0)
           (list 10 5.312664 0.674116)
           (cons 40 0)
           (cons 41 0)
           (cons 42 0)
           (cons 91 0)
           (list 10 5.971032 0.674116)
           (cons 40 0)
           (cons 41 0)
           (cons 42 0)
           (cons 91 0)
           (list 10 6.099048 0.57479184)
           (cons 40 0)
           (cons 41 0)
           (cons 42 0)
           (cons 91 0)
           (list 10 6.099048 0.24512016)
           (cons 40 0)
           (cons 41 0)
           (cons 42 0)
           (cons 91 0)
           (list 10 5.971032 0.145796)
           (cons 40 0)
           (cons 41 0)
           (cons 42 0)
           (cons 91 0)
           (list 10 5.312664 0.145796)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.184648 1.20270016)
           (cons 40 0)
           (cons 41 0)
           (cons 42 0)
           (cons 91 0)
           (list 10 5.184648 1.53237184)
           (cons 40 0)
           (cons 41 0)
           (cons 42 0)
           (cons 91 0)
           (list 10 5.312664 1.631696)
           (cons 40 0)
           (cons 41 0)
           (cons 42 0)
           (cons 91 0)
           (list 10 5.971032 1.631696)
           (cons 40 0)
           (cons 41 0)
           (cons 42 0)
           (cons 91 0)
           (list 10 6.099048 1.53237184)
           (cons 40 0)
           (cons 41 0)
           (cons 42 0)
           (cons 91 0)
           (list 10 6.099048 1.20270016)
           (cons 40 0)
           (cons 41 0)
           (cons 42 0)
           (cons 91 0)
           (list 10 5.971032 1.103376)
           (cons 40 0)
           (cons 41 0)
           (cons 42 0)
           (cons 91 0)
           (list 10 5.312664 1.103376)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.184648 2.16028016)
           (cons 40 0)
           (cons 41 0)
           (cons 42 0)
           (cons 91 0)
           (list 10 5.184648 2.48995184)
           (cons 40 0)
           (cons 41 0)
           (cons 42 0)
           (cons 91 0)
           (list 10 5.312664 2.589276)
           (cons 40 0)
           (cons 41 0)
           (cons 42 0)
           (cons 91 0)
           (list 10 5.971032 2.589276)
           (cons 40 0)
           (cons 41 0)
           (cons 42 0)
           (cons 91 0)
           (list 10 6.099048 2.48995184)
           (cons 40 0)
           (cons 41 0)
           (cons 42 0)
           (cons 91 0)
           (list 10 6.099048 2.16028016)
           (cons 40 0)
           (cons 41 0)
           (cons 42 0)
           (cons 91 0)
           (list 10 5.971032 2.060956)
           (cons 40 0)
           (cons 41 0)
           (cons 42 0)
           (cons 91 0)
           (list 10 5.312664 2.060956)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 4.879848 0 0)
           (cons 50 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 3.660648 2.589276)
           (cons 40 0)
           (cons 41 0)
           (cons 42 0)
           (cons 91 0)
           (list 10 6.099048 2.589276)
           (cons 40 0)
           (cons 41 0)
           (cons 42 0)
           (cons 91 0)
           (list 10 6.099048 -2.589276)
           (cons 40 0)
           (cons 41 0)
           (cons 42 0)
           (cons 91 0)
           (list 10 3.660648 -2.589276)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 -0.3 0.56666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 0.23333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.1 0)
           (cons 40 0.2)
           (cons 1 "4.88")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.3 -0.43333333 0)
           (cons 40 0.2)
           (cons 1 "4.88")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "POINT")
           (cons 100 "AcDbEntity")
           (cons 67 0)
           (cons 8 "0")
           (cons 100 "AcDbPoint")
           (list 10 4.879848 2.589276 0)
           (cons 50 0)
          )
         )
         (entmake
          (list
           (cons 0 "POINT")
           (cons 100 "AcDbEntity")
           (cons 67 0)
           (cons 8 "0")
           (cons 100 "AcDbPoint")
           (list 10 4.879848 -2.589276 0)
           (cons 50 0)
          )
         )
         (entmake
          (list
           (cons 0 "ATTDEF")
           (cons 100 "AcDbEntity")
           (cons 67 0)
           (cons 8 "0")
           (cons 100 "AcDbText")
           (list 10 -0.3 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-HeavyHaul-Truck"))
        (progn
         (entmake)
         (entmake
          (list
           (cons 0 "BLOCK")
           (cons 2 "AB_INF-HeavyHaul-Truck")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2954 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.898648 -1.2954 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.898648 -0.5842 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.7216 -0.5842 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.7216 0.5842 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.898648 0.5842 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 2.898648 1.2954 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.2954 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2954 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2954 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 7.0104 0 0)
           (cons 40 0.37011429)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 7.27211032 -0.26171032 0)
           (list 11 7.27211032 0.26171032 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.7912 -0.790448)
           (cons 40 0)
           (cons 41 0)
           (cons 42 0)
           (cons 91 0)
           (list 10 5.7912 -0.631952)
           (cons 40 0)
           (cons 41 0)
           (cons 42 0)
           (cons 91 0)
           (list 10 5.93344 -0.5842)
           (cons 40 0)
           (cons 41 0)
           (cons 42 0)
           (cons 91 0)
           (list 10 6.66496 -0.5842)
           (cons 40 0)
           (cons 41 0)
           (cons 42 0)
           (cons 91 0)
           (list 10 6.8072 -0.631952)
           (cons 40 0)
           (cons 41 0)
           (cons 42 0)
           (cons 91 0)
           (list 10 6.8072 -0.790448)
           (cons 40 0)
           (cons 41 0)
           (cons 42 0)
           (cons 91 0)
           (list 10 6.66496 -0.8382)
           (cons 40 0)
           (cons 41 0)
           (cons 42 0)
           (cons 91 0)
           (list 10 5.93344 -0.8382)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.7912 -1.247648)
           (cons 40 0)
           (cons 41 0)
           (cons 42 0)
           (cons 91 0)
           (list 10 5.7912 -1.089152)
           (cons 40 0)
           (cons 41 0)
           (cons 42 0)
           (cons 91 0)
           (list 10 5.93344 -1.0414)
           (cons 40 0)
           (cons 41 0)
           (cons 42 0)
           (cons 91 0)
           (list 10 6.66496 -1.0414)
           (cons 40 0)
           (cons 41 0)
           (cons 42 0)
           (cons 91 0)
           (list 10 6.8072 -1.089152)
           (cons 40 0)
           (cons 41 0)
           (cons 42 0)
           (cons 91 0)
           (list 10 6.8072 -1.247648)
           (cons 40 0)
           (cons 41 0)
           (cons 42 0)
           (cons 91 0)
           (list 10 6.66496 -1.2954)
           (cons 40 0)
           (cons 41 0)
           (cons 42 0)
           (cons 91 0)
           (list 10 5.93344 -1.2954)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.7912 0.631952)
           (cons 40 0)
           (cons 41 0)
           (cons 42 0)
           (cons 91 0)
           (list 10 5.7912 0.790448)
           (cons 40 0)
           (cons 41 0)
           (cons 42 0)
           (cons 91 0)
           (list 10 5.93344 0.8382)
           (cons 40 0)
           (cons 41 0)
           (cons 42 0)
           (cons 91 0)
           (list 10 6.66496 0.8382)
           (cons 40 0)
           (cons 41 0)
           (cons 42 0)
           (cons 91 0)
           (list 10 6.8072 0.790448)
           (cons 40 0)
           (cons 41 0)
           (cons 42 0)
           (cons 91 0)
           (list 10 6.8072 0.631952)
           (cons 40 0)
           (cons 41 0)
           (cons 42 0)
           (cons 91 0)
           (list 10 6.66496 0.5842)
           (cons 40 0)
           (cons 41 0)
           (cons 42 0)
           (cons 91 0)
           (list 10 5.93344 0.5842)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.7912 1.089152)
           (cons 40 0)
           (cons 41 0)
           (cons 42 0)
           (cons 91 0)
           (list 10 5.7912 1.247648)
           (cons 40 0)
           (cons 41 0)
           (cons 42 0)
           (cons 91 0)
           (list 10 5.93344 1.2954)
           (cons 40 0)
           (cons 41 0)
           (cons 42 0)
           (cons 91 0)
           (list 10 6.66496 1.2954)
           (cons 40 0)
           (cons 41 0)
           (cons 42 0)
           (cons 91 0)
           (list 10 6.8072 1.247648)
           (cons 40 0)
           (cons 41 0)
           (cons 42 0)
           (cons 91 0)
           (list 10 6.8072 1.089152)
           (cons 40 0)
           (cons 41 0)
           (cons 42 0)
           (cons 91 0)
           (list 10 6.66496 1.0414)
           (cons 40 0)
           (cons 41 0)
           (cons 42 0)
           (cons 91 0)
           (list 10 5.93344 1.0414)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.2136 -0.790448)
           (cons 40 0)
           (cons 41 0)
           (cons 42 0)
           (cons 91 0)
           (list 10 7.2136 -0.631952)
           (cons 40 0)
           (cons 41 0)
           (cons 42 0)
           (cons 91 0)
           (list 10 7.35584 -0.5842)
           (cons 40 0)
           (cons 41 0)
           (cons 42 0)
           (cons 91 0)
           (list 10 8.08736 -0.5842)
           (cons 40 0)
           (cons 41 0)
           (cons 42 0)
           (cons 91 0)
           (list 10 8.2296 -0.631952)
           (cons 40 0)
           (cons 41 0)
           (cons 42 0)
           (cons 91 0)
           (list 10 8.2296 -0.790448)
           (cons 40 0)
           (cons 41 0)
           (cons 42 0)
           (cons 91 0)
           (list 10 8.08736 -0.8382)
           (cons 40 0)
           (cons 41 0)
           (cons 42 0)
           (cons 91 0)
           (list 10 7.35584 -0.8382)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.2136 -1.247648)
           (cons 40 0)
           (cons 41 0)
           (cons 42 0)
           (cons 91 0)
           (list 10 7.2136 -1.089152)
           (cons 40 0)
           (cons 41 0)
           (cons 42 0)
           (cons 91 0)
           (list 10 7.35584 -1.0414)
           (cons 40 0)
           (cons 41 0)
           (cons 42 0)
           (cons 91 0)
           (list 10 8.08736 -1.0414)
           (cons 40 0)
           (cons 41 0)
           (cons 42 0)
           (cons 91 0)
           (list 10 8.2296 -1.089152)
           (cons 40 0)
           (cons 41 0)
           (cons 42 0)
           (cons 91 0)
           (list 10 8.2296 -1.247648)
           (cons 40 0)
           (cons 41 0)
           (cons 42 0)
           (cons 91 0)
           (list 10 8.08736 -1.2954)
           (cons 40 0)
           (cons 41 0)
           (cons 42 0)
           (cons 91 0)
           (list 10 7.35584 -1.2954)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.2136 0.631952)
           (cons 40 0)
           (cons 41 0)
           (cons 42 0)
           (cons 91 0)
           (list 10 7.2136 0.790448)
           (cons 40 0)
           (cons 41 0)
           (cons 42 0)
           (cons 91 0)
           (list 10 7.35584 0.8382)
           (cons 40 0)
           (cons 41 0)
           (cons 42 0)
           (cons 91 0)
           (list 10 8.08736 0.8382)
           (cons 40 0)
           (cons 41 0)
           (cons 42 0)
           (cons 91 0)
           (list 10 8.2296 0.790448)
           (cons 40 0)
           (cons 41 0)
           (cons 42 0)
           (cons 91 0)
           (list 10 8.2296 0.631952)
           (cons 40 0)
           (cons 41 0)
           (cons 42 0)
           (cons 91 0)
           (list 10 8.08736 0.5842)
           (cons 40 0)
           (cons 41 0)
           (cons 42 0)
           (cons 91 0)
           (list 10 7.35584 0.5842)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.2136 1.089152)
           (cons 40 0)
           (cons 41 0)
           (cons 42 0)
           (cons 91 0)
           (list 10 7.2136 1.247648)
           (cons 40 0)
           (cons 41 0)
           (cons 42 0)
           (cons 91 0)
           (list 10 7.35584 1.2954)
           (cons 40 0)
           (cons 41 0)
           (cons 42 0)
           (cons 91 0)
           (list 10 8.08736 1.2954)
           (cons 40 0)
           (cons 41 0)
           (cons 42 0)
           (cons 91 0)
           (list 10 8.2296 1.247648)
           (cons 40 0)
           (cons 41 0)
           (cons 42 0)
           (cons 91 0)
           (list 10 8.2296 1.089152)
           (cons 40 0)
           (cons 41 0)
           (cons 42 0)
           (cons 91 0)
           (list 10 8.08736 1.0414)
           (cons 40 0)
           (cons 41 0)
           (cons 42 0)
           (cons 91 0)
           (list 10 7.35584 1.0414)
           (cons 40 0)
           (cons 41 0)
           (cons 42 0)
           (cons 91 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.2954)
           (cons 40 0)
           (cons 41 0)
           (cons 42 0)
           (cons 91 0)
           (list 10 7.7216 -1.2954)
           (cons 40 0)
           (cons 41 0)
           (cons 42 0)
           (cons 91 0)
           (list 10 7.7216 1.2954)
           (cons 40 0)
           (cons 41 0)
           (cons 42 0)
           (cons 91 0)
           (list 10 0 1.2954)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0.813816 0 0)
           (cons 50 0)
          )
         )
         (entmake
          (list
           (cons 0 "POINT")
           (cons 100 "AcDbEntity")
           (cons 67 0)
           (cons 8 "0")
           (cons 100 "AcDbPoint")
           (list 10 0.813816 1.2954 0)
           (cons 50 0)
          )
         )
         (entmake
          (list
           (cons 0 "POINT")
           (cons 100 "AcDbEntity")
           (cons 67 0)
           (cons 8 "0")
           (cons 100 "AcDbPoint")
           (list 10 0.813816 -1.2954 0)
           (cons 50 0)
          )
         )
         (entmake
          (list
           (cons 0 "POINT")
           (cons 100 "AcDbEntity")
           (cons 67 0)
           (cons 8 "0")
           (cons 100 "AcDbPoint")
           (list 10 7.0104 -1.2954 0)
           (cons 50 0)
          )
         )
         (entmake
          (list
           (cons 0 "POINT")
           (cons 100 "AcDbEntity")
           (cons 67 0)
           (cons 8 "0")
           (cons 100 "AcDbPoint")
           (list 10 7.0104 1.2954 0)
           (cons 50 0)
          )
         )
         (entmake
          (list
           (cons 0 "POINT")
           (cons 100 "AcDbEntity")
           (cons 67 0)
           (cons 8 "0")
           (cons 100 "AcDbPoint")
           (list 10 0 1.2954 0)
           (cons 50 0)
          )
         )
         (entmake
          (list
           (cons 0 "POINT")
           (cons 100 "AcDbEntity")
           (cons 67 0)
           (cons 8 "0")
           (cons 100 "AcDbPoint")
           (list 10 0 -1.2954 0)
           (cons 50 0)
          )
         )
         (entmake
          (list
           (cons 0 "POINT")
           (cons 100 "AcDbEntity")
           (cons 67 0)
           (cons 8 "0")
           (cons 100 "AcDbPoint")
           (list 10 7.0104 0 0)
           (cons 50 0)
          )
         )
         (entmake
          (list
           (cons 0 "ATTDEF")
           (cons 100 "AcDbEntity")
           (cons 67 0)
           (cons 8 "0")
           (cons 100 "AcDbText")
           (list 10 0.513816 0.56666667 0)
           (cons 40 0.2)
           (cons 1 "0.81")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.513816 0.23333333 0)
           (cons 40 0.2)
           (cons 1 "0.81")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.513816 -0.1 0)
           (cons 40 0.2)
           (cons 1 "7.01")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.513816 -0.43333333 0)
           (cons 40 0.2)
           (cons 1 "7.01")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.513816 -0.76666667 0)
           (cons 40 0.2)
           (cons 1 "16.8")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelLeftM2")
           (list 10 0.813816 -1.0414 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM2")
           (list 10 0.813816 1.0414 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "AB_INF-BUS"))
        (progn
         (entmake)
         (entmake
          (list
           (cons 0 "BLOCK")
           (cons 2 "AB_INF-BUS")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 12.1 -1.3)
           (cons 40 0)
           (cons 41 0)
           (cons 42 0)
           (cons 91 0)
           (list 10 12.1 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 12.1 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 12.1 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.892 -1.252248)
           (cons 40 0)
           (cons 41 0)
           (cons 42 0)
           (cons 91 0)
           (list 10 8.892 -1.093752)
           (cons 40 0)
           (cons 41 0)
           (cons 42 0)
           (cons 91 0)
           (list 10 9.03424 -1.046)
           (cons 40 0)
           (cons 41 0)
           (cons 42 0)
           (cons 91 0)
           (list 10 9.76576 -1.046)
           (cons 40 0)
           (cons 41 0)
           (cons 42 0)
           (cons 91 0)
           (list 10 9.908 -1.093752)
           (cons 40 0)
           (cons 41 0)
           (cons 42 0)
           (cons 91 0)
           (list 10 9.908 -1.252248)
           (cons 40 0)
           (cons 41 0)
           (cons 42 0)
           (cons 91 0)
           (list 10 9.76576 -1.3)
           (cons 40 0)
           (cons 41 0)
           (cons 42 0)
           (cons 91 0)
           (list 10 9.03424 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.892 1.093752)
           (cons 40 0)
           (cons 41 0)
           (cons 42 0)
           (cons 91 0)
           (list 10 8.892 1.252248)
           (cons 40 0)
           (cons 41 0)
           (cons 42 0)
           (cons 91 0)
           (list 10 9.03424 1.3)
           (cons 40 0)
           (cons 41 0)
           (cons 42 0)
           (cons 91 0)
           (list 10 9.76576 1.3)
           (cons 40 0)
           (cons 41 0)
           (cons 42 0)
           (cons 91 0)
           (list 10 9.908 1.252248)
           (cons 40 0)
           (cons 41 0)
           (cons 42 0)
           (cons 91 0)
           (list 10 9.908 1.093752)
           (cons 40 0)
           (cons 41 0)
           (cons 42 0)
           (cons 91 0)
           (list 10 9.76576 1.046)
           (cons 40 0)
           (cons 41 0)
           (cons 42 0)
           (cons 91 0)
           (list 10 9.03424 1.046)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 2.1 0 0)
           (cons 50 0)
          )
         )
         (entmake
          (list
           (cons 0 "INSERT")
           (cons 100 "AcDbEntity")
           (cons 67 0)
           (cons 8 "0")
           (cons 100 "AcDbBlockReference")
           (cons 2 "WheelLeftM2")
           (list 10 2.1 -1.046 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM2")
           (list 10 2.1 1.046 0)
           (cons 41 1)
           (cons 42 1)
           (cons 43 1)
           (cons 50 0)
           (cons 70 0)
           (cons 71 0)
           (cons 44 0)
           (cons 45 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 2.1 -1.3 0)
           (cons 50 0)
          )
         )
         (entmake
          (list
           (cons 0 "POINT")
           (cons 100 "AcDbEntity")
           (cons 67 0)
           (cons 8 "0")
           (cons 100 "AcDbPoint")
           (list 10 9.4 -1.3 0)
           (cons 50 0)
          )
         )
         (entmake
          (list
           (cons 0 "POINT")
           (cons 100 "AcDbEntity")
           (cons 67 0)
           (cons 8 "0")
           (cons 100 "AcDbPoint")
           (list 10 12.1 -1.3 0)
           (cons 50 0)
          )
         )
         (entmake
          (list
           (cons 0 "POINT")
           (cons 100 "AcDbEntity")
           (cons 67 0)
           (cons 8 "0")
           (cons 100 "AcDbPoint")
           (list 10 12.1 1.3 0)
           (cons 50 0)
          )
         )
         (entmake
          (list
           (cons 0 "POINT")
           (cons 100 "AcDbEntity")
           (cons 67 0)
           (cons 8 "0")
           (cons 100 "AcDbPoint")
           (list 10 9.4 1.3 0)
           (cons 50 0)
          )
         )
         (entmake
          (list
           (cons 0 "POINT")
           (cons 100 "AcDbEntity")
           (cons 67 0)
           (cons 8 "0")
           (cons 100 "AcDbPoint")
           (list 10 2.1 1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "ATTDEF")
           (cons 100 "AcDbEntity")
           (cons 67 0)
           (cons 8 "0")
           (cons 100 "AcDbText")
           (list 10 1.4 0.56666667 0)
           (cons 40 0.2)
           (cons 1 "2.100")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.4 0.23333333 0)
           (cons 40 0.2)
           (cons 1 "2.100")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.4 -0.1 0)
           (cons 40 0.2)
           (cons 1 "9.400")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.4 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.4 -0.76666667 0)
           (cons 40 0.2)
           (cons 1 "40.7")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-ABus-Rear"))
        (progn
         (entmake)
         (entmake
          (list
           (cons 0 "BLOCK")
           (cons 2 "AB_INF-ABus-Rear")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 5)
           (cons 70 129)
           (cons 43 0)
           (cons 38 0)
           (cons 39 0)
           (list 10 0 0)
           (cons 40 0)
           (cons 41 0)
           (cons 42 0)
           (cons 91 0)
           (list 10 0.6 -1.3)
           (cons 40 0)
           (cons 41 0)
           (cons 42 0)
           (cons 91 0)
           (list 10 8.7 -1.3)
           (cons 40 0)
           (cons 41 0)
           (cons 42 0)
           (cons 91 0)
           (list 10 8.7 1.3)
           (cons 40 0)
           (cons 41 0)
           (cons 42 0)
           (cons 91 0)
           (list 10 0.6 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0.6 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.7 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.7 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0.6 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0.6 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0.6 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 0.6 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.17333333)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.292 -1.252248)
           (cons 40 0)
           (cons 41 0)
           (cons 42 0)
           (cons 91 0)
           (list 10 5.292 -1.093752)
           (cons 40 0)
           (cons 41 0)
           (cons 42 0)
           (cons 91 0)
           (list 10 5.43424 -1.046)
           (cons 40 0)
           (cons 41 0)
           (cons 42 0)
           (cons 91 0)
           (list 10 6.16576 -1.046)
           (cons 40 0)
           (cons 41 0)
           (cons 42 0)
           (cons 91 0)
           (list 10 6.308 -1.093752)
           (cons 40 0)
           (cons 41 0)
           (cons 42 0)
           (cons 91 0)
           (list 10 6.308 -1.252248)
           (cons 40 0)
           (cons 41 0)
           (cons 42 0)
           (cons 91 0)
           (list 10 6.16576 -1.3)
           (cons 40 0)
           (cons 41 0)
           (cons 42 0)
           (cons 91 0)
           (list 10 5.43424 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.292 1.093752)
           (cons 40 0)
           (cons 41 0)
           (cons 42 0)
           (cons 91 0)
           (list 10 5.292 1.252248)
           (cons 40 0)
           (cons 41 0)
           (cons 42 0)
           (cons 91 0)
           (list 10 5.43424 1.3)
           (cons 40 0)
           (cons 41 0)
           (cons 42 0)
           (cons 91 0)
           (list 10 6.16576 1.3)
           (cons 40 0)
           (cons 41 0)
           (cons 42 0)
           (cons 91 0)
           (list 10 6.308 1.252248)
           (cons 40 0)
           (cons 41 0)
           (cons 42 0)
           (cons 91 0)
           (list 10 6.308 1.093752)
           (cons 40 0)
           (cons 41 0)
           (cons 42 0)
           (cons 91 0)
           (list 10 6.16576 1.046)
           (cons 40 0)
           (cons 41 0)
           (cons 42 0)
           (cons 91 0)
           (list 10 5.43424 1.046)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 0.6 -1.3 0)
           (cons 50 0)
          )
         )
         (entmake
          (list
           (cons 0 "POINT")
           (cons 100 "AcDbEntity")
           (cons 67 0)
           (cons 8 "0")
           (cons 100 "AcDbPoint")
           (list 10 0.6 1.3 0)
           (cons 50 0)
          )
         )
         (entmake
          (list
           (cons 0 "POINT")
           (cons 100 "AcDbEntity")
           (cons 67 0)
           (cons 8 "0")
           (cons 100 "AcDbPoint")
           (list 10 8.7 1.3 0)
           (cons 50 0)
          )
         )
         (entmake
          (list
           (cons 0 "POINT")
           (cons 100 "AcDbEntity")
           (cons 67 0)
           (cons 8 "0")
           (cons 100 "AcDbPoint")
           (list 10 8.7 -1.3 0)
           (cons 50 0)
          )
         )
         (entmake
          (list
           (cons 0 "POINT")
           (cons 100 "AcDbEntity")
           (cons 67 0)
           (cons 8 "0")
           (cons 100 "AcDbPoint")
           (list 10 5.8 -1.3 0)
           (cons 50 0)
          )
         )
         (entmake
          (list
           (cons 0 "POINT")
           (cons 100 "AcDbEntity")
           (cons 67 0)
           (cons 8 "0")
           (cons 100 "AcDbPoint")
           (list 10 5.8 1.3 0)
           (cons 50 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "5.800")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-ABus-Front"))
        (progn
         (entmake)
         (entmake
          (list
           (cons 0 "BLOCK")
           (cons 2 "AB_INF-ABus-Front")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 5)
           (cons 70 129)
           (cons 43 0)
           (cons 38 0)
           (cons 39 0)
           (list 10 0 -1.3)
           (cons 40 0)
           (cons 41 0)
           (cons 42 0)
           (cons 91 0)
           (list 10 9.1 -1.3)
           (cons 40 0)
           (cons 41 0)
           (cons 42 0)
           (cons 91 0)
           (list 10 9.7 0)
           (cons 40 0)
           (cons 41 0)
           (cons 42 0)
           (cons 91 0)
           (list 10 9.1 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.1 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.1 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 9.1 0 0)
           (list 11 9.7 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 9.7 0 0)
           (cons 40 0.1016)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.092 -1.252248)
           (cons 40 0)
           (cons 41 0)
           (cons 42 0)
           (cons 91 0)
           (list 10 7.092 -1.093752)
           (cons 40 0)
           (cons 41 0)
           (cons 42 0)
           (cons 91 0)
           (list 10 7.23424 -1.046)
           (cons 40 0)
           (cons 41 0)
           (cons 42 0)
           (cons 91 0)
           (list 10 7.96576 -1.046)
           (cons 40 0)
           (cons 41 0)
           (cons 42 0)
           (cons 91 0)
           (list 10 8.108 -1.093752)
           (cons 40 0)
           (cons 41 0)
           (cons 42 0)
           (cons 91 0)
           (list 10 8.108 -1.252248)
           (cons 40 0)
           (cons 41 0)
           (cons 42 0)
           (cons 91 0)
           (list 10 7.96576 -1.3)
           (cons 40 0)
           (cons 41 0)
           (cons 42 0)
           (cons 91 0)
           (list 10 7.23424 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.092 1.093752)
           (cons 40 0)
           (cons 41 0)
           (cons 42 0)
           (cons 91 0)
           (list 10 7.092 1.252248)
           (cons 40 0)
           (cons 41 0)
           (cons 42 0)
           (cons 91 0)
           (list 10 7.23424 1.3)
           (cons 40 0)
           (cons 41 0)
           (cons 42 0)
           (cons 91 0)
           (list 10 7.96576 1.3)
           (cons 40 0)
           (cons 41 0)
           (cons 42 0)
           (cons 91 0)
           (list 10 8.108 1.252248)
           (cons 40 0)
           (cons 41 0)
           (cons 42 0)
           (cons 91 0)
           (list 10 8.108 1.093752)
           (cons 40 0)
           (cons 41 0)
           (cons 42 0)
           (cons 91 0)
           (list 10 7.96576 1.046)
           (cons 40 0)
           (cons 41 0)
           (cons 42 0)
           (cons 91 0)
           (list 10 7.23424 1.046)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelRightM2")
           (list 10 2.5 1.046 0)
           (cons 41 1)
           (cons 42 1)
           (cons 43 1)
           (cons 50 0)
           (cons 70 0)
           (cons 71 0)
           (cons 44 0)
           (cons 45 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 9.1 -1.3 0)
           (cons 50 0)
          )
         )
         (entmake
          (list
           (cons 0 "POINT")
           (cons 100 "AcDbEntity")
           (cons 67 0)
           (cons 8 "0")
           (cons 100 "AcDbPoint")
           (list 10 9.1 1.3 0)
           (cons 50 0)
          )
         )
         (entmake
          (list
           (cons 0 "POINT")
           (cons 100 "AcDbEntity")
           (cons 67 0)
           (cons 8 "0")
           (cons 100 "AcDbPoint")
           (list 10 7.6 1.3 0)
           (cons 50 0)
          )
         )
         (entmake
          (list
           (cons 0 "POINT")
           (cons 100 "AcDbEntity")
           (cons 67 0)
           (cons 8 "0")
           (cons 100 "AcDbPoint")
           (list 10 7.6 -1.3 0)
           (cons 50 0)
          )
         )
         (entmake
          (list
           (cons 0 "POINT")
           (cons 100 "AcDbEntity")
           (cons 67 0)
           (cons 8 "0")
           (cons 100 "AcDbPoint")
           (list 10 2.5 -1.3 0)
           (cons 50 0)
          )
         )
         (entmake
          (list
           (cons 0 "POINT")
           (cons 100 "AcDbEntity")
           (cons 67 0)
           (cons 8 "0")
           (cons 100 "AcDbPoint")
           (list 10 2.5 1.3 0)
           (cons 50 0)
          )
         )
         (entmake
          (list
           (cons 0 "POINT")
           (cons 100 "AcDbEntity")
           (cons 67 0)
           (cons 8 "0")
           (cons 100 "AcDbPoint")
           (list 10 2.5 0.0127 0)
           (cons 50 0)
          )
         )
         (entmake
          (list
           (cons 0 "POINT")
           (cons 100 "AcDbEntity")
           (cons 67 0)
           (cons 8 "0")
           (cons 100 "AcDbPoint")
           (list 10 9.7 0 0)
           (cons 50 0)
          )
         )
         (entmake
          (list
           (cons 0 "ATTDEF")
           (cons 100 "AcDbEntity")
           (cons 67 0)
           (cons 8 "0")
           (cons 100 "AcDbText")
           (list 10 1.8 0.57936667 0)
           (cons 40 0.2)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.8 0.24603333 0)
           (cons 40 0.2)
           (cons 1 "2.500")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.8 -0.0873 0)
           (cons 40 0.2)
           (cons 1 "7.600")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.8 -0.42063333 0)
           (cons 40 0.2)
           (cons 1 "9.700")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.8 -0.75396667 0)
           (cons 40 0.2)
           (cons 1 "27.500")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelLeftM2")
           (list 10 2.5 -1.046 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "AB_INF-5Axle-Trailer"))
        (progn
         (entmake)
         (entmake
          (list
           (cons 0 "BLOCK")
           (cons 2 "AB_INF-5Axle-Trailer")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.6)
           (cons 40 0)
           (cons 41 0)
           (cons 42 0)
           (cons 91 0)
           (list 10 26.45 -1.6)
           (cons 40 0)
           (cons 41 0)
           (cons 42 0)
           (cons 91 0)
           (list 10 26.45 1.6)
           (cons 40 0)
           (cons 41 0)
           (cons 42 0)
           (cons 91 0)
           (list 10 0 1.6)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.6 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 26.45 -1.6 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 26.45 1.6 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.6 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.6 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.6 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 3.1 0 0)
           (cons 40 0.104)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 15.491 -0.744548)
           (cons 40 0)
           (cons 41 0)
           (cons 42 0)
           (cons 91 0)
           (list 10 15.491 -0.570452)
           (cons 40 0)
           (cons 41 0)
           (cons 42 0)
           (cons 91 0)
           (list 10 15.64752 -0.518)
           (cons 40 0)
           (cons 41 0)
           (cons 42 0)
           (cons 91 0)
           (list 10 16.45248 -0.518)
           (cons 40 0)
           (cons 41 0)
           (cons 42 0)
           (cons 91 0)
           (list 10 16.609 -0.570452)
           (cons 40 0)
           (cons 41 0)
           (cons 42 0)
           (cons 91 0)
           (list 10 16.609 -0.744548)
           (cons 40 0)
           (cons 41 0)
           (cons 42 0)
           (cons 91 0)
           (list 10 16.45248 -0.797)
           (cons 40 0)
           (cons 41 0)
           (cons 42 0)
           (cons 91 0)
           (list 10 15.64752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 15.491 -1.247548)
           (cons 40 0)
           (cons 41 0)
           (cons 42 0)
           (cons 91 0)
           (list 10 15.491 -1.073452)
           (cons 40 0)
           (cons 41 0)
           (cons 42 0)
           (cons 91 0)
           (list 10 15.64752 -1.021)
           (cons 40 0)
           (cons 41 0)
           (cons 42 0)
           (cons 91 0)
           (list 10 16.45248 -1.021)
           (cons 40 0)
           (cons 41 0)
           (cons 42 0)
           (cons 91 0)
           (list 10 16.609 -1.073452)
           (cons 40 0)
           (cons 41 0)
           (cons 42 0)
           (cons 91 0)
           (list 10 16.609 -1.247548)
           (cons 40 0)
           (cons 41 0)
           (cons 42 0)
           (cons 91 0)
           (list 10 16.45248 -1.3)
           (cons 40 0)
           (cons 41 0)
           (cons 42 0)
           (cons 91 0)
           (list 10 15.64752 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 15.491 0.570452)
           (cons 40 0)
           (cons 41 0)
           (cons 42 0)
           (cons 91 0)
           (list 10 15.491 0.744548)
           (cons 40 0)
           (cons 41 0)
           (cons 42 0)
           (cons 91 0)
           (list 10 15.64752 0.797)
           (cons 40 0)
           (cons 41 0)
           (cons 42 0)
           (cons 91 0)
           (list 10 16.45248 0.797)
           (cons 40 0)
           (cons 41 0)
           (cons 42 0)
           (cons 91 0)
           (list 10 16.609 0.744548)
           (cons 40 0)
           (cons 41 0)
           (cons 42 0)
           (cons 91 0)
           (list 10 16.609 0.570452)
           (cons 40 0)
           (cons 41 0)
           (cons 42 0)
           (cons 91 0)
           (list 10 16.45248 0.518)
           (cons 40 0)
           (cons 41 0)
           (cons 42 0)
           (cons 91 0)
           (list 10 15.64752 0.518)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 15.491 1.073452)
           (cons 40 0)
           (cons 41 0)
           (cons 42 0)
           (cons 91 0)
           (list 10 15.491 1.247548)
           (cons 40 0)
           (cons 41 0)
           (cons 42 0)
           (cons 91 0)
           (list 10 15.64752 1.3)
           (cons 40 0)
           (cons 41 0)
           (cons 42 0)
           (cons 91 0)
           (list 10 16.45248 1.3)
           (cons 40 0)
           (cons 41 0)
           (cons 42 0)
           (cons 91 0)
           (list 10 16.609 1.247548)
           (cons 40 0)
           (cons 41 0)
           (cons 42 0)
           (cons 91 0)
           (list 10 16.609 1.073452)
           (cons 40 0)
           (cons 41 0)
           (cons 42 0)
           (cons 91 0)
           (list 10 16.45248 1.021)
           (cons 40 0)
           (cons 41 0)
           (cons 42 0)
           (cons 91 0)
           (list 10 15.64752 1.021)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 16.891 -0.744548)
           (cons 40 0)
           (cons 41 0)
           (cons 42 0)
           (cons 91 0)
           (list 10 16.891 -0.570452)
           (cons 40 0)
           (cons 41 0)
           (cons 42 0)
           (cons 91 0)
           (list 10 17.04752 -0.518)
           (cons 40 0)
           (cons 41 0)
           (cons 42 0)
           (cons 91 0)
           (list 10 17.85248 -0.518)
           (cons 40 0)
           (cons 41 0)
           (cons 42 0)
           (cons 91 0)
           (list 10 18.009 -0.570452)
           (cons 40 0)
           (cons 41 0)
           (cons 42 0)
           (cons 91 0)
           (list 10 18.009 -0.744548)
           (cons 40 0)
           (cons 41 0)
           (cons 42 0)
           (cons 91 0)
           (list 10 17.85248 -0.797)
           (cons 40 0)
           (cons 41 0)
           (cons 42 0)
           (cons 91 0)
           (list 10 17.04752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 16.891 -1.247548)
           (cons 40 0)
           (cons 41 0)
           (cons 42 0)
           (cons 91 0)
           (list 10 16.891 -1.073452)
           (cons 40 0)
           (cons 41 0)
           (cons 42 0)
           (cons 91 0)
           (list 10 17.04752 -1.021)
           (cons 40 0)
           (cons 41 0)
           (cons 42 0)
           (cons 91 0)
           (list 10 17.85248 -1.021)
           (cons 40 0)
           (cons 41 0)
           (cons 42 0)
           (cons 91 0)
           (list 10 18.009 -1.073452)
           (cons 40 0)
           (cons 41 0)
           (cons 42 0)
           (cons 91 0)
           (list 10 18.009 -1.247548)
           (cons 40 0)
           (cons 41 0)
           (cons 42 0)
           (cons 91 0)
           (list 10 17.85248 -1.3)
           (cons 40 0)
           (cons 41 0)
           (cons 42 0)
           (cons 91 0)
           (list 10 17.04752 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 16.891 0.570452)
           (cons 40 0)
           (cons 41 0)
           (cons 42 0)
           (cons 91 0)
           (list 10 16.891 0.744548)
           (cons 40 0)
           (cons 41 0)
           (cons 42 0)
           (cons 91 0)
           (list 10 17.04752 0.797)
           (cons 40 0)
           (cons 41 0)
           (cons 42 0)
           (cons 91 0)
           (list 10 17.85248 0.797)
           (cons 40 0)
           (cons 41 0)
           (cons 42 0)
           (cons 91 0)
           (list 10 18.009 0.744548)
           (cons 40 0)
           (cons 41 0)
           (cons 42 0)
           (cons 91 0)
           (list 10 18.009 0.570452)
           (cons 40 0)
           (cons 41 0)
           (cons 42 0)
           (cons 91 0)
           (list 10 17.85248 0.518)
           (cons 40 0)
           (cons 41 0)
           (cons 42 0)
           (cons 91 0)
           (list 10 17.04752 0.518)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 16.891 1.073452)
           (cons 40 0)
           (cons 41 0)
           (cons 42 0)
           (cons 91 0)
           (list 10 16.891 1.247548)
           (cons 40 0)
           (cons 41 0)
           (cons 42 0)
           (cons 91 0)
           (list 10 17.04752 1.3)
           (cons 40 0)
           (cons 41 0)
           (cons 42 0)
           (cons 91 0)
           (list 10 17.85248 1.3)
           (cons 40 0)
           (cons 41 0)
           (cons 42 0)
           (cons 91 0)
           (list 10 18.009 1.247548)
           (cons 40 0)
           (cons 41 0)
           (cons 42 0)
           (cons 91 0)
           (list 10 18.009 1.073452)
           (cons 40 0)
           (cons 41 0)
           (cons 42 0)
           (cons 91 0)
           (list 10 17.85248 1.021)
           (cons 40 0)
           (cons 41 0)
           (cons 42 0)
           (cons 91 0)
           (list 10 17.04752 1.021)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 1.6 0)
           (cons 50 0)
          )
         )
         (entmake
          (list
           (cons 0 "POINT")
           (cons 100 "AcDbEntity")
           (cons 67 0)
           (cons 8 "0")
           (cons 100 "AcDbPoint")
           (list 10 0 -1.6 0)
           (cons 50 0)
          )
         )
         (entmake
          (list
           (cons 0 "POINT")
           (cons 100 "AcDbEntity")
           (cons 67 0)
           (cons 8 "0")
           (cons 100 "AcDbPoint")
           (list 10 26.45 -1.6 0)
           (cons 50 0)
          )
         )
         (entmake
          (list
           (cons 0 "POINT")
           (cons 100 "AcDbEntity")
           (cons 67 0)
           (cons 8 "0")
           (cons 100 "AcDbPoint")
           (list 10 26.45 1.6 0)
           (cons 50 0)
          )
         )
         (entmake
          (list
           (cons 0 "POINT")
           (cons 100 "AcDbEntity")
           (cons 67 0)
           (cons 8 "0")
           (cons 100 "AcDbPoint")
           (list 10 3.1 0 0)
           (cons 50 0)
          )
         )
         (entmake
          (list
           (cons 0 "POINT")
           (cons 100 "AcDbEntity")
           (cons 67 0)
           (cons 8 "0")
           (cons 100 "AcDbPoint")
           (list 10 16.75 1.3 0)
           (cons 50 0)
          )
         )
         (entmake
          (list
           (cons 0 "POINT")
           (cons 100 "AcDbEntity")
           (cons 67 0)
           (cons 8 "0")
           (cons 100 "AcDbPoint")
           (list 10 16.75 -1.3 0)
           (cons 50 0)
          )
         )
         (entmake
          (list
           (cons 0 "ATTDEF")
           (cons 100 "AcDbEntity")
           (cons 67 0)
           (cons 8 "0")
           (cons 100 "AcDbText")
           (list 10 2.4 0.56666667 0)
           (cons 40 0.2)
           (cons 1 "3.100")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 2.4 0.23333333 0)
           (cons 40 0.2)
           (cons 1 "3.100")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 2.4 -0.1 0)
           (cons 40 0.2)
           (cons 1 "8.700")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 2.4 -0.43333333 0)
           (cons 40 0.2)
           (cons 1 "16.750")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 2.4 -0.76666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "AB_INF-5Axle-Truck"))
        (progn
         (entmake)
         (entmake
          (list
           (cons 0 "BLOCK")
           (cons 2 "AB_INF-5Axle-Truck")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 7.85 -1.3)
           (cons 40 0)
           (cons 41 0)
           (cons 42 0)
           (cons 91 0)
           (list 10 7.85 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.85 -0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.85 0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 0.5188 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 7.15 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 7.41263966 -0.26263966 0)
           (list 11 7.41263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.891 -0.744548)
           (cons 40 0)
           (cons 41 0)
           (cons 42 0)
           (cons 91 0)
           (list 10 5.891 -0.570452)
           (cons 40 0)
           (cons 41 0)
           (cons 42 0)
           (cons 91 0)
           (list 10 6.04752 -0.518)
           (cons 40 0)
           (cons 41 0)
           (cons 42 0)
           (cons 91 0)
           (list 10 6.85248 -0.518)
           (cons 40 0)
           (cons 41 0)
           (cons 42 0)
           (cons 91 0)
           (list 10 7.009 -0.570452)
           (cons 40 0)
           (cons 41 0)
           (cons 42 0)
           (cons 91 0)
           (list 10 7.009 -0.744548)
           (cons 40 0)
           (cons 41 0)
           (cons 42 0)
           (cons 91 0)
           (list 10 6.85248 -0.797)
           (cons 40 0)
           (cons 41 0)
           (cons 42 0)
           (cons 91 0)
           (list 10 6.04752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.891 -1.247548)
           (cons 40 0)
           (cons 41 0)
           (cons 42 0)
           (cons 91 0)
           (list 10 5.891 -1.073452)
           (cons 40 0)
           (cons 41 0)
           (cons 42 0)
           (cons 91 0)
           (list 10 6.04752 -1.021)
           (cons 40 0)
           (cons 41 0)
           (cons 42 0)
           (cons 91 0)
           (list 10 6.85248 -1.021)
           (cons 40 0)
           (cons 41 0)
           (cons 42 0)
           (cons 91 0)
           (list 10 7.009 -1.073452)
           (cons 40 0)
           (cons 41 0)
           (cons 42 0)
           (cons 91 0)
           (list 10 7.009 -1.247548)
           (cons 40 0)
           (cons 41 0)
           (cons 42 0)
           (cons 91 0)
           (list 10 6.85248 -1.3)
           (cons 40 0)
           (cons 41 0)
           (cons 42 0)
           (cons 91 0)
           (list 10 6.04752 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.891 0.570452)
           (cons 40 0)
           (cons 41 0)
           (cons 42 0)
           (cons 91 0)
           (list 10 5.891 0.744548)
           (cons 40 0)
           (cons 41 0)
           (cons 42 0)
           (cons 91 0)
           (list 10 6.04752 0.797)
           (cons 40 0)
           (cons 41 0)
           (cons 42 0)
           (cons 91 0)
           (list 10 6.85248 0.797)
           (cons 40 0)
           (cons 41 0)
           (cons 42 0)
           (cons 91 0)
           (list 10 7.009 0.744548)
           (cons 40 0)
           (cons 41 0)
           (cons 42 0)
           (cons 91 0)
           (list 10 7.009 0.570452)
           (cons 40 0)
           (cons 41 0)
           (cons 42 0)
           (cons 91 0)
           (list 10 6.85248 0.518)
           (cons 40 0)
           (cons 41 0)
           (cons 42 0)
           (cons 91 0)
           (list 10 6.04752 0.518)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.891 1.073452)
           (cons 40 0)
           (cons 41 0)
           (cons 42 0)
           (cons 91 0)
           (list 10 5.891 1.247548)
           (cons 40 0)
           (cons 41 0)
           (cons 42 0)
           (cons 91 0)
           (list 10 6.04752 1.3)
           (cons 40 0)
           (cons 41 0)
           (cons 42 0)
           (cons 91 0)
           (list 10 6.85248 1.3)
           (cons 40 0)
           (cons 41 0)
           (cons 42 0)
           (cons 91 0)
           (list 10 7.009 1.247548)
           (cons 40 0)
           (cons 41 0)
           (cons 42 0)
           (cons 91 0)
           (list 10 7.009 1.073452)
           (cons 40 0)
           (cons 41 0)
           (cons 42 0)
           (cons 91 0)
           (list 10 6.85248 1.021)
           (cons 40 0)
           (cons 41 0)
           (cons 42 0)
           (cons 91 0)
           (list 10 6.04752 1.021)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.291 -0.744548)
           (cons 40 0)
           (cons 41 0)
           (cons 42 0)
           (cons 91 0)
           (list 10 7.291 -0.570452)
           (cons 40 0)
           (cons 41 0)
           (cons 42 0)
           (cons 91 0)
           (list 10 7.44752 -0.518)
           (cons 40 0)
           (cons 41 0)
           (cons 42 0)
           (cons 91 0)
           (list 10 8.25248 -0.518)
           (cons 40 0)
           (cons 41 0)
           (cons 42 0)
           (cons 91 0)
           (list 10 8.409 -0.570452)
           (cons 40 0)
           (cons 41 0)
           (cons 42 0)
           (cons 91 0)
           (list 10 8.409 -0.744548)
           (cons 40 0)
           (cons 41 0)
           (cons 42 0)
           (cons 91 0)
           (list 10 8.25248 -0.797)
           (cons 40 0)
           (cons 41 0)
           (cons 42 0)
           (cons 91 0)
           (list 10 7.44752 -0.797)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.291 -1.247548)
           (cons 40 0)
           (cons 41 0)
           (cons 42 0)
           (cons 91 0)
           (list 10 7.291 -1.073452)
           (cons 40 0)
           (cons 41 0)
           (cons 42 0)
           (cons 91 0)
           (list 10 7.44752 -1.021)
           (cons 40 0)
           (cons 41 0)
           (cons 42 0)
           (cons 91 0)
           (list 10 8.25248 -1.021)
           (cons 40 0)
           (cons 41 0)
           (cons 42 0)
           (cons 91 0)
           (list 10 8.409 -1.073452)
           (cons 40 0)
           (cons 41 0)
           (cons 42 0)
           (cons 91 0)
           (list 10 8.409 -1.247548)
           (cons 40 0)
           (cons 41 0)
           (cons 42 0)
           (cons 91 0)
           (list 10 8.25248 -1.3)
           (cons 40 0)
           (cons 41 0)
           (cons 42 0)
           (cons 91 0)
           (list 10 7.44752 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.291 0.570452)
           (cons 40 0)
           (cons 41 0)
           (cons 42 0)
           (cons 91 0)
           (list 10 7.291 0.744548)
           (cons 40 0)
           (cons 41 0)
           (cons 42 0)
           (cons 91 0)
           (list 10 7.44752 0.797)
           (cons 40 0)
           (cons 41 0)
           (cons 42 0)
           (cons 91 0)
           (list 10 8.25248 0.797)
           (cons 40 0)
           (cons 41 0)
           (cons 42 0)
           (cons 91 0)
           (list 10 8.409 0.744548)
           (cons 40 0)
           (cons 41 0)
           (cons 42 0)
           (cons 91 0)
           (list 10 8.409 0.570452)
           (cons 40 0)
           (cons 41 0)
           (cons 42 0)
           (cons 91 0)
           (list 10 8.25248 0.518)
           (cons 40 0)
           (cons 41 0)
           (cons 42 0)
           (cons 91 0)
           (list 10 7.44752 0.518)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.291 1.073452)
           (cons 40 0)
           (cons 41 0)
           (cons 42 0)
           (cons 91 0)
           (list 10 7.291 1.247548)
           (cons 40 0)
           (cons 41 0)
           (cons 42 0)
           (cons 91 0)
           (list 10 7.44752 1.3)
           (cons 40 0)
           (cons 41 0)
           (cons 42 0)
           (cons 91 0)
           (list 10 8.25248 1.3)
           (cons 40 0)
           (cons 41 0)
           (cons 42 0)
           (cons 91 0)
           (list 10 8.409 1.247548)
           (cons 40 0)
           (cons 41 0)
           (cons 42 0)
           (cons 91 0)
           (list 10 8.409 1.073452)
           (cons 40 0)
           (cons 41 0)
           (cons 42 0)
           (cons 91 0)
           (list 10 8.25248 1.021)
           (cons 40 0)
           (cons 41 0)
           (cons 42 0)
           (cons 91 0)
           (list 10 7.44752 1.021)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelLeftM1")
           (list 10 1 -1.021 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM1")
           (list 10 1 1.021 0)
           (cons 41 1)
           (cons 42 1)
           (cons 43 1)
           (cons 50 0)
           (cons 70 0)
           (cons 71 0)
           (cons 44 0)
           (cons 45 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 1 0 0)
           (cons 50 0)
          )
         )
         (entmake
          (list
           (cons 0 "POINT")
           (cons 100 "AcDbEntity")
           (cons 67 0)
           (cons 8 "0")
           (cons 100 "AcDbPoint")
           (list 10 7.15 0 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 7.15 1.3 0)
           (cons 50 0)
          )
         )
         (entmake
          (list
           (cons 0 "POINT")
           (cons 100 "AcDbEntity")
           (cons 67 0)
           (cons 8 "0")
           (cons 100 "AcDbPoint")
           (list 10 7.15 -1.3 0)
           (cons 50 0)
          )
         )
         (entmake
          (list
           (cons 0 "ATTDEF")
           (cons 100 "AcDbEntity")
           (cons 67 0)
           (cons 8 "0")
           (cons 100 "AcDbText")
           (list 10 0.3 0.56666667 0)
           (cons 40 0.2)
           (cons 1 "1.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 0.23333333 0)
           (cons 40 0.2)
           (cons 1 "1.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.1 0)
           (cons 40 0.2)
           (cons 1 "7.150")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.43333333 0)
           (cons 40 0.2)
           (cons 1 "7.150")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.76666667 0)
           (cons 40 0.2)
           (cons 1 "26.4")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "Special-19HeavyHaul-Pup4"))
        (progn
         (entmake)
         (entmake
          (list
           (cons 0 "BLOCK")
           (cons 2 "Special-19HeavyHaul-Pup4")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 11.5824 -0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 11.5824 0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.3048 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 6.096 0 0)
           (cons 40 0.16256)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.2804 -0.714248)
           (cons 40 0)
           (cons 41 0)
           (cons 42 0)
           (cons 91 0)
           (list 10 8.2804 -0.555752)
           (cons 40 0)
           (cons 41 0)
           (cons 42 0)
           (cons 91 0)
           (list 10 8.42264 -0.508)
           (cons 40 0)
           (cons 41 0)
           (cons 42 0)
           (cons 91 0)
           (list 10 9.15416 -0.508)
           (cons 40 0)
           (cons 41 0)
           (cons 42 0)
           (cons 91 0)
           (list 10 9.2964 -0.555752)
           (cons 40 0)
           (cons 41 0)
           (cons 42 0)
           (cons 91 0)
           (list 10 9.2964 -0.714248)
           (cons 40 0)
           (cons 41 0)
           (cons 42 0)
           (cons 91 0)
           (list 10 9.15416 -0.762)
           (cons 40 0)
           (cons 41 0)
           (cons 42 0)
           (cons 91 0)
           (list 10 8.42264 -0.762)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.2804 -1.171448)
           (cons 40 0)
           (cons 41 0)
           (cons 42 0)
           (cons 91 0)
           (list 10 8.2804 -1.012952)
           (cons 40 0)
           (cons 41 0)
           (cons 42 0)
           (cons 91 0)
           (list 10 8.42264 -0.9652)
           (cons 40 0)
           (cons 41 0)
           (cons 42 0)
           (cons 91 0)
           (list 10 9.15416 -0.9652)
           (cons 40 0)
           (cons 41 0)
           (cons 42 0)
           (cons 91 0)
           (list 10 9.2964 -1.012952)
           (cons 40 0)
           (cons 41 0)
           (cons 42 0)
           (cons 91 0)
           (list 10 9.2964 -1.171448)
           (cons 40 0)
           (cons 41 0)
           (cons 42 0)
           (cons 91 0)
           (list 10 9.15416 -1.2192)
           (cons 40 0)
           (cons 41 0)
           (cons 42 0)
           (cons 91 0)
           (list 10 8.42264 -1.2192)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.2804 0.555752)
           (cons 40 0)
           (cons 41 0)
           (cons 42 0)
           (cons 91 0)
           (list 10 8.2804 0.714248)
           (cons 40 0)
           (cons 41 0)
           (cons 42 0)
           (cons 91 0)
           (list 10 8.42264 0.762)
           (cons 40 0)
           (cons 41 0)
           (cons 42 0)
           (cons 91 0)
           (list 10 9.15416 0.762)
           (cons 40 0)
           (cons 41 0)
           (cons 42 0)
           (cons 91 0)
           (list 10 9.2964 0.714248)
           (cons 40 0)
           (cons 41 0)
           (cons 42 0)
           (cons 91 0)
           (list 10 9.2964 0.555752)
           (cons 40 0)
           (cons 41 0)
           (cons 42 0)
           (cons 91 0)
           (list 10 9.15416 0.508)
           (cons 40 0)
           (cons 41 0)
           (cons 42 0)
           (cons 91 0)
           (list 10 8.42264 0.508)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.2804 1.012952)
           (cons 40 0)
           (cons 41 0)
           (cons 42 0)
           (cons 91 0)
           (list 10 8.2804 1.171448)
           (cons 40 0)
           (cons 41 0)
           (cons 42 0)
           (cons 91 0)
           (list 10 8.42264 1.2192)
           (cons 40 0)
           (cons 41 0)
           (cons 42 0)
           (cons 91 0)
           (list 10 9.15416 1.2192)
           (cons 40 0)
           (cons 41 0)
           (cons 42 0)
           (cons 91 0)
           (list 10 9.2964 1.171448)
           (cons 40 0)
           (cons 41 0)
           (cons 42 0)
           (cons 91 0)
           (list 10 9.2964 1.012952)
           (cons 40 0)
           (cons 41 0)
           (cons 42 0)
           (cons 91 0)
           (list 10 9.15416 0.9652)
           (cons 40 0)
           (cons 41 0)
           (cons 42 0)
           (cons 91 0)
           (list 10 8.42264 0.9652)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.5504 -0.714248)
           (cons 40 0)
           (cons 41 0)
           (cons 42 0)
           (cons 91 0)
           (list 10 9.5504 -0.555752)
           (cons 40 0)
           (cons 41 0)
           (cons 42 0)
           (cons 91 0)
           (list 10 9.69264 -0.508)
           (cons 40 0)
           (cons 41 0)
           (cons 42 0)
           (cons 91 0)
           (list 10 10.42416 -0.508)
           (cons 40 0)
           (cons 41 0)
           (cons 42 0)
           (cons 91 0)
           (list 10 10.5664 -0.555752)
           (cons 40 0)
           (cons 41 0)
           (cons 42 0)
           (cons 91 0)
           (list 10 10.5664 -0.714248)
           (cons 40 0)
           (cons 41 0)
           (cons 42 0)
           (cons 91 0)
           (list 10 10.42416 -0.762)
           (cons 40 0)
           (cons 41 0)
           (cons 42 0)
           (cons 91 0)
           (list 10 9.69264 -0.762)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.5504 -1.171448)
           (cons 40 0)
           (cons 41 0)
           (cons 42 0)
           (cons 91 0)
           (list 10 9.5504 -1.012952)
           (cons 40 0)
           (cons 41 0)
           (cons 42 0)
           (cons 91 0)
           (list 10 9.69264 -0.9652)
           (cons 40 0)
           (cons 41 0)
           (cons 42 0)
           (cons 91 0)
           (list 10 10.42416 -0.9652)
           (cons 40 0)
           (cons 41 0)
           (cons 42 0)
           (cons 91 0)
           (list 10 10.5664 -1.012952)
           (cons 40 0)
           (cons 41 0)
           (cons 42 0)
           (cons 91 0)
           (list 10 10.5664 -1.171448)
           (cons 40 0)
           (cons 41 0)
           (cons 42 0)
           (cons 91 0)
           (list 10 10.42416 -1.2192)
           (cons 40 0)
           (cons 41 0)
           (cons 42 0)
           (cons 91 0)
           (list 10 9.69264 -1.2192)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.5504 0.555752)
           (cons 40 0)
           (cons 41 0)
           (cons 42 0)
           (cons 91 0)
           (list 10 9.5504 0.714248)
           (cons 40 0)
           (cons 41 0)
           (cons 42 0)
           (cons 91 0)
           (list 10 9.69264 0.762)
           (cons 40 0)
           (cons 41 0)
           (cons 42 0)
           (cons 91 0)
           (list 10 10.42416 0.762)
           (cons 40 0)
           (cons 41 0)
           (cons 42 0)
           (cons 91 0)
           (list 10 10.5664 0.714248)
           (cons 40 0)
           (cons 41 0)
           (cons 42 0)
           (cons 91 0)
           (list 10 10.5664 0.555752)
           (cons 40 0)
           (cons 41 0)
           (cons 42 0)
           (cons 91 0)
           (list 10 10.42416 0.508)
           (cons 40 0)
           (cons 41 0)
           (cons 42 0)
           (cons 91 0)
           (list 10 9.69264 0.508)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.5504 1.012952)
           (cons 40 0)
           (cons 41 0)
           (cons 42 0)
           (cons 91 0)
           (list 10 9.5504 1.171448)
           (cons 40 0)
           (cons 41 0)
           (cons 42 0)
           (cons 91 0)
           (list 10 9.69264 1.2192)
           (cons 40 0)
           (cons 41 0)
           (cons 42 0)
           (cons 91 0)
           (list 10 10.42416 1.2192)
           (cons 40 0)
           (cons 41 0)
           (cons 42 0)
           (cons 91 0)
           (list 10 10.5664 1.171448)
           (cons 40 0)
           (cons 41 0)
           (cons 42 0)
           (cons 91 0)
           (list 10 10.5664 1.012952)
           (cons 40 0)
           (cons 41 0)
           (cons 42 0)
           (cons 91 0)
           (list 10 10.42416 0.9652)
           (cons 40 0)
           (cons 41 0)
           (cons 42 0)
           (cons 91 0)
           (list 10 9.69264 0.9652)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.8204 -0.714248)
           (cons 40 0)
           (cons 41 0)
           (cons 42 0)
           (cons 91 0)
           (list 10 10.8204 -0.555752)
           (cons 40 0)
           (cons 41 0)
           (cons 42 0)
           (cons 91 0)
           (list 10 10.96264 -0.508)
           (cons 40 0)
           (cons 41 0)
           (cons 42 0)
           (cons 91 0)
           (list 10 11.69416 -0.508)
           (cons 40 0)
           (cons 41 0)
           (cons 42 0)
           (cons 91 0)
           (list 10 11.8364 -0.555752)
           (cons 40 0)
           (cons 41 0)
           (cons 42 0)
           (cons 91 0)
           (list 10 11.8364 -0.714248)
           (cons 40 0)
           (cons 41 0)
           (cons 42 0)
           (cons 91 0)
           (list 10 11.69416 -0.762)
           (cons 40 0)
           (cons 41 0)
           (cons 42 0)
           (cons 91 0)
           (list 10 10.96264 -0.762)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.8204 -1.171448)
           (cons 40 0)
           (cons 41 0)
           (cons 42 0)
           (cons 91 0)
           (list 10 10.8204 -1.012952)
           (cons 40 0)
           (cons 41 0)
           (cons 42 0)
           (cons 91 0)
           (list 10 10.96264 -0.9652)
           (cons 40 0)
           (cons 41 0)
           (cons 42 0)
           (cons 91 0)
           (list 10 11.69416 -0.9652)
           (cons 40 0)
           (cons 41 0)
           (cons 42 0)
           (cons 91 0)
           (list 10 11.8364 -1.012952)
           (cons 40 0)
           (cons 41 0)
           (cons 42 0)
           (cons 91 0)
           (list 10 11.8364 -1.171448)
           (cons 40 0)
           (cons 41 0)
           (cons 42 0)
           (cons 91 0)
           (list 10 11.69416 -1.2192)
           (cons 40 0)
           (cons 41 0)
           (cons 42 0)
           (cons 91 0)
           (list 10 10.96264 -1.2192)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.8204 0.555752)
           (cons 40 0)
           (cons 41 0)
           (cons 42 0)
           (cons 91 0)
           (list 10 10.8204 0.714248)
           (cons 40 0)
           (cons 41 0)
           (cons 42 0)
           (cons 91 0)
           (list 10 10.96264 0.762)
           (cons 40 0)
           (cons 41 0)
           (cons 42 0)
           (cons 91 0)
           (list 10 11.69416 0.762)
           (cons 40 0)
           (cons 41 0)
           (cons 42 0)
           (cons 91 0)
           (list 10 11.8364 0.714248)
           (cons 40 0)
           (cons 41 0)
           (cons 42 0)
           (cons 91 0)
           (list 10 11.8364 0.555752)
           (cons 40 0)
           (cons 41 0)
           (cons 42 0)
           (cons 91 0)
           (list 10 11.69416 0.508)
           (cons 40 0)
           (cons 41 0)
           (cons 42 0)
           (cons 91 0)
           (list 10 10.96264 0.508)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.8204 1.012952)
           (cons 40 0)
           (cons 41 0)
           (cons 42 0)
           (cons 91 0)
           (list 10 10.8204 1.171448)
           (cons 40 0)
           (cons 41 0)
           (cons 42 0)
           (cons 91 0)
           (list 10 10.96264 1.2192)
           (cons 40 0)
           (cons 41 0)
           (cons 42 0)
           (cons 91 0)
           (list 10 11.69416 1.2192)
           (cons 40 0)
           (cons 41 0)
           (cons 42 0)
           (cons 91 0)
           (list 10 11.8364 1.171448)
           (cons 40 0)
           (cons 41 0)
           (cons 42 0)
           (cons 91 0)
           (list 10 11.8364 1.012952)
           (cons 40 0)
           (cons 41 0)
           (cons 42 0)
           (cons 91 0)
           (list 10 11.69416 0.9652)
           (cons 40 0)
           (cons 41 0)
           (cons 42 0)
           (cons 91 0)
           (list 10 10.96264 0.9652)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 1.524 1.2192 0)
           (cons 50 0)
          )
         )
         (entmake
          (list
           (cons 0 "POINT")
           (cons 100 "AcDbEntity")
           (cons 67 0)
           (cons 8 "0")
           (cons 100 "AcDbPoint")
           (list 10 1.524 -1.2192 0)
           (cons 50 0)
          )
         )
         (entmake
          (list
           (cons 0 "POINT")
           (cons 100 "AcDbEntity")
           (cons 67 0)
           (cons 8 "0")
           (cons 100 "AcDbPoint")
           (list 10 10.0584 -1.2192 0)
           (cons 50 0)
          )
         )
         (entmake
          (list
           (cons 0 "POINT")
           (cons 100 "AcDbEntity")
           (cons 67 0)
           (cons 8 "0")
           (cons 100 "AcDbPoint")
           (list 10 10.0584 1.2192 0)
           (cons 50 0)
          )
         )
         (entmake
          (list
           (cons 0 "POINT")
           (cons 100 "AcDbEntity")
           (cons 67 0)
           (cons 8 "0")
           (cons 62 3)
           (cons 100 "AcDbPoint")
           (list 10 6.096 0 0)
           (cons 50 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "6.10")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "1.52")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "10.05")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "TEXT")
           (cons 100 "AcDbEntity")
           (cons 67 0)
           (cons 8 "0")
           (cons 100 "AcDbText")
           (list 10 6.9412381 -0.25 0)
           (cons 40 0.5)
           (cons 1 "6")
           (cons 50 0)
           (cons 41 1)
           (cons 51 0)
           (cons 7 "Standard")
           (cons 71 0)
           (cons 72 4)
           (list 11 7.096 0 0)
           (cons 100 "AcDbText")
           (cons 73 0)
          )
         )
         (entmake
          (list
           (cons 0 "LWPOLYLINE")
           (cons 100 "AcDbEntity")
           (cons 67 0)
           (cons 8 "Defpoints")
           (cons 100 "AcDbPolyline")
           (cons 90 12)
           (cons 70 129)
           (cons 43 0)
           (cons 38 0)
           (cons 39 0)
           (list 10 8.2804 1.2192)
           (cons 40 0)
           (cons 41 0)
           (cons 42 0)
           (cons 91 0)
           (list 10 11.8364 1.2192)
           (cons 40 0)
           (cons 41 0)
           (cons 42 0)
           (cons 91 0)
           (list 10 11.8364 -1.2192)
           (cons 40 0)
           (cons 41 0)
           (cons 42 0)
           (cons 91 0)
           (list 10 8.2804 -1.2192)
           (cons 40 0)
           (cons 41 0)
           (cons 42 0)
           (cons 91 0)
           (list 10 8.2804 -0.3048)
           (cons 40 0)
           (cons 41 0)
           (cons 42 0)
           (cons 91 0)
           (list 10 3.302 -0.3048)
           (cons 40 0)
           (cons 41 0)
           (cons 42 0)
           (cons 91 0)
           (list 10 3.302 -1.2192)
           (cons 40 0)
           (cons 41 0)
           (cons 42 0)
           (cons 91 0)
           (list 10 -0.254 -1.2192)
           (cons 40 0)
           (cons 41 0)
           (cons 42 0)
           (cons 91 0)
           (list 10 -0.254 1.2192)
           (cons 40 0)
           (cons 41 0)
           (cons 42 0)
           (cons 91 0)
           (list 10 3.302 1.2192)
           (cons 40 0)
           (cons 41 0)
           (cons 42 0)
           (cons 91 0)
           (list 10 3.302 0.3048)
           (cons 40 0)
           (cons 41 0)
           (cons 42 0)
           (cons 91 0)
           (list 10 8.2804 0.3048)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelLeftM6")
           (list 10 0.254 -0.508 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM6")
           (list 10 1.524 -0.508 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM6")
           (list 10 2.794 -0.508 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM6")
           (list 10 0.254 0.508 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM6")
           (list 10 1.524 0.508 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM6")
           (list 10 2.794 0.508 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "Special-19HeavyHaul-Pup3"))
        (progn
         (entmake)
         (entmake
          (list
           (cons 0 "BLOCK")
           (cons 2 "Special-19HeavyHaul-Pup3")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 13.1064 -0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 13.1064 0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.3048 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 3.9624 0 0)
           (cons 40 0.16256)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.8044 -0.714248)
           (cons 40 0)
           (cons 41 0)
           (cons 42 0)
           (cons 91 0)
           (list 10 9.8044 -0.555752)
           (cons 40 0)
           (cons 41 0)
           (cons 42 0)
           (cons 91 0)
           (list 10 9.94664 -0.508)
           (cons 40 0)
           (cons 41 0)
           (cons 42 0)
           (cons 91 0)
           (list 10 10.67816 -0.508)
           (cons 40 0)
           (cons 41 0)
           (cons 42 0)
           (cons 91 0)
           (list 10 10.8204 -0.555752)
           (cons 40 0)
           (cons 41 0)
           (cons 42 0)
           (cons 91 0)
           (list 10 10.8204 -0.714248)
           (cons 40 0)
           (cons 41 0)
           (cons 42 0)
           (cons 91 0)
           (list 10 10.67816 -0.762)
           (cons 40 0)
           (cons 41 0)
           (cons 42 0)
           (cons 91 0)
           (list 10 9.94664 -0.762)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.8044 -1.171448)
           (cons 40 0)
           (cons 41 0)
           (cons 42 0)
           (cons 91 0)
           (list 10 9.8044 -1.012952)
           (cons 40 0)
           (cons 41 0)
           (cons 42 0)
           (cons 91 0)
           (list 10 9.94664 -0.9652)
           (cons 40 0)
           (cons 41 0)
           (cons 42 0)
           (cons 91 0)
           (list 10 10.67816 -0.9652)
           (cons 40 0)
           (cons 41 0)
           (cons 42 0)
           (cons 91 0)
           (list 10 10.8204 -1.012952)
           (cons 40 0)
           (cons 41 0)
           (cons 42 0)
           (cons 91 0)
           (list 10 10.8204 -1.171448)
           (cons 40 0)
           (cons 41 0)
           (cons 42 0)
           (cons 91 0)
           (list 10 10.67816 -1.2192)
           (cons 40 0)
           (cons 41 0)
           (cons 42 0)
           (cons 91 0)
           (list 10 9.94664 -1.2192)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.8044 0.555752)
           (cons 40 0)
           (cons 41 0)
           (cons 42 0)
           (cons 91 0)
           (list 10 9.8044 0.714248)
           (cons 40 0)
           (cons 41 0)
           (cons 42 0)
           (cons 91 0)
           (list 10 9.94664 0.762)
           (cons 40 0)
           (cons 41 0)
           (cons 42 0)
           (cons 91 0)
           (list 10 10.67816 0.762)
           (cons 40 0)
           (cons 41 0)
           (cons 42 0)
           (cons 91 0)
           (list 10 10.8204 0.714248)
           (cons 40 0)
           (cons 41 0)
           (cons 42 0)
           (cons 91 0)
           (list 10 10.8204 0.555752)
           (cons 40 0)
           (cons 41 0)
           (cons 42 0)
           (cons 91 0)
           (list 10 10.67816 0.508)
           (cons 40 0)
           (cons 41 0)
           (cons 42 0)
           (cons 91 0)
           (list 10 9.94664 0.508)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.8044 1.012952)
           (cons 40 0)
           (cons 41 0)
           (cons 42 0)
           (cons 91 0)
           (list 10 9.8044 1.171448)
           (cons 40 0)
           (cons 41 0)
           (cons 42 0)
           (cons 91 0)
           (list 10 9.94664 1.2192)
           (cons 40 0)
           (cons 41 0)
           (cons 42 0)
           (cons 91 0)
           (list 10 10.67816 1.2192)
           (cons 40 0)
           (cons 41 0)
           (cons 42 0)
           (cons 91 0)
           (list 10 10.8204 1.171448)
           (cons 40 0)
           (cons 41 0)
           (cons 42 0)
           (cons 91 0)
           (list 10 10.8204 1.012952)
           (cons 40 0)
           (cons 41 0)
           (cons 42 0)
           (cons 91 0)
           (list 10 10.67816 0.9652)
           (cons 40 0)
           (cons 41 0)
           (cons 42 0)
           (cons 91 0)
           (list 10 9.94664 0.9652)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.0744 -0.714248)
           (cons 40 0)
           (cons 41 0)
           (cons 42 0)
           (cons 91 0)
           (list 10 11.0744 -0.555752)
           (cons 40 0)
           (cons 41 0)
           (cons 42 0)
           (cons 91 0)
           (list 10 11.21664 -0.508)
           (cons 40 0)
           (cons 41 0)
           (cons 42 0)
           (cons 91 0)
           (list 10 11.94816 -0.508)
           (cons 40 0)
           (cons 41 0)
           (cons 42 0)
           (cons 91 0)
           (list 10 12.0904 -0.555752)
           (cons 40 0)
           (cons 41 0)
           (cons 42 0)
           (cons 91 0)
           (list 10 12.0904 -0.714248)
           (cons 40 0)
           (cons 41 0)
           (cons 42 0)
           (cons 91 0)
           (list 10 11.94816 -0.762)
           (cons 40 0)
           (cons 41 0)
           (cons 42 0)
           (cons 91 0)
           (list 10 11.21664 -0.762)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.0744 -1.171448)
           (cons 40 0)
           (cons 41 0)
           (cons 42 0)
           (cons 91 0)
           (list 10 11.0744 -1.012952)
           (cons 40 0)
           (cons 41 0)
           (cons 42 0)
           (cons 91 0)
           (list 10 11.21664 -0.9652)
           (cons 40 0)
           (cons 41 0)
           (cons 42 0)
           (cons 91 0)
           (list 10 11.94816 -0.9652)
           (cons 40 0)
           (cons 41 0)
           (cons 42 0)
           (cons 91 0)
           (list 10 12.0904 -1.012952)
           (cons 40 0)
           (cons 41 0)
           (cons 42 0)
           (cons 91 0)
           (list 10 12.0904 -1.171448)
           (cons 40 0)
           (cons 41 0)
           (cons 42 0)
           (cons 91 0)
           (list 10 11.94816 -1.2192)
           (cons 40 0)
           (cons 41 0)
           (cons 42 0)
           (cons 91 0)
           (list 10 11.21664 -1.2192)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.0744 0.555752)
           (cons 40 0)
           (cons 41 0)
           (cons 42 0)
           (cons 91 0)
           (list 10 11.0744 0.714248)
           (cons 40 0)
           (cons 41 0)
           (cons 42 0)
           (cons 91 0)
           (list 10 11.21664 0.762)
           (cons 40 0)
           (cons 41 0)
           (cons 42 0)
           (cons 91 0)
           (list 10 11.94816 0.762)
           (cons 40 0)
           (cons 41 0)
           (cons 42 0)
           (cons 91 0)
           (list 10 12.0904 0.714248)
           (cons 40 0)
           (cons 41 0)
           (cons 42 0)
           (cons 91 0)
           (list 10 12.0904 0.555752)
           (cons 40 0)
           (cons 41 0)
           (cons 42 0)
           (cons 91 0)
           (list 10 11.94816 0.508)
           (cons 40 0)
           (cons 41 0)
           (cons 42 0)
           (cons 91 0)
           (list 10 11.21664 0.508)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.0744 1.012952)
           (cons 40 0)
           (cons 41 0)
           (cons 42 0)
           (cons 91 0)
           (list 10 11.0744 1.171448)
           (cons 40 0)
           (cons 41 0)
           (cons 42 0)
           (cons 91 0)
           (list 10 11.21664 1.2192)
           (cons 40 0)
           (cons 41 0)
           (cons 42 0)
           (cons 91 0)
           (list 10 11.94816 1.2192)
           (cons 40 0)
           (cons 41 0)
           (cons 42 0)
           (cons 91 0)
           (list 10 12.0904 1.171448)
           (cons 40 0)
           (cons 41 0)
           (cons 42 0)
           (cons 91 0)
           (list 10 12.0904 1.012952)
           (cons 40 0)
           (cons 41 0)
           (cons 42 0)
           (cons 91 0)
           (list 10 11.94816 0.9652)
           (cons 40 0)
           (cons 41 0)
           (cons 42 0)
           (cons 91 0)
           (list 10 11.21664 0.9652)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.3444 -0.714248)
           (cons 40 0)
           (cons 41 0)
           (cons 42 0)
           (cons 91 0)
           (list 10 12.3444 -0.555752)
           (cons 40 0)
           (cons 41 0)
           (cons 42 0)
           (cons 91 0)
           (list 10 12.48664 -0.508)
           (cons 40 0)
           (cons 41 0)
           (cons 42 0)
           (cons 91 0)
           (list 10 13.21816 -0.508)
           (cons 40 0)
           (cons 41 0)
           (cons 42 0)
           (cons 91 0)
           (list 10 13.3604 -0.555752)
           (cons 40 0)
           (cons 41 0)
           (cons 42 0)
           (cons 91 0)
           (list 10 13.3604 -0.714248)
           (cons 40 0)
           (cons 41 0)
           (cons 42 0)
           (cons 91 0)
           (list 10 13.21816 -0.762)
           (cons 40 0)
           (cons 41 0)
           (cons 42 0)
           (cons 91 0)
           (list 10 12.48664 -0.762)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.3444 -1.171448)
           (cons 40 0)
           (cons 41 0)
           (cons 42 0)
           (cons 91 0)
           (list 10 12.3444 -1.012952)
           (cons 40 0)
           (cons 41 0)
           (cons 42 0)
           (cons 91 0)
           (list 10 12.48664 -0.9652)
           (cons 40 0)
           (cons 41 0)
           (cons 42 0)
           (cons 91 0)
           (list 10 13.21816 -0.9652)
           (cons 40 0)
           (cons 41 0)
           (cons 42 0)
           (cons 91 0)
           (list 10 13.3604 -1.012952)
           (cons 40 0)
           (cons 41 0)
           (cons 42 0)
           (cons 91 0)
           (list 10 13.3604 -1.171448)
           (cons 40 0)
           (cons 41 0)
           (cons 42 0)
           (cons 91 0)
           (list 10 13.21816 -1.2192)
           (cons 40 0)
           (cons 41 0)
           (cons 42 0)
           (cons 91 0)
           (list 10 12.48664 -1.2192)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.3444 0.555752)
           (cons 40 0)
           (cons 41 0)
           (cons 42 0)
           (cons 91 0)
           (list 10 12.3444 0.714248)
           (cons 40 0)
           (cons 41 0)
           (cons 42 0)
           (cons 91 0)
           (list 10 12.48664 0.762)
           (cons 40 0)
           (cons 41 0)
           (cons 42 0)
           (cons 91 0)
           (list 10 13.21816 0.762)
           (cons 40 0)
           (cons 41 0)
           (cons 42 0)
           (cons 91 0)
           (list 10 13.3604 0.714248)
           (cons 40 0)
           (cons 41 0)
           (cons 42 0)
           (cons 91 0)
           (list 10 13.3604 0.555752)
           (cons 40 0)
           (cons 41 0)
           (cons 42 0)
           (cons 91 0)
           (list 10 13.21816 0.508)
           (cons 40 0)
           (cons 41 0)
           (cons 42 0)
           (cons 91 0)
           (list 10 12.48664 0.508)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.3444 1.012952)
           (cons 40 0)
           (cons 41 0)
           (cons 42 0)
           (cons 91 0)
           (list 10 12.3444 1.171448)
           (cons 40 0)
           (cons 41 0)
           (cons 42 0)
           (cons 91 0)
           (list 10 12.48664 1.2192)
           (cons 40 0)
           (cons 41 0)
           (cons 42 0)
           (cons 91 0)
           (list 10 13.21816 1.2192)
           (cons 40 0)
           (cons 41 0)
           (cons 42 0)
           (cons 91 0)
           (list 10 13.3604 1.171448)
           (cons 40 0)
           (cons 41 0)
           (cons 42 0)
           (cons 91 0)
           (list 10 13.3604 1.012952)
           (cons 40 0)
           (cons 41 0)
           (cons 42 0)
           (cons 91 0)
           (list 10 13.21816 0.9652)
           (cons 40 0)
           (cons 41 0)
           (cons 42 0)
           (cons 91 0)
           (list 10 12.48664 0.9652)
           (cons 40 0)
           (cons 41 0)
           (cons 42 0)
           (cons 91 0)
          )
         )
         (entmake
          (list
           (cons 0 "POINT")
           (cons 100 "AcDbEntity")
           (cons 67 0)
           (cons 8 "0")
           (cons 62 3)
           (cons 100 "AcDbPoint")
           (list 10 3.9624 0 0)
           (cons 50 0)
          )
         )
         (entmake
          (list
           (cons 0 "POINT")
           (cons 100 "AcDbEntity")
           (cons 67 0)
           (cons 8 "0")
           (cons 100 "AcDbPoint")
           (list 10 11.5824 1.2192 0)
           (cons 50 0)
          )
         )
         (entmake
          (list
           (cons 0 "POINT")
           (cons 100 "AcDbEntity")
           (cons 67 0)
           (cons 8 "0")
           (cons 100 "AcDbPoint")
           (list 10 11.5824 -1.2192 0)
           (cons 50 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "3.96")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "3.96")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "11.58")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "0.0001")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "POINT")
           (cons 100 "AcDbEntity")
           (cons 67 0)
           (cons 8 "0")
           (cons 62 1)
           (cons 100 "AcDbPoint")
           (list 10 0 0 0)
           (cons 50 0)
          )
         )
         (entmake
          (list
           (cons 0 "TEXT")
           (cons 100 "AcDbEntity")
           (cons 67 0)
           (cons 8 "0")
           (cons 100 "AcDbText")
           (list 10 4.79573333 -0.25 0)
           (cons 40 0.5)
           (cons 1 "5")
           (cons 50 0)
           (cons 41 1)
           (cons 51 0)
           (cons 7 "Standard")
           (cons 71 0)
           (cons 72 4)
           (list 11 4.9624 0 0)
           (cons 100 "AcDbText")
           (cons 73 0)
          )
         )
         (entmake
          (list
           (cons 0 "LWPOLYLINE")
           (cons 100 "AcDbEntity")
           (cons 67 0)
           (cons 8 "Defpoints")
           (cons 100 "AcDbPolyline")
           (cons 90 8)
           (cons 70 129)
           (cons 43 0)
           (cons 38 0)
           (cons 39 0)
           (list 10 9.8044 1.2192)
           (cons 40 0)
           (cons 41 0)
           (cons 42 0)
           (cons 91 0)
           (list 10 13.3604 1.2192)
           (cons 40 0)
           (cons 41 0)
           (cons 42 0)
           (cons 91 0)
           (list 10 13.3604 -1.2192)
           (cons 40 0)
           (cons 41 0)
           (cons 42 0)
           (cons 91 0)
           (list 10 9.8044 -1.2192)
           (cons 40 0)
           (cons 41 0)
           (cons 42 0)
           (cons 91 0)
           (list 10 9.8044 -0.3048)
           (cons 40 0)
           (cons 41 0)
           (cons 42 0)
           (cons 91 0)
           (list 10 0 -0.3048)
           (cons 40 0)
           (cons 41 0)
           (cons 42 0)
           (cons 91 0)
           (list 10 0 0.3048)
           (cons 40 0)
           (cons 41 0)
           (cons 42 0)
           (cons 91 0)
           (list 10 9.8044 0.3048)
           (cons 40 0)
           (cons 41 0)
           (cons 42 0)
           (cons 91 0)
          )
         )
         (entmake (list (cons 0 "ENDBLK")))
        )
       )
       ((= (strcase BLKNAME) (strcase "Special-19HeavyHaul-Trailer"))
        (progn
         (entmake)
         (entmake
          (list
           (cons 0 "BLOCK")
           (cons 2 "Special-19HeavyHaul-Trailer")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.8288 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 35.9664 -1.8288 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 35.9664 1.8288 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.8288 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.8288 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.8288 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "POINT")
           (cons 100 "AcDbEntity")
           (cons 67 0)
           (cons 8 "0")
           (cons 100 "AcDbPoint")
           (list 10 18.288 0 0)
           (cons 50 0)
          )
         )
         (entmake
          (list
           (cons 0 "POINT")
           (cons 100 "AcDbEntity")
           (cons 67 0)
           (cons 8 "0")
           (cons 100 "AcDbPoint")
           (list 10 0 -1.8288 0)
           (cons 50 0)
          )
         )
         (entmake
          (list
           (cons 0 "POINT")
           (cons 100 "AcDbEntity")
           (cons 67 0)
           (cons 8 "0")
           (cons 100 "AcDbPoint")
           (list 10 35.9664 -1.8288 0)
           (cons 50 0)
          )
         )
         (entmake
          (list
           (cons 0 "POINT")
           (cons 100 "AcDbEntity")
           (cons 67 0)
           (cons 8 "0")
           (cons 100 "AcDbPoint")
           (list 10 35.9664 1.8288 0)
           (cons 50 0)
          )
         )
         (entmake
          (list
           (cons 0 "POINT")
           (cons 100 "AcDbEntity")
           (cons 67 0)
           (cons 8 "0")
           (cons 100 "AcDbPoint")
           (list 10 0 1.8288 0)
           (cons 50 0)
          )
         )
         (entmake
          (list
           (cons 0 "POINT")
           (cons 100 "AcDbEntity")
           (cons 67 0)
           (cons 8 "0")
           (cons 62 3)
           (cons 100 "AcDbPoint")
           (list 10 0 0 0)
           (cons 50 0)
          )
         )
         (entmake
          (list
           (cons 0 "POINT")
           (cons 100 "AcDbEntity")
           (cons 67 0)
           (cons 8 "0")
           (cons 62 1)
           (cons 100 "AcDbPoint")
           (list 10 35.9664 0 0)
           (cons 50 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "0.00")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "0.00")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "18.29")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "35.97")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "TEXT")
           (cons 100 "AcDbEntity")
           (cons 67 0)
           (cons 8 "0")
           (cons 100 "AcDbText")
           (list 10 0.82142857 -0.25 0)
           (cons 40 0.5)
           (cons 1 "4")
           (cons 50 0)
           (cons 41 1)
           (cons 51 0)
           (cons 7 "Standard")
           (cons 71 0)
           (cons 72 4)
           (list 11 1 0 0)
           (cons 100 "AcDbText")
           (cons 73 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 1.8288)
           (cons 40 0)
           (cons 41 0)
           (cons 42 0)
           (cons 91 0)
           (list 10 35.9664 1.8288)
           (cons 40 0)
           (cons 41 0)
           (cons 42 0)
           (cons 91 0)
           (list 10 35.9664 -1.8288)
           (cons 40 0)
           (cons 41 0)
           (cons 42 0)
           (cons 91 0)
           (list 10 0 -1.8288)
           (cons 40 0)
           (cons 41 0)
           (cons 42 0)
           (cons 91 0)
          )
         )
         (entmake (list (cons 0 "ENDBLK")))
        )
       )
       ((= (strcase BLKNAME) (strcase "Special-19HeavyHaul-Pup2"))
        (progn
         (entmake)
         (entmake
          (list
           (cons 0 "BLOCK")
           (cons 2 "Special-19HeavyHaul-Pup2")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15.24 -0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15.24 -0.508 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15.9004 -0.508 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15.9004 0.508 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15.24 0.508 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15.24 0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.3048 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 1.8288 0 0)
           (cons 40 0.097536)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 5.4864 0 0)
           (cons 40 0.34834286)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 5.7327156 -0.2463156 0)
           (list 11 5.7327156 0.2463156 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.8524 -0.714248)
           (cons 40 0)
           (cons 41 0)
           (cons 42 0)
           (cons 91 0)
           (list 10 12.8524 -0.555752)
           (cons 40 0)
           (cons 41 0)
           (cons 42 0)
           (cons 91 0)
           (list 10 12.99464 -0.508)
           (cons 40 0)
           (cons 41 0)
           (cons 42 0)
           (cons 91 0)
           (list 10 13.72616 -0.508)
           (cons 40 0)
           (cons 41 0)
           (cons 42 0)
           (cons 91 0)
           (list 10 13.8684 -0.555752)
           (cons 40 0)
           (cons 41 0)
           (cons 42 0)
           (cons 91 0)
           (list 10 13.8684 -0.714248)
           (cons 40 0)
           (cons 41 0)
           (cons 42 0)
           (cons 91 0)
           (list 10 13.72616 -0.762)
           (cons 40 0)
           (cons 41 0)
           (cons 42 0)
           (cons 91 0)
           (list 10 12.99464 -0.762)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.8524 -1.171448)
           (cons 40 0)
           (cons 41 0)
           (cons 42 0)
           (cons 91 0)
           (list 10 12.8524 -1.012952)
           (cons 40 0)
           (cons 41 0)
           (cons 42 0)
           (cons 91 0)
           (list 10 12.99464 -0.9652)
           (cons 40 0)
           (cons 41 0)
           (cons 42 0)
           (cons 91 0)
           (list 10 13.72616 -0.9652)
           (cons 40 0)
           (cons 41 0)
           (cons 42 0)
           (cons 91 0)
           (list 10 13.8684 -1.012952)
           (cons 40 0)
           (cons 41 0)
           (cons 42 0)
           (cons 91 0)
           (list 10 13.8684 -1.171448)
           (cons 40 0)
           (cons 41 0)
           (cons 42 0)
           (cons 91 0)
           (list 10 13.72616 -1.2192)
           (cons 40 0)
           (cons 41 0)
           (cons 42 0)
           (cons 91 0)
           (list 10 12.99464 -1.2192)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.8524 0.555752)
           (cons 40 0)
           (cons 41 0)
           (cons 42 0)
           (cons 91 0)
           (list 10 12.8524 0.714248)
           (cons 40 0)
           (cons 41 0)
           (cons 42 0)
           (cons 91 0)
           (list 10 12.99464 0.762)
           (cons 40 0)
           (cons 41 0)
           (cons 42 0)
           (cons 91 0)
           (list 10 13.72616 0.762)
           (cons 40 0)
           (cons 41 0)
           (cons 42 0)
           (cons 91 0)
           (list 10 13.8684 0.714248)
           (cons 40 0)
           (cons 41 0)
           (cons 42 0)
           (cons 91 0)
           (list 10 13.8684 0.555752)
           (cons 40 0)
           (cons 41 0)
           (cons 42 0)
           (cons 91 0)
           (list 10 13.72616 0.508)
           (cons 40 0)
           (cons 41 0)
           (cons 42 0)
           (cons 91 0)
           (list 10 12.99464 0.508)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.8524 1.012952)
           (cons 40 0)
           (cons 41 0)
           (cons 42 0)
           (cons 91 0)
           (list 10 12.8524 1.171448)
           (cons 40 0)
           (cons 41 0)
           (cons 42 0)
           (cons 91 0)
           (list 10 12.99464 1.2192)
           (cons 40 0)
           (cons 41 0)
           (cons 42 0)
           (cons 91 0)
           (list 10 13.72616 1.2192)
           (cons 40 0)
           (cons 41 0)
           (cons 42 0)
           (cons 91 0)
           (list 10 13.8684 1.171448)
           (cons 40 0)
           (cons 41 0)
           (cons 42 0)
           (cons 91 0)
           (list 10 13.8684 1.012952)
           (cons 40 0)
           (cons 41 0)
           (cons 42 0)
           (cons 91 0)
           (list 10 13.72616 0.9652)
           (cons 40 0)
           (cons 41 0)
           (cons 42 0)
           (cons 91 0)
           (list 10 12.99464 0.9652)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.1224 -0.714248)
           (cons 40 0)
           (cons 41 0)
           (cons 42 0)
           (cons 91 0)
           (list 10 14.1224 -0.555752)
           (cons 40 0)
           (cons 41 0)
           (cons 42 0)
           (cons 91 0)
           (list 10 14.26464 -0.508)
           (cons 40 0)
           (cons 41 0)
           (cons 42 0)
           (cons 91 0)
           (list 10 14.99616 -0.508)
           (cons 40 0)
           (cons 41 0)
           (cons 42 0)
           (cons 91 0)
           (list 10 15.1384 -0.555752)
           (cons 40 0)
           (cons 41 0)
           (cons 42 0)
           (cons 91 0)
           (list 10 15.1384 -0.714248)
           (cons 40 0)
           (cons 41 0)
           (cons 42 0)
           (cons 91 0)
           (list 10 14.99616 -0.762)
           (cons 40 0)
           (cons 41 0)
           (cons 42 0)
           (cons 91 0)
           (list 10 14.26464 -0.762)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.1224 -1.171448)
           (cons 40 0)
           (cons 41 0)
           (cons 42 0)
           (cons 91 0)
           (list 10 14.1224 -1.012952)
           (cons 40 0)
           (cons 41 0)
           (cons 42 0)
           (cons 91 0)
           (list 10 14.26464 -0.9652)
           (cons 40 0)
           (cons 41 0)
           (cons 42 0)
           (cons 91 0)
           (list 10 14.99616 -0.9652)
           (cons 40 0)
           (cons 41 0)
           (cons 42 0)
           (cons 91 0)
           (list 10 15.1384 -1.012952)
           (cons 40 0)
           (cons 41 0)
           (cons 42 0)
           (cons 91 0)
           (list 10 15.1384 -1.171448)
           (cons 40 0)
           (cons 41 0)
           (cons 42 0)
           (cons 91 0)
           (list 10 14.99616 -1.2192)
           (cons 40 0)
           (cons 41 0)
           (cons 42 0)
           (cons 91 0)
           (list 10 14.26464 -1.2192)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.1224 0.555752)
           (cons 40 0)
           (cons 41 0)
           (cons 42 0)
           (cons 91 0)
           (list 10 14.1224 0.714248)
           (cons 40 0)
           (cons 41 0)
           (cons 42 0)
           (cons 91 0)
           (list 10 14.26464 0.762)
           (cons 40 0)
           (cons 41 0)
           (cons 42 0)
           (cons 91 0)
           (list 10 14.99616 0.762)
           (cons 40 0)
           (cons 41 0)
           (cons 42 0)
           (cons 91 0)
           (list 10 15.1384 0.714248)
           (cons 40 0)
           (cons 41 0)
           (cons 42 0)
           (cons 91 0)
           (list 10 15.1384 0.555752)
           (cons 40 0)
           (cons 41 0)
           (cons 42 0)
           (cons 91 0)
           (list 10 14.99616 0.508)
           (cons 40 0)
           (cons 41 0)
           (cons 42 0)
           (cons 91 0)
           (list 10 14.26464 0.508)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 14.1224 1.012952)
           (cons 40 0)
           (cons 41 0)
           (cons 42 0)
           (cons 91 0)
           (list 10 14.1224 1.171448)
           (cons 40 0)
           (cons 41 0)
           (cons 42 0)
           (cons 91 0)
           (list 10 14.26464 1.2192)
           (cons 40 0)
           (cons 41 0)
           (cons 42 0)
           (cons 91 0)
           (list 10 14.99616 1.2192)
           (cons 40 0)
           (cons 41 0)
           (cons 42 0)
           (cons 91 0)
           (list 10 15.1384 1.171448)
           (cons 40 0)
           (cons 41 0)
           (cons 42 0)
           (cons 91 0)
           (list 10 15.1384 1.012952)
           (cons 40 0)
           (cons 41 0)
           (cons 42 0)
           (cons 91 0)
           (list 10 14.99616 0.9652)
           (cons 40 0)
           (cons 41 0)
           (cons 42 0)
           (cons 91 0)
           (list 10 14.26464 0.9652)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 15.3924 -0.714248)
           (cons 40 0)
           (cons 41 0)
           (cons 42 0)
           (cons 91 0)
           (list 10 15.3924 -0.555752)
           (cons 40 0)
           (cons 41 0)
           (cons 42 0)
           (cons 91 0)
           (list 10 15.53464 -0.508)
           (cons 40 0)
           (cons 41 0)
           (cons 42 0)
           (cons 91 0)
           (list 10 16.26616 -0.508)
           (cons 40 0)
           (cons 41 0)
           (cons 42 0)
           (cons 91 0)
           (list 10 16.4084 -0.555752)
           (cons 40 0)
           (cons 41 0)
           (cons 42 0)
           (cons 91 0)
           (list 10 16.4084 -0.714248)
           (cons 40 0)
           (cons 41 0)
           (cons 42 0)
           (cons 91 0)
           (list 10 16.26616 -0.762)
           (cons 40 0)
           (cons 41 0)
           (cons 42 0)
           (cons 91 0)
           (list 10 15.53464 -0.762)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 15.3924 -1.171448)
           (cons 40 0)
           (cons 41 0)
           (cons 42 0)
           (cons 91 0)
           (list 10 15.3924 -1.012952)
           (cons 40 0)
           (cons 41 0)
           (cons 42 0)
           (cons 91 0)
           (list 10 15.53464 -0.9652)
           (cons 40 0)
           (cons 41 0)
           (cons 42 0)
           (cons 91 0)
           (list 10 16.26616 -0.9652)
           (cons 40 0)
           (cons 41 0)
           (cons 42 0)
           (cons 91 0)
           (list 10 16.4084 -1.012952)
           (cons 40 0)
           (cons 41 0)
           (cons 42 0)
           (cons 91 0)
           (list 10 16.4084 -1.171448)
           (cons 40 0)
           (cons 41 0)
           (cons 42 0)
           (cons 91 0)
           (list 10 16.26616 -1.2192)
           (cons 40 0)
           (cons 41 0)
           (cons 42 0)
           (cons 91 0)
           (list 10 15.53464 -1.2192)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 15.3924 0.555752)
           (cons 40 0)
           (cons 41 0)
           (cons 42 0)
           (cons 91 0)
           (list 10 15.3924 0.714248)
           (cons 40 0)
           (cons 41 0)
           (cons 42 0)
           (cons 91 0)
           (list 10 15.53464 0.762)
           (cons 40 0)
           (cons 41 0)
           (cons 42 0)
           (cons 91 0)
           (list 10 16.26616 0.762)
           (cons 40 0)
           (cons 41 0)
           (cons 42 0)
           (cons 91 0)
           (list 10 16.4084 0.714248)
           (cons 40 0)
           (cons 41 0)
           (cons 42 0)
           (cons 91 0)
           (list 10 16.4084 0.555752)
           (cons 40 0)
           (cons 41 0)
           (cons 42 0)
           (cons 91 0)
           (list 10 16.26616 0.508)
           (cons 40 0)
           (cons 41 0)
           (cons 42 0)
           (cons 91 0)
           (list 10 15.53464 0.508)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 15.3924 1.012952)
           (cons 40 0)
           (cons 41 0)
           (cons 42 0)
           (cons 91 0)
           (list 10 15.3924 1.171448)
           (cons 40 0)
           (cons 41 0)
           (cons 42 0)
           (cons 91 0)
           (list 10 15.53464 1.2192)
           (cons 40 0)
           (cons 41 0)
           (cons 42 0)
           (cons 91 0)
           (list 10 16.26616 1.2192)
           (cons 40 0)
           (cons 41 0)
           (cons 42 0)
           (cons 91 0)
           (list 10 16.4084 1.171448)
           (cons 40 0)
           (cons 41 0)
           (cons 42 0)
           (cons 91 0)
           (list 10 16.4084 1.012952)
           (cons 40 0)
           (cons 41 0)
           (cons 42 0)
           (cons 91 0)
           (list 10 16.26616 0.9652)
           (cons 40 0)
           (cons 41 0)
           (cons 42 0)
           (cons 91 0)
           (list 10 15.53464 0.9652)
           (cons 40 0)
           (cons 41 0)
           (cons 42 0)
           (cons 91 0)
          )
         )
         (entmake
          (list
           (cons 0 "POINT")
           (cons 100 "AcDbEntity")
           (cons 67 0)
           (cons 8 "0")
           (cons 62 3)
           (cons 100 "AcDbPoint")
           (list 10 1.8288 0 0)
           (cons 50 0)
          )
         )
         (entmake
          (list
           (cons 0 "POINT")
           (cons 100 "AcDbEntity")
           (cons 67 0)
           (cons 8 "0")
           (cons 62 1)
           (cons 100 "AcDbPoint")
           (list 10 5.4864 0 0)
           (cons 50 0)
          )
         )
         (entmake
          (list
           (cons 0 "POINT")
           (cons 100 "AcDbEntity")
           (cons 67 0)
           (cons 8 "0")
           (cons 100 "AcDbPoint")
           (list 10 14.6304 1.2192 0)
           (cons 50 0)
          )
         )
         (entmake
          (list
           (cons 0 "POINT")
           (cons 100 "AcDbEntity")
           (cons 67 0)
           (cons 8 "0")
           (cons 100 "AcDbPoint")
           (list 10 14.6304 -1.2192 0)
           (cons 50 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "1.83")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "1.83")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "14.63")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "5.49")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "TEXT")
           (cons 100 "AcDbEntity")
           (cons 67 0)
           (cons 8 "0")
           (cons 100 "AcDbText")
           (list 10 2.66213333 -0.25 0)
           (cons 40 0.5)
           (cons 1 "3")
           (cons 50 0)
           (cons 41 1)
           (cons 51 0)
           (cons 7 "Standard")
           (cons 71 0)
           (cons 72 4)
           (list 11 2.8288 0 0)
           (cons 100 "AcDbText")
           (cons 73 0)
          )
         )
         (entmake
          (list
           (cons 0 "LWPOLYLINE")
           (cons 100 "AcDbEntity")
           (cons 67 0)
           (cons 8 "Defpoints")
           (cons 100 "AcDbPolyline")
           (cons 90 8)
           (cons 70 129)
           (cons 43 0)
           (cons 38 0)
           (cons 39 0)
           (list 10 12.8524 1.2192)
           (cons 40 0)
           (cons 41 0)
           (cons 42 0)
           (cons 91 0)
           (list 10 16.4084 1.2192)
           (cons 40 0)
           (cons 41 0)
           (cons 42 0)
           (cons 91 0)
           (list 10 16.4084 -1.2192)
           (cons 40 0)
           (cons 41 0)
           (cons 42 0)
           (cons 91 0)
           (list 10 12.8524 -1.2192)
           (cons 40 0)
           (cons 41 0)
           (cons 42 0)
           (cons 91 0)
           (list 10 12.8524 -0.3048)
           (cons 40 0)
           (cons 41 0)
           (cons 42 0)
           (cons 91 0)
           (list 10 0 -0.3048)
           (cons 40 0)
           (cons 41 0)
           (cons 42 0)
           (cons 91 0)
           (list 10 0 0.3048)
           (cons 40 0)
           (cons 41 0)
           (cons 42 0)
           (cons 91 0)
           (list 10 12.8524 0.3048)
           (cons 40 0)
           (cons 41 0)
           (cons 42 0)
           (cons 91 0)
          )
         )
         (entmake (list (cons 0 "ENDBLK")))
        )
       )
       ((= (strcase BLKNAME) (strcase "Special-19HeavyHaul-Pup1"))
        (progn
         (entmake)
         (entmake
          (list
           (cons 0 "BLOCK")
           (cons 2 "Special-19HeavyHaul-Pup1")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 10.3632 -0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 10.3632 -0.508 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 11.0236 -0.508 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 11.0236 0.508 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 10.3632 0.508 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 10.3632 0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.3048 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -0.3048 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 1.8288 0 0)
           (cons 40 0.097536)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 6.096 0 0)
           (cons 40 0.34834286)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 6.3423156 -0.2463156 0)
           (list 11 6.3423156 0.2463156 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.9756 -0.714248)
           (cons 40 0)
           (cons 41 0)
           (cons 42 0)
           (cons 91 0)
           (list 10 7.9756 -0.555752)
           (cons 40 0)
           (cons 41 0)
           (cons 42 0)
           (cons 91 0)
           (list 10 8.11784 -0.508)
           (cons 40 0)
           (cons 41 0)
           (cons 42 0)
           (cons 91 0)
           (list 10 8.84936 -0.508)
           (cons 40 0)
           (cons 41 0)
           (cons 42 0)
           (cons 91 0)
           (list 10 8.9916 -0.555752)
           (cons 40 0)
           (cons 41 0)
           (cons 42 0)
           (cons 91 0)
           (list 10 8.9916 -0.714248)
           (cons 40 0)
           (cons 41 0)
           (cons 42 0)
           (cons 91 0)
           (list 10 8.84936 -0.762)
           (cons 40 0)
           (cons 41 0)
           (cons 42 0)
           (cons 91 0)
           (list 10 8.11784 -0.762)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.9756 -1.171448)
           (cons 40 0)
           (cons 41 0)
           (cons 42 0)
           (cons 91 0)
           (list 10 7.9756 -1.012952)
           (cons 40 0)
           (cons 41 0)
           (cons 42 0)
           (cons 91 0)
           (list 10 8.11784 -0.9652)
           (cons 40 0)
           (cons 41 0)
           (cons 42 0)
           (cons 91 0)
           (list 10 8.84936 -0.9652)
           (cons 40 0)
           (cons 41 0)
           (cons 42 0)
           (cons 91 0)
           (list 10 8.9916 -1.012952)
           (cons 40 0)
           (cons 41 0)
           (cons 42 0)
           (cons 91 0)
           (list 10 8.9916 -1.171448)
           (cons 40 0)
           (cons 41 0)
           (cons 42 0)
           (cons 91 0)
           (list 10 8.84936 -1.2192)
           (cons 40 0)
           (cons 41 0)
           (cons 42 0)
           (cons 91 0)
           (list 10 8.11784 -1.2192)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.9756 0.555752)
           (cons 40 0)
           (cons 41 0)
           (cons 42 0)
           (cons 91 0)
           (list 10 7.9756 0.714248)
           (cons 40 0)
           (cons 41 0)
           (cons 42 0)
           (cons 91 0)
           (list 10 8.11784 0.762)
           (cons 40 0)
           (cons 41 0)
           (cons 42 0)
           (cons 91 0)
           (list 10 8.84936 0.762)
           (cons 40 0)
           (cons 41 0)
           (cons 42 0)
           (cons 91 0)
           (list 10 8.9916 0.714248)
           (cons 40 0)
           (cons 41 0)
           (cons 42 0)
           (cons 91 0)
           (list 10 8.9916 0.555752)
           (cons 40 0)
           (cons 41 0)
           (cons 42 0)
           (cons 91 0)
           (list 10 8.84936 0.508)
           (cons 40 0)
           (cons 41 0)
           (cons 42 0)
           (cons 91 0)
           (list 10 8.11784 0.508)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.9756 1.012952)
           (cons 40 0)
           (cons 41 0)
           (cons 42 0)
           (cons 91 0)
           (list 10 7.9756 1.171448)
           (cons 40 0)
           (cons 41 0)
           (cons 42 0)
           (cons 91 0)
           (list 10 8.11784 1.2192)
           (cons 40 0)
           (cons 41 0)
           (cons 42 0)
           (cons 91 0)
           (list 10 8.84936 1.2192)
           (cons 40 0)
           (cons 41 0)
           (cons 42 0)
           (cons 91 0)
           (list 10 8.9916 1.171448)
           (cons 40 0)
           (cons 41 0)
           (cons 42 0)
           (cons 91 0)
           (list 10 8.9916 1.012952)
           (cons 40 0)
           (cons 41 0)
           (cons 42 0)
           (cons 91 0)
           (list 10 8.84936 0.9652)
           (cons 40 0)
           (cons 41 0)
           (cons 42 0)
           (cons 91 0)
           (list 10 8.11784 0.9652)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.2456 -0.714248)
           (cons 40 0)
           (cons 41 0)
           (cons 42 0)
           (cons 91 0)
           (list 10 9.2456 -0.555752)
           (cons 40 0)
           (cons 41 0)
           (cons 42 0)
           (cons 91 0)
           (list 10 9.38784 -0.508)
           (cons 40 0)
           (cons 41 0)
           (cons 42 0)
           (cons 91 0)
           (list 10 10.11936 -0.508)
           (cons 40 0)
           (cons 41 0)
           (cons 42 0)
           (cons 91 0)
           (list 10 10.2616 -0.555752)
           (cons 40 0)
           (cons 41 0)
           (cons 42 0)
           (cons 91 0)
           (list 10 10.2616 -0.714248)
           (cons 40 0)
           (cons 41 0)
           (cons 42 0)
           (cons 91 0)
           (list 10 10.11936 -0.762)
           (cons 40 0)
           (cons 41 0)
           (cons 42 0)
           (cons 91 0)
           (list 10 9.38784 -0.762)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.2456 -1.171448)
           (cons 40 0)
           (cons 41 0)
           (cons 42 0)
           (cons 91 0)
           (list 10 9.2456 -1.012952)
           (cons 40 0)
           (cons 41 0)
           (cons 42 0)
           (cons 91 0)
           (list 10 9.38784 -0.9652)
           (cons 40 0)
           (cons 41 0)
           (cons 42 0)
           (cons 91 0)
           (list 10 10.11936 -0.9652)
           (cons 40 0)
           (cons 41 0)
           (cons 42 0)
           (cons 91 0)
           (list 10 10.2616 -1.012952)
           (cons 40 0)
           (cons 41 0)
           (cons 42 0)
           (cons 91 0)
           (list 10 10.2616 -1.171448)
           (cons 40 0)
           (cons 41 0)
           (cons 42 0)
           (cons 91 0)
           (list 10 10.11936 -1.2192)
           (cons 40 0)
           (cons 41 0)
           (cons 42 0)
           (cons 91 0)
           (list 10 9.38784 -1.2192)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.2456 0.555752)
           (cons 40 0)
           (cons 41 0)
           (cons 42 0)
           (cons 91 0)
           (list 10 9.2456 0.714248)
           (cons 40 0)
           (cons 41 0)
           (cons 42 0)
           (cons 91 0)
           (list 10 9.38784 0.762)
           (cons 40 0)
           (cons 41 0)
           (cons 42 0)
           (cons 91 0)
           (list 10 10.11936 0.762)
           (cons 40 0)
           (cons 41 0)
           (cons 42 0)
           (cons 91 0)
           (list 10 10.2616 0.714248)
           (cons 40 0)
           (cons 41 0)
           (cons 42 0)
           (cons 91 0)
           (list 10 10.2616 0.555752)
           (cons 40 0)
           (cons 41 0)
           (cons 42 0)
           (cons 91 0)
           (list 10 10.11936 0.508)
           (cons 40 0)
           (cons 41 0)
           (cons 42 0)
           (cons 91 0)
           (list 10 9.38784 0.508)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.2456 1.012952)
           (cons 40 0)
           (cons 41 0)
           (cons 42 0)
           (cons 91 0)
           (list 10 9.2456 1.171448)
           (cons 40 0)
           (cons 41 0)
           (cons 42 0)
           (cons 91 0)
           (list 10 9.38784 1.2192)
           (cons 40 0)
           (cons 41 0)
           (cons 42 0)
           (cons 91 0)
           (list 10 10.11936 1.2192)
           (cons 40 0)
           (cons 41 0)
           (cons 42 0)
           (cons 91 0)
           (list 10 10.2616 1.171448)
           (cons 40 0)
           (cons 41 0)
           (cons 42 0)
           (cons 91 0)
           (list 10 10.2616 1.012952)
           (cons 40 0)
           (cons 41 0)
           (cons 42 0)
           (cons 91 0)
           (list 10 10.11936 0.9652)
           (cons 40 0)
           (cons 41 0)
           (cons 42 0)
           (cons 91 0)
           (list 10 9.38784 0.9652)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.5156 -0.714248)
           (cons 40 0)
           (cons 41 0)
           (cons 42 0)
           (cons 91 0)
           (list 10 10.5156 -0.555752)
           (cons 40 0)
           (cons 41 0)
           (cons 42 0)
           (cons 91 0)
           (list 10 10.65784 -0.508)
           (cons 40 0)
           (cons 41 0)
           (cons 42 0)
           (cons 91 0)
           (list 10 11.38936 -0.508)
           (cons 40 0)
           (cons 41 0)
           (cons 42 0)
           (cons 91 0)
           (list 10 11.5316 -0.555752)
           (cons 40 0)
           (cons 41 0)
           (cons 42 0)
           (cons 91 0)
           (list 10 11.5316 -0.714248)
           (cons 40 0)
           (cons 41 0)
           (cons 42 0)
           (cons 91 0)
           (list 10 11.38936 -0.762)
           (cons 40 0)
           (cons 41 0)
           (cons 42 0)
           (cons 91 0)
           (list 10 10.65784 -0.762)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.5156 -1.171448)
           (cons 40 0)
           (cons 41 0)
           (cons 42 0)
           (cons 91 0)
           (list 10 10.5156 -1.012952)
           (cons 40 0)
           (cons 41 0)
           (cons 42 0)
           (cons 91 0)
           (list 10 10.65784 -0.9652)
           (cons 40 0)
           (cons 41 0)
           (cons 42 0)
           (cons 91 0)
           (list 10 11.38936 -0.9652)
           (cons 40 0)
           (cons 41 0)
           (cons 42 0)
           (cons 91 0)
           (list 10 11.5316 -1.012952)
           (cons 40 0)
           (cons 41 0)
           (cons 42 0)
           (cons 91 0)
           (list 10 11.5316 -1.171448)
           (cons 40 0)
           (cons 41 0)
           (cons 42 0)
           (cons 91 0)
           (list 10 11.38936 -1.2192)
           (cons 40 0)
           (cons 41 0)
           (cons 42 0)
           (cons 91 0)
           (list 10 10.65784 -1.2192)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.5156 0.555752)
           (cons 40 0)
           (cons 41 0)
           (cons 42 0)
           (cons 91 0)
           (list 10 10.5156 0.714248)
           (cons 40 0)
           (cons 41 0)
           (cons 42 0)
           (cons 91 0)
           (list 10 10.65784 0.762)
           (cons 40 0)
           (cons 41 0)
           (cons 42 0)
           (cons 91 0)
           (list 10 11.38936 0.762)
           (cons 40 0)
           (cons 41 0)
           (cons 42 0)
           (cons 91 0)
           (list 10 11.5316 0.714248)
           (cons 40 0)
           (cons 41 0)
           (cons 42 0)
           (cons 91 0)
           (list 10 11.5316 0.555752)
           (cons 40 0)
           (cons 41 0)
           (cons 42 0)
           (cons 91 0)
           (list 10 11.38936 0.508)
           (cons 40 0)
           (cons 41 0)
           (cons 42 0)
           (cons 91 0)
           (list 10 10.65784 0.508)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 10.5156 1.012952)
           (cons 40 0)
           (cons 41 0)
           (cons 42 0)
           (cons 91 0)
           (list 10 10.5156 1.171448)
           (cons 40 0)
           (cons 41 0)
           (cons 42 0)
           (cons 91 0)
           (list 10 10.65784 1.2192)
           (cons 40 0)
           (cons 41 0)
           (cons 42 0)
           (cons 91 0)
           (list 10 11.38936 1.2192)
           (cons 40 0)
           (cons 41 0)
           (cons 42 0)
           (cons 91 0)
           (list 10 11.5316 1.171448)
           (cons 40 0)
           (cons 41 0)
           (cons 42 0)
           (cons 91 0)
           (list 10 11.5316 1.012952)
           (cons 40 0)
           (cons 41 0)
           (cons 42 0)
           (cons 91 0)
           (list 10 11.38936 0.9652)
           (cons 40 0)
           (cons 41 0)
           (cons 42 0)
           (cons 91 0)
           (list 10 10.65784 0.9652)
           (cons 40 0)
           (cons 41 0)
           (cons 42 0)
           (cons 91 0)
          )
         )
         (entmake
          (list
           (cons 0 "POINT")
           (cons 100 "AcDbEntity")
           (cons 67 0)
           (cons 8 "0")
           (cons 62 3)
           (cons 100 "AcDbPoint")
           (list 10 1.8288 0 0)
           (cons 50 0)
          )
         )
         (entmake
          (list
           (cons 0 "POINT")
           (cons 100 "AcDbEntity")
           (cons 67 0)
           (cons 8 "0")
           (cons 62 1)
           (cons 100 "AcDbPoint")
           (list 10 6.096 0 0)
           (cons 50 0)
          )
         )
         (entmake
          (list
           (cons 0 "POINT")
           (cons 100 "AcDbEntity")
           (cons 67 0)
           (cons 8 "0")
           (cons 100 "AcDbPoint")
           (list 10 9.7536 1.2192 0)
           (cons 50 0)
          )
         )
         (entmake
          (list
           (cons 0 "POINT")
           (cons 100 "AcDbEntity")
           (cons 67 0)
           (cons 8 "0")
           (cons 100 "AcDbPoint")
           (list 10 9.7536 -1.2192 0)
           (cons 50 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "1.83")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "1.83")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "9.75")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "6.09")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "TEXT")
           (cons 100 "AcDbEntity")
           (cons 67 0)
           (cons 8 "0")
           (cons 100 "AcDbText")
           (list 10 2.66213333 -0.25 0)
           (cons 40 0.5)
           (cons 1 "2")
           (cons 50 0)
           (cons 41 1)
           (cons 51 0)
           (cons 7 "Standard")
           (cons 71 0)
           (cons 72 4)
           (list 11 2.8288 0 0)
           (cons 100 "AcDbText")
           (cons 73 0)
          )
         )
         (entmake
          (list
           (cons 0 "LWPOLYLINE")
           (cons 100 "AcDbEntity")
           (cons 67 0)
           (cons 8 "Defpoints")
           (cons 100 "AcDbPolyline")
           (cons 90 8)
           (cons 70 129)
           (cons 43 0)
           (cons 38 0)
           (cons 39 0)
           (list 10 7.9756 1.2192)
           (cons 40 0)
           (cons 41 0)
           (cons 42 0)
           (cons 91 0)
           (list 10 11.5316 1.2192)
           (cons 40 0)
           (cons 41 0)
           (cons 42 0)
           (cons 91 0)
           (list 10 11.5316 -1.2192)
           (cons 40 0)
           (cons 41 0)
           (cons 42 0)
           (cons 91 0)
           (list 10 7.9756 -1.2192)
           (cons 40 0)
           (cons 41 0)
           (cons 42 0)
           (cons 91 0)
           (list 10 7.9756 -0.3048)
           (cons 40 0)
           (cons 41 0)
           (cons 42 0)
           (cons 91 0)
           (list 10 0 -0.3048)
           (cons 40 0)
           (cons 41 0)
           (cons 42 0)
           (cons 91 0)
           (list 10 0 0.3048)
           (cons 40 0)
           (cons 41 0)
           (cons 42 0)
           (cons 91 0)
           (list 10 7.9756 0.3048)
           (cons 40 0)
           (cons 41 0)
           (cons 42 0)
           (cons 91 0)
          )
         )
         (entmake (list (cons 0 "ENDBLK")))
        )
       )
       ((= (strcase BLKNAME) (strcase "Special-19HeavyHaul-Truck"))
        (progn
         (entmake)
         (entmake
          (list
           (cons 0 "BLOCK")
           (cons 2 "Special-19HeavyHaul-Truck")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.524 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.1816 -1.524 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.1816 -0.5842 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.89 -0.5842 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.89 0.5842 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.1816 0.5842 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.1816 1.524 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.524 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.524 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.524 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 7.62 0 0)
           (cons 40 0.37011429)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 7.88171032 -0.26171032 0)
           (list 11 7.88171032 0.26171032 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.842 -0.790448)
           (cons 40 0)
           (cons 41 0)
           (cons 42 0)
           (cons 91 0)
           (list 10 5.842 -0.631952)
           (cons 40 0)
           (cons 41 0)
           (cons 42 0)
           (cons 91 0)
           (list 10 5.98424 -0.5842)
           (cons 40 0)
           (cons 41 0)
           (cons 42 0)
           (cons 91 0)
           (list 10 6.71576 -0.5842)
           (cons 40 0)
           (cons 41 0)
           (cons 42 0)
           (cons 91 0)
           (list 10 6.858 -0.631952)
           (cons 40 0)
           (cons 41 0)
           (cons 42 0)
           (cons 91 0)
           (list 10 6.858 -0.790448)
           (cons 40 0)
           (cons 41 0)
           (cons 42 0)
           (cons 91 0)
           (list 10 6.71576 -0.8382)
           (cons 40 0)
           (cons 41 0)
           (cons 42 0)
           (cons 91 0)
           (list 10 5.98424 -0.8382)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.842 -1.247648)
           (cons 40 0)
           (cons 41 0)
           (cons 42 0)
           (cons 91 0)
           (list 10 5.842 -1.089152)
           (cons 40 0)
           (cons 41 0)
           (cons 42 0)
           (cons 91 0)
           (list 10 5.98424 -1.0414)
           (cons 40 0)
           (cons 41 0)
           (cons 42 0)
           (cons 91 0)
           (list 10 6.71576 -1.0414)
           (cons 40 0)
           (cons 41 0)
           (cons 42 0)
           (cons 91 0)
           (list 10 6.858 -1.089152)
           (cons 40 0)
           (cons 41 0)
           (cons 42 0)
           (cons 91 0)
           (list 10 6.858 -1.247648)
           (cons 40 0)
           (cons 41 0)
           (cons 42 0)
           (cons 91 0)
           (list 10 6.71576 -1.2954)
           (cons 40 0)
           (cons 41 0)
           (cons 42 0)
           (cons 91 0)
           (list 10 5.98424 -1.2954)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.842 0.631952)
           (cons 40 0)
           (cons 41 0)
           (cons 42 0)
           (cons 91 0)
           (list 10 5.842 0.790448)
           (cons 40 0)
           (cons 41 0)
           (cons 42 0)
           (cons 91 0)
           (list 10 5.98424 0.8382)
           (cons 40 0)
           (cons 41 0)
           (cons 42 0)
           (cons 91 0)
           (list 10 6.71576 0.8382)
           (cons 40 0)
           (cons 41 0)
           (cons 42 0)
           (cons 91 0)
           (list 10 6.858 0.790448)
           (cons 40 0)
           (cons 41 0)
           (cons 42 0)
           (cons 91 0)
           (list 10 6.858 0.631952)
           (cons 40 0)
           (cons 41 0)
           (cons 42 0)
           (cons 91 0)
           (list 10 6.71576 0.5842)
           (cons 40 0)
           (cons 41 0)
           (cons 42 0)
           (cons 91 0)
           (list 10 5.98424 0.5842)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.842 1.089152)
           (cons 40 0)
           (cons 41 0)
           (cons 42 0)
           (cons 91 0)
           (list 10 5.842 1.247648)
           (cons 40 0)
           (cons 41 0)
           (cons 42 0)
           (cons 91 0)
           (list 10 5.98424 1.2954)
           (cons 40 0)
           (cons 41 0)
           (cons 42 0)
           (cons 91 0)
           (list 10 6.71576 1.2954)
           (cons 40 0)
           (cons 41 0)
           (cons 42 0)
           (cons 91 0)
           (list 10 6.858 1.247648)
           (cons 40 0)
           (cons 41 0)
           (cons 42 0)
           (cons 91 0)
           (list 10 6.858 1.089152)
           (cons 40 0)
           (cons 41 0)
           (cons 42 0)
           (cons 91 0)
           (list 10 6.71576 1.0414)
           (cons 40 0)
           (cons 41 0)
           (cons 42 0)
           (cons 91 0)
           (list 10 5.98424 1.0414)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.112 -0.790448)
           (cons 40 0)
           (cons 41 0)
           (cons 42 0)
           (cons 91 0)
           (list 10 7.112 -0.631952)
           (cons 40 0)
           (cons 41 0)
           (cons 42 0)
           (cons 91 0)
           (list 10 7.25424 -0.5842)
           (cons 40 0)
           (cons 41 0)
           (cons 42 0)
           (cons 91 0)
           (list 10 7.98576 -0.5842)
           (cons 40 0)
           (cons 41 0)
           (cons 42 0)
           (cons 91 0)
           (list 10 8.128 -0.631952)
           (cons 40 0)
           (cons 41 0)
           (cons 42 0)
           (cons 91 0)
           (list 10 8.128 -0.790448)
           (cons 40 0)
           (cons 41 0)
           (cons 42 0)
           (cons 91 0)
           (list 10 7.98576 -0.8382)
           (cons 40 0)
           (cons 41 0)
           (cons 42 0)
           (cons 91 0)
           (list 10 7.25424 -0.8382)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.112 -1.247648)
           (cons 40 0)
           (cons 41 0)
           (cons 42 0)
           (cons 91 0)
           (list 10 7.112 -1.089152)
           (cons 40 0)
           (cons 41 0)
           (cons 42 0)
           (cons 91 0)
           (list 10 7.25424 -1.0414)
           (cons 40 0)
           (cons 41 0)
           (cons 42 0)
           (cons 91 0)
           (list 10 7.98576 -1.0414)
           (cons 40 0)
           (cons 41 0)
           (cons 42 0)
           (cons 91 0)
           (list 10 8.128 -1.089152)
           (cons 40 0)
           (cons 41 0)
           (cons 42 0)
           (cons 91 0)
           (list 10 8.128 -1.247648)
           (cons 40 0)
           (cons 41 0)
           (cons 42 0)
           (cons 91 0)
           (list 10 7.98576 -1.2954)
           (cons 40 0)
           (cons 41 0)
           (cons 42 0)
           (cons 91 0)
           (list 10 7.25424 -1.2954)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.112 0.631952)
           (cons 40 0)
           (cons 41 0)
           (cons 42 0)
           (cons 91 0)
           (list 10 7.112 0.790448)
           (cons 40 0)
           (cons 41 0)
           (cons 42 0)
           (cons 91 0)
           (list 10 7.25424 0.8382)
           (cons 40 0)
           (cons 41 0)
           (cons 42 0)
           (cons 91 0)
           (list 10 7.98576 0.8382)
           (cons 40 0)
           (cons 41 0)
           (cons 42 0)
           (cons 91 0)
           (list 10 8.128 0.790448)
           (cons 40 0)
           (cons 41 0)
           (cons 42 0)
           (cons 91 0)
           (list 10 8.128 0.631952)
           (cons 40 0)
           (cons 41 0)
           (cons 42 0)
           (cons 91 0)
           (list 10 7.98576 0.5842)
           (cons 40 0)
           (cons 41 0)
           (cons 42 0)
           (cons 91 0)
           (list 10 7.25424 0.5842)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.112 1.089152)
           (cons 40 0)
           (cons 41 0)
           (cons 42 0)
           (cons 91 0)
           (list 10 7.112 1.247648)
           (cons 40 0)
           (cons 41 0)
           (cons 42 0)
           (cons 91 0)
           (list 10 7.25424 1.2954)
           (cons 40 0)
           (cons 41 0)
           (cons 42 0)
           (cons 91 0)
           (list 10 7.98576 1.2954)
           (cons 40 0)
           (cons 41 0)
           (cons 42 0)
           (cons 91 0)
           (list 10 8.128 1.247648)
           (cons 40 0)
           (cons 41 0)
           (cons 42 0)
           (cons 91 0)
           (list 10 8.128 1.089152)
           (cons 40 0)
           (cons 41 0)
           (cons 42 0)
           (cons 91 0)
           (list 10 7.98576 1.0414)
           (cons 40 0)
           (cons 41 0)
           (cons 42 0)
           (cons 91 0)
           (list 10 7.25424 1.0414)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.382 -0.790448)
           (cons 40 0)
           (cons 41 0)
           (cons 42 0)
           (cons 91 0)
           (list 10 8.382 -0.631952)
           (cons 40 0)
           (cons 41 0)
           (cons 42 0)
           (cons 91 0)
           (list 10 8.52424 -0.5842)
           (cons 40 0)
           (cons 41 0)
           (cons 42 0)
           (cons 91 0)
           (list 10 9.25576 -0.5842)
           (cons 40 0)
           (cons 41 0)
           (cons 42 0)
           (cons 91 0)
           (list 10 9.398 -0.631952)
           (cons 40 0)
           (cons 41 0)
           (cons 42 0)
           (cons 91 0)
           (list 10 9.398 -0.790448)
           (cons 40 0)
           (cons 41 0)
           (cons 42 0)
           (cons 91 0)
           (list 10 9.25576 -0.8382)
           (cons 40 0)
           (cons 41 0)
           (cons 42 0)
           (cons 91 0)
           (list 10 8.52424 -0.8382)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.382 -1.247648)
           (cons 40 0)
           (cons 41 0)
           (cons 42 0)
           (cons 91 0)
           (list 10 8.382 -1.089152)
           (cons 40 0)
           (cons 41 0)
           (cons 42 0)
           (cons 91 0)
           (list 10 8.52424 -1.0414)
           (cons 40 0)
           (cons 41 0)
           (cons 42 0)
           (cons 91 0)
           (list 10 9.25576 -1.0414)
           (cons 40 0)
           (cons 41 0)
           (cons 42 0)
           (cons 91 0)
           (list 10 9.398 -1.089152)
           (cons 40 0)
           (cons 41 0)
           (cons 42 0)
           (cons 91 0)
           (list 10 9.398 -1.247648)
           (cons 40 0)
           (cons 41 0)
           (cons 42 0)
           (cons 91 0)
           (list 10 9.25576 -1.2954)
           (cons 40 0)
           (cons 41 0)
           (cons 42 0)
           (cons 91 0)
           (list 10 8.52424 -1.2954)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.382 0.631952)
           (cons 40 0)
           (cons 41 0)
           (cons 42 0)
           (cons 91 0)
           (list 10 8.382 0.790448)
           (cons 40 0)
           (cons 41 0)
           (cons 42 0)
           (cons 91 0)
           (list 10 8.52424 0.8382)
           (cons 40 0)
           (cons 41 0)
           (cons 42 0)
           (cons 91 0)
           (list 10 9.25576 0.8382)
           (cons 40 0)
           (cons 41 0)
           (cons 42 0)
           (cons 91 0)
           (list 10 9.398 0.790448)
           (cons 40 0)
           (cons 41 0)
           (cons 42 0)
           (cons 91 0)
           (list 10 9.398 0.631952)
           (cons 40 0)
           (cons 41 0)
           (cons 42 0)
           (cons 91 0)
           (list 10 9.25576 0.5842)
           (cons 40 0)
           (cons 41 0)
           (cons 42 0)
           (cons 91 0)
           (list 10 8.52424 0.5842)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.382 1.089152)
           (cons 40 0)
           (cons 41 0)
           (cons 42 0)
           (cons 91 0)
           (list 10 8.382 1.247648)
           (cons 40 0)
           (cons 41 0)
           (cons 42 0)
           (cons 91 0)
           (list 10 8.52424 1.2954)
           (cons 40 0)
           (cons 41 0)
           (cons 42 0)
           (cons 91 0)
           (list 10 9.25576 1.2954)
           (cons 40 0)
           (cons 41 0)
           (cons 42 0)
           (cons 91 0)
           (list 10 9.398 1.247648)
           (cons 40 0)
           (cons 41 0)
           (cons 42 0)
           (cons 91 0)
           (list 10 9.398 1.089152)
           (cons 40 0)
           (cons 41 0)
           (cons 42 0)
           (cons 91 0)
           (list 10 9.25576 1.0414)
           (cons 40 0)
           (cons 41 0)
           (cons 42 0)
           (cons 91 0)
           (list 10 8.52424 1.0414)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0.9144 1.2954 0)
           (cons 50 0)
          )
         )
         (entmake
          (list
           (cons 0 "POINT")
           (cons 100 "AcDbEntity")
           (cons 67 0)
           (cons 8 "0")
           (cons 100 "AcDbPoint")
           (list 10 0.9144 -1.2954 0)
           (cons 50 0)
          )
         )
         (entmake
          (list
           (cons 0 "POINT")
           (cons 100 "AcDbEntity")
           (cons 67 0)
           (cons 8 "0")
           (cons 100 "AcDbPoint")
           (list 10 0 1.524 0)
           (cons 50 0)
          )
         )
         (entmake
          (list
           (cons 0 "POINT")
           (cons 100 "AcDbEntity")
           (cons 67 0)
           (cons 8 "0")
           (cons 100 "AcDbPoint")
           (list 10 0 -1.524 0)
           (cons 50 0)
          )
         )
         (entmake
          (list
           (cons 0 "POINT")
           (cons 100 "AcDbEntity")
           (cons 67 0)
           (cons 8 "0")
           (cons 100 "AcDbPoint")
           (list 10 7.62 -1.2954 0)
           (cons 50 0)
          )
         )
         (entmake
          (list
           (cons 0 "POINT")
           (cons 100 "AcDbEntity")
           (cons 67 0)
           (cons 8 "0")
           (cons 100 "AcDbPoint")
           (list 10 7.62 1.2954 0)
           (cons 50 0)
          )
         )
         (entmake
          (list
           (cons 0 "POINT")
           (cons 100 "AcDbEntity")
           (cons 67 0)
           (cons 8 "0")
           (cons 62 1)
           (cons 100 "AcDbPoint")
           (list 10 7.62 0 0)
           (cons 50 0)
          )
         )
         (entmake
          (list
           (cons 0 "POINT")
           (cons 100 "AcDbEntity")
           (cons 67 0)
           (cons 8 "0")
           (cons 62 3)
           (cons 100 "AcDbPoint")
           (list 10 0.9144 0 0)
           (cons 50 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "0.91")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "0.91")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "7.62")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "7.62")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "40.0")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "TEXT")
           (cons 100 "AcDbEntity")
           (cons 67 0)
           (cons 8 "0")
           (cons 100 "AcDbText")
           (list 10 1.85487619 -0.25 0)
           (cons 40 0.5)
           (cons 1 "1")
           (cons 50 0)
           (cons 41 1)
           (cons 51 0)
           (cons 7 "Standard")
           (cons 71 0)
           (cons 72 4)
           (list 11 1.9144 0 0)
           (cons 100 "AcDbText")
           (cons 73 0)
          )
         )
         (entmake
          (list
           (cons 0 "LWPOLYLINE")
           (cons 100 "AcDbEntity")
           (cons 67 0)
           (cons 8 "Defpoints")
           (cons 100 "AcDbPolyline")
           (cons 90 4)
           (cons 70 129)
           (cons 43 0)
           (cons 38 0)
           (cons 39 0)
           (list 10 0 1.524)
           (cons 40 0)
           (cons 41 0)
           (cons 42 0)
           (cons 91 0)
           (list 10 8.89 1.524)
           (cons 40 0)
           (cons 41 0)
           (cons 42 0)
           (cons 91 0)
           (list 10 8.89 -1.524)
           (cons 40 0)
           (cons 41 0)
           (cons 42 0)
           (cons 91 0)
           (list 10 0 -1.524)
           (cons 40 0)
           (cons 41 0)
           (cons 42 0)
           (cons 91 0)
          )
         )
         (entmake
          (list
           (cons 0 "INSERT")
           (cons 100 "AcDbEntity")
           (cons 67 0)
           (cons 8 "0")
           (cons 100 "AcDbBlockReference")
           (cons 2 "WheelRightM2")
           (list 10 0.9144 1.0414 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM2")
           (list 10 0.9144 -1.0414 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "TAC-1999-WB-20-TRAILER"))
        (progn
         (entmake)
         (entmake
          (list
           (cons 0 "BLOCK")
           (cons 2 "TAC-1999-WB-20-TRAILER")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 17 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 17 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 1.3 0 0)
           (cons 40 0.104)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.5062 -0.7445528)
           (cons 40 0)
           (cons 41 0)
           (cons 42 0)
           (cons 91 0)
           (list 10 12.5062 -0.5702072)
           (cons 40 0)
           (cons 41 0)
           (cons 42 0)
           (cons 91 0)
           (list 10 12.662664 -0.51768)
           (cons 40 0)
           (cons 41 0)
           (cons 42 0)
           (cons 91 0)
           (list 10 13.467336 -0.51768)
           (cons 40 0)
           (cons 41 0)
           (cons 42 0)
           (cons 91 0)
           (list 10 13.6238 -0.5702072)
           (cons 40 0)
           (cons 41 0)
           (cons 42 0)
           (cons 91 0)
           (list 10 13.6238 -0.7445528)
           (cons 40 0)
           (cons 41 0)
           (cons 42 0)
           (cons 91 0)
           (list 10 13.467336 -0.79708)
           (cons 40 0)
           (cons 41 0)
           (cons 42 0)
           (cons 91 0)
           (list 10 12.662664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.5062 -1.2474728)
           (cons 40 0)
           (cons 41 0)
           (cons 42 0)
           (cons 91 0)
           (list 10 12.5062 -1.0731272)
           (cons 40 0)
           (cons 41 0)
           (cons 42 0)
           (cons 91 0)
           (list 10 12.662664 -1.0206)
           (cons 40 0)
           (cons 41 0)
           (cons 42 0)
           (cons 91 0)
           (list 10 13.467336 -1.0206)
           (cons 40 0)
           (cons 41 0)
           (cons 42 0)
           (cons 91 0)
           (list 10 13.6238 -1.0731272)
           (cons 40 0)
           (cons 41 0)
           (cons 42 0)
           (cons 91 0)
           (list 10 13.6238 -1.2474728)
           (cons 40 0)
           (cons 41 0)
           (cons 42 0)
           (cons 91 0)
           (list 10 13.467336 -1.3)
           (cons 40 0)
           (cons 41 0)
           (cons 42 0)
           (cons 91 0)
           (list 10 12.662664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.5062 0.5702072)
           (cons 40 0)
           (cons 41 0)
           (cons 42 0)
           (cons 91 0)
           (list 10 12.5062 0.7445528)
           (cons 40 0)
           (cons 41 0)
           (cons 42 0)
           (cons 91 0)
           (list 10 12.662664 0.79708)
           (cons 40 0)
           (cons 41 0)
           (cons 42 0)
           (cons 91 0)
           (list 10 13.467336 0.79708)
           (cons 40 0)
           (cons 41 0)
           (cons 42 0)
           (cons 91 0)
           (list 10 13.6238 0.7445528)
           (cons 40 0)
           (cons 41 0)
           (cons 42 0)
           (cons 91 0)
           (list 10 13.6238 0.5702072)
           (cons 40 0)
           (cons 41 0)
           (cons 42 0)
           (cons 91 0)
           (list 10 13.467336 0.51768)
           (cons 40 0)
           (cons 41 0)
           (cons 42 0)
           (cons 91 0)
           (list 10 12.662664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.5062 1.0731272)
           (cons 40 0)
           (cons 41 0)
           (cons 42 0)
           (cons 91 0)
           (list 10 12.5062 1.2474728)
           (cons 40 0)
           (cons 41 0)
           (cons 42 0)
           (cons 91 0)
           (list 10 12.662664 1.3)
           (cons 40 0)
           (cons 41 0)
           (cons 42 0)
           (cons 91 0)
           (list 10 13.467336 1.3)
           (cons 40 0)
           (cons 41 0)
           (cons 42 0)
           (cons 91 0)
           (list 10 13.6238 1.2474728)
           (cons 40 0)
           (cons 41 0)
           (cons 42 0)
           (cons 91 0)
           (list 10 13.6238 1.0731272)
           (cons 40 0)
           (cons 41 0)
           (cons 42 0)
           (cons 91 0)
           (list 10 13.467336 1.0206)
           (cons 40 0)
           (cons 41 0)
           (cons 42 0)
           (cons 91 0)
           (list 10 12.662664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.7762 -0.7445528)
           (cons 40 0)
           (cons 41 0)
           (cons 42 0)
           (cons 91 0)
           (list 10 13.7762 -0.5702072)
           (cons 40 0)
           (cons 41 0)
           (cons 42 0)
           (cons 91 0)
           (list 10 13.932664 -0.51768)
           (cons 40 0)
           (cons 41 0)
           (cons 42 0)
           (cons 91 0)
           (list 10 14.737336 -0.51768)
           (cons 40 0)
           (cons 41 0)
           (cons 42 0)
           (cons 91 0)
           (list 10 14.8938 -0.5702072)
           (cons 40 0)
           (cons 41 0)
           (cons 42 0)
           (cons 91 0)
           (list 10 14.8938 -0.7445528)
           (cons 40 0)
           (cons 41 0)
           (cons 42 0)
           (cons 91 0)
           (list 10 14.737336 -0.79708)
           (cons 40 0)
           (cons 41 0)
           (cons 42 0)
           (cons 91 0)
           (list 10 13.932664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.7762 -1.2474728)
           (cons 40 0)
           (cons 41 0)
           (cons 42 0)
           (cons 91 0)
           (list 10 13.7762 -1.0731272)
           (cons 40 0)
           (cons 41 0)
           (cons 42 0)
           (cons 91 0)
           (list 10 13.932664 -1.0206)
           (cons 40 0)
           (cons 41 0)
           (cons 42 0)
           (cons 91 0)
           (list 10 14.737336 -1.0206)
           (cons 40 0)
           (cons 41 0)
           (cons 42 0)
           (cons 91 0)
           (list 10 14.8938 -1.0731272)
           (cons 40 0)
           (cons 41 0)
           (cons 42 0)
           (cons 91 0)
           (list 10 14.8938 -1.2474728)
           (cons 40 0)
           (cons 41 0)
           (cons 42 0)
           (cons 91 0)
           (list 10 14.737336 -1.3)
           (cons 40 0)
           (cons 41 0)
           (cons 42 0)
           (cons 91 0)
           (list 10 13.932664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.7762 0.5702072)
           (cons 40 0)
           (cons 41 0)
           (cons 42 0)
           (cons 91 0)
           (list 10 13.7762 0.7445528)
           (cons 40 0)
           (cons 41 0)
           (cons 42 0)
           (cons 91 0)
           (list 10 13.932664 0.79708)
           (cons 40 0)
           (cons 41 0)
           (cons 42 0)
           (cons 91 0)
           (list 10 14.737336 0.79708)
           (cons 40 0)
           (cons 41 0)
           (cons 42 0)
           (cons 91 0)
           (list 10 14.8938 0.7445528)
           (cons 40 0)
           (cons 41 0)
           (cons 42 0)
           (cons 91 0)
           (list 10 14.8938 0.5702072)
           (cons 40 0)
           (cons 41 0)
           (cons 42 0)
           (cons 91 0)
           (list 10 14.737336 0.51768)
           (cons 40 0)
           (cons 41 0)
           (cons 42 0)
           (cons 91 0)
           (list 10 13.932664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.7762 1.0731272)
           (cons 40 0)
           (cons 41 0)
           (cons 42 0)
           (cons 91 0)
           (list 10 13.7762 1.2474728)
           (cons 40 0)
           (cons 41 0)
           (cons 42 0)
           (cons 91 0)
           (list 10 13.932664 1.3)
           (cons 40 0)
           (cons 41 0)
           (cons 42 0)
           (cons 91 0)
           (list 10 14.737336 1.3)
           (cons 40 0)
           (cons 41 0)
           (cons 42 0)
           (cons 91 0)
           (list 10 14.8938 1.2474728)
           (cons 40 0)
           (cons 41 0)
           (cons 42 0)
           (cons 91 0)
           (list 10 14.8938 1.0731272)
           (cons 40 0)
           (cons 41 0)
           (cons 42 0)
           (cons 91 0)
           (list 10 14.737336 1.0206)
           (cons 40 0)
           (cons 41 0)
           (cons 42 0)
           (cons 91 0)
           (list 10 13.932664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 1.3 0 0)
           (cons 50 0)
          )
         )
         (entmake
          (list
           (cons 0 "POINT")
           (cons 100 "AcDbEntity")
           (cons 67 0)
           (cons 8 "0")
           (cons 100 "AcDbPoint")
           (list 10 13.7 -1.3 0)
           (cons 50 0)
          )
         )
         (entmake
          (list
           (cons 0 "POINT")
           (cons 100 "AcDbEntity")
           (cons 67 0)
           (cons 8 "0")
           (cons 100 "AcDbPoint")
           (list 10 13.7 1.3 0)
           (cons 50 0)
          )
         )
         (entmake
          (list
           (cons 0 "POINT")
           (cons 100 "AcDbEntity")
           (cons 67 0)
           (cons 8 "0")
           (cons 100 "AcDbPoint")
           (list 10 17 1.3 0)
           (cons 50 0)
          )
         )
         (entmake
          (list
           (cons 0 "POINT")
           (cons 100 "AcDbEntity")
           (cons 67 0)
           (cons 8 "0")
           (cons 100 "AcDbPoint")
           (list 10 17 -1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 17 -1.3)
           (cons 40 0)
           (cons 41 0)
           (cons 42 0)
           (cons 91 0)
           (list 10 17 1.3)
           (cons 40 0)
           (cons 41 0)
           (cons 42 0)
           (cons 91 0)
           (list 10 0 1.3)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.6 0.56666667 0)
           (cons 40 0.2)
           (cons 1 "1.30")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 0.23333333 0)
           (cons 40 0.2)
           (cons 1 "1.30")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.1 0)
           (cons 40 0.2)
           (cons 1 "13.70")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.43333333 0)
           (cons 40 0.2)
           (cons 1 "0.00")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "TAC-1999-WB-20-TRUCK"))
        (progn
         (entmake)
         (entmake
          (list
           (cons 0 "BLOCK")
           (cons 2 "TAC-1999-WB-20-TRUCK")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.635 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.635 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 7 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 7.26263966 -0.26263966 0)
           (list 11 7.26263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.8062 -0.7445528)
           (cons 40 0)
           (cons 41 0)
           (cons 42 0)
           (cons 91 0)
           (list 10 5.8062 -0.5702072)
           (cons 40 0)
           (cons 41 0)
           (cons 42 0)
           (cons 91 0)
           (list 10 5.962664 -0.51768)
           (cons 40 0)
           (cons 41 0)
           (cons 42 0)
           (cons 91 0)
           (list 10 6.767336 -0.51768)
           (cons 40 0)
           (cons 41 0)
           (cons 42 0)
           (cons 91 0)
           (list 10 6.9238 -0.5702072)
           (cons 40 0)
           (cons 41 0)
           (cons 42 0)
           (cons 91 0)
           (list 10 6.9238 -0.7445528)
           (cons 40 0)
           (cons 41 0)
           (cons 42 0)
           (cons 91 0)
           (list 10 6.767336 -0.79708)
           (cons 40 0)
           (cons 41 0)
           (cons 42 0)
           (cons 91 0)
           (list 10 5.962664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.8062 -1.2474728)
           (cons 40 0)
           (cons 41 0)
           (cons 42 0)
           (cons 91 0)
           (list 10 5.8062 -1.0731272)
           (cons 40 0)
           (cons 41 0)
           (cons 42 0)
           (cons 91 0)
           (list 10 5.962664 -1.0206)
           (cons 40 0)
           (cons 41 0)
           (cons 42 0)
           (cons 91 0)
           (list 10 6.767336 -1.0206)
           (cons 40 0)
           (cons 41 0)
           (cons 42 0)
           (cons 91 0)
           (list 10 6.9238 -1.0731272)
           (cons 40 0)
           (cons 41 0)
           (cons 42 0)
           (cons 91 0)
           (list 10 6.9238 -1.2474728)
           (cons 40 0)
           (cons 41 0)
           (cons 42 0)
           (cons 91 0)
           (list 10 6.767336 -1.3)
           (cons 40 0)
           (cons 41 0)
           (cons 42 0)
           (cons 91 0)
           (list 10 5.962664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.8062 0.5702072)
           (cons 40 0)
           (cons 41 0)
           (cons 42 0)
           (cons 91 0)
           (list 10 5.8062 0.7445528)
           (cons 40 0)
           (cons 41 0)
           (cons 42 0)
           (cons 91 0)
           (list 10 5.962664 0.79708)
           (cons 40 0)
           (cons 41 0)
           (cons 42 0)
           (cons 91 0)
           (list 10 6.767336 0.79708)
           (cons 40 0)
           (cons 41 0)
           (cons 42 0)
           (cons 91 0)
           (list 10 6.9238 0.7445528)
           (cons 40 0)
           (cons 41 0)
           (cons 42 0)
           (cons 91 0)
           (list 10 6.9238 0.5702072)
           (cons 40 0)
           (cons 41 0)
           (cons 42 0)
           (cons 91 0)
           (list 10 6.767336 0.51768)
           (cons 40 0)
           (cons 41 0)
           (cons 42 0)
           (cons 91 0)
           (list 10 5.962664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.8062 1.0731272)
           (cons 40 0)
           (cons 41 0)
           (cons 42 0)
           (cons 91 0)
           (list 10 5.8062 1.2474728)
           (cons 40 0)
           (cons 41 0)
           (cons 42 0)
           (cons 91 0)
           (list 10 5.962664 1.3)
           (cons 40 0)
           (cons 41 0)
           (cons 42 0)
           (cons 91 0)
           (list 10 6.767336 1.3)
           (cons 40 0)
           (cons 41 0)
           (cons 42 0)
           (cons 91 0)
           (list 10 6.9238 1.2474728)
           (cons 40 0)
           (cons 41 0)
           (cons 42 0)
           (cons 91 0)
           (list 10 6.9238 1.0731272)
           (cons 40 0)
           (cons 41 0)
           (cons 42 0)
           (cons 91 0)
           (list 10 6.767336 1.0206)
           (cons 40 0)
           (cons 41 0)
           (cons 42 0)
           (cons 91 0)
           (list 10 5.962664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.0762 -0.7445528)
           (cons 40 0)
           (cons 41 0)
           (cons 42 0)
           (cons 91 0)
           (list 10 7.0762 -0.5702072)
           (cons 40 0)
           (cons 41 0)
           (cons 42 0)
           (cons 91 0)
           (list 10 7.232664 -0.51768)
           (cons 40 0)
           (cons 41 0)
           (cons 42 0)
           (cons 91 0)
           (list 10 8.037336 -0.51768)
           (cons 40 0)
           (cons 41 0)
           (cons 42 0)
           (cons 91 0)
           (list 10 8.1938 -0.5702072)
           (cons 40 0)
           (cons 41 0)
           (cons 42 0)
           (cons 91 0)
           (list 10 8.1938 -0.7445528)
           (cons 40 0)
           (cons 41 0)
           (cons 42 0)
           (cons 91 0)
           (list 10 8.037336 -0.79708)
           (cons 40 0)
           (cons 41 0)
           (cons 42 0)
           (cons 91 0)
           (list 10 7.232664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.0762 -1.2474728)
           (cons 40 0)
           (cons 41 0)
           (cons 42 0)
           (cons 91 0)
           (list 10 7.0762 -1.0731272)
           (cons 40 0)
           (cons 41 0)
           (cons 42 0)
           (cons 91 0)
           (list 10 7.232664 -1.0206)
           (cons 40 0)
           (cons 41 0)
           (cons 42 0)
           (cons 91 0)
           (list 10 8.037336 -1.0206)
           (cons 40 0)
           (cons 41 0)
           (cons 42 0)
           (cons 91 0)
           (list 10 8.1938 -1.0731272)
           (cons 40 0)
           (cons 41 0)
           (cons 42 0)
           (cons 91 0)
           (list 10 8.1938 -1.2474728)
           (cons 40 0)
           (cons 41 0)
           (cons 42 0)
           (cons 91 0)
           (list 10 8.037336 -1.3)
           (cons 40 0)
           (cons 41 0)
           (cons 42 0)
           (cons 91 0)
           (list 10 7.232664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.0762 0.5702072)
           (cons 40 0)
           (cons 41 0)
           (cons 42 0)
           (cons 91 0)
           (list 10 7.0762 0.7445528)
           (cons 40 0)
           (cons 41 0)
           (cons 42 0)
           (cons 91 0)
           (list 10 7.232664 0.79708)
           (cons 40 0)
           (cons 41 0)
           (cons 42 0)
           (cons 91 0)
           (list 10 8.037336 0.79708)
           (cons 40 0)
           (cons 41 0)
           (cons 42 0)
           (cons 91 0)
           (list 10 8.1938 0.7445528)
           (cons 40 0)
           (cons 41 0)
           (cons 42 0)
           (cons 91 0)
           (list 10 8.1938 0.5702072)
           (cons 40 0)
           (cons 41 0)
           (cons 42 0)
           (cons 91 0)
           (list 10 8.037336 0.51768)
           (cons 40 0)
           (cons 41 0)
           (cons 42 0)
           (cons 91 0)
           (list 10 7.232664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.0762 1.0731272)
           (cons 40 0)
           (cons 41 0)
           (cons 42 0)
           (cons 91 0)
           (list 10 7.0762 1.2474728)
           (cons 40 0)
           (cons 41 0)
           (cons 42 0)
           (cons 91 0)
           (list 10 7.232664 1.3)
           (cons 40 0)
           (cons 41 0)
           (cons 42 0)
           (cons 91 0)
           (list 10 8.037336 1.3)
           (cons 40 0)
           (cons 41 0)
           (cons 42 0)
           (cons 91 0)
           (list 10 8.1938 1.2474728)
           (cons 40 0)
           (cons 41 0)
           (cons 42 0)
           (cons 91 0)
           (list 10 8.1938 1.0731272)
           (cons 40 0)
           (cons 41 0)
           (cons 42 0)
           (cons 91 0)
           (list 10 8.037336 1.0206)
           (cons 40 0)
           (cons 41 0)
           (cons 42 0)
           (cons 91 0)
           (list 10 7.232664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0.8 0 0)
           (cons 50 0)
          )
         )
         (entmake
          (list
           (cons 0 "POINT")
           (cons 100 "AcDbEntity")
           (cons 67 0)
           (cons 8 "0")
           (cons 100 "AcDbPoint")
           (list 10 7 -1.3 0)
           (cons 50 0)
          )
         )
         (entmake
          (list
           (cons 0 "POINT")
           (cons 100 "AcDbEntity")
           (cons 67 0)
           (cons 8 "0")
           (cons 100 "AcDbPoint")
           (list 10 7 1.3 0)
           (cons 50 0)
          )
         )
         (entmake
          (list
           (cons 0 "POINT")
           (cons 100 "AcDbEntity")
           (cons 67 0)
           (cons 8 "0")
           (cons 100 "AcDbPoint")
           (list 10 7 0 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0.8 -1.3 0)
           (cons 50 0)
          )
         )
         (entmake
          (list
           (cons 0 "POINT")
           (cons 100 "AcDbEntity")
           (cons 67 0)
           (cons 8 "0")
           (cons 100 "AcDbPoint")
           (list 10 0.8 1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 7.635 -1.3)
           (cons 40 0)
           (cons 41 0)
           (cons 42 0)
           (cons 91 0)
           (list 10 7.635 1.3)
           (cons 40 0)
           (cons 41 0)
           (cons 42 0)
           (cons 91 0)
           (list 10 0 1.3)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.1 0.56666667 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 0.23333333 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.1 0)
           (cons 40 0.2)
           (cons 1 "7.00")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.43333333 0)
           (cons 40 0.2)
           (cons 1 "7.00")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.76666667 0)
           (cons 40 0.2)
           (cons 1 "28.3")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelLeftM1")
           (list 10 0.8 -1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM1")
           (list 10 0.8 1.0206 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "TAC-1999-WB-19-TRAILER"))
        (progn
         (entmake)
         (entmake
          (list
           (cons 0 "BLOCK")
           (cons 2 "TAC-1999-WB-19-TRAILER")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 15 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 1.3 0 0)
           (cons 40 0.104)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.1062 -0.7445528)
           (cons 40 0)
           (cons 41 0)
           (cons 42 0)
           (cons 91 0)
           (list 10 12.1062 -0.5702072)
           (cons 40 0)
           (cons 41 0)
           (cons 42 0)
           (cons 91 0)
           (list 10 12.262664 -0.51768)
           (cons 40 0)
           (cons 41 0)
           (cons 42 0)
           (cons 91 0)
           (list 10 13.067336 -0.51768)
           (cons 40 0)
           (cons 41 0)
           (cons 42 0)
           (cons 91 0)
           (list 10 13.2238 -0.5702072)
           (cons 40 0)
           (cons 41 0)
           (cons 42 0)
           (cons 91 0)
           (list 10 13.2238 -0.7445528)
           (cons 40 0)
           (cons 41 0)
           (cons 42 0)
           (cons 91 0)
           (list 10 13.067336 -0.79708)
           (cons 40 0)
           (cons 41 0)
           (cons 42 0)
           (cons 91 0)
           (list 10 12.262664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.1062 -1.2474728)
           (cons 40 0)
           (cons 41 0)
           (cons 42 0)
           (cons 91 0)
           (list 10 12.1062 -1.0731272)
           (cons 40 0)
           (cons 41 0)
           (cons 42 0)
           (cons 91 0)
           (list 10 12.262664 -1.0206)
           (cons 40 0)
           (cons 41 0)
           (cons 42 0)
           (cons 91 0)
           (list 10 13.067336 -1.0206)
           (cons 40 0)
           (cons 41 0)
           (cons 42 0)
           (cons 91 0)
           (list 10 13.2238 -1.0731272)
           (cons 40 0)
           (cons 41 0)
           (cons 42 0)
           (cons 91 0)
           (list 10 13.2238 -1.2474728)
           (cons 40 0)
           (cons 41 0)
           (cons 42 0)
           (cons 91 0)
           (list 10 13.067336 -1.3)
           (cons 40 0)
           (cons 41 0)
           (cons 42 0)
           (cons 91 0)
           (list 10 12.262664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.1062 0.5702072)
           (cons 40 0)
           (cons 41 0)
           (cons 42 0)
           (cons 91 0)
           (list 10 12.1062 0.7445528)
           (cons 40 0)
           (cons 41 0)
           (cons 42 0)
           (cons 91 0)
           (list 10 12.262664 0.79708)
           (cons 40 0)
           (cons 41 0)
           (cons 42 0)
           (cons 91 0)
           (list 10 13.067336 0.79708)
           (cons 40 0)
           (cons 41 0)
           (cons 42 0)
           (cons 91 0)
           (list 10 13.2238 0.7445528)
           (cons 40 0)
           (cons 41 0)
           (cons 42 0)
           (cons 91 0)
           (list 10 13.2238 0.5702072)
           (cons 40 0)
           (cons 41 0)
           (cons 42 0)
           (cons 91 0)
           (list 10 13.067336 0.51768)
           (cons 40 0)
           (cons 41 0)
           (cons 42 0)
           (cons 91 0)
           (list 10 12.262664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 12.1062 1.0731272)
           (cons 40 0)
           (cons 41 0)
           (cons 42 0)
           (cons 91 0)
           (list 10 12.1062 1.2474728)
           (cons 40 0)
           (cons 41 0)
           (cons 42 0)
           (cons 91 0)
           (list 10 12.262664 1.3)
           (cons 40 0)
           (cons 41 0)
           (cons 42 0)
           (cons 91 0)
           (list 10 13.067336 1.3)
           (cons 40 0)
           (cons 41 0)
           (cons 42 0)
           (cons 91 0)
           (list 10 13.2238 1.2474728)
           (cons 40 0)
           (cons 41 0)
           (cons 42 0)
           (cons 91 0)
           (list 10 13.2238 1.0731272)
           (cons 40 0)
           (cons 41 0)
           (cons 42 0)
           (cons 91 0)
           (list 10 13.067336 1.0206)
           (cons 40 0)
           (cons 41 0)
           (cons 42 0)
           (cons 91 0)
           (list 10 12.262664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.3762 -0.7445528)
           (cons 40 0)
           (cons 41 0)
           (cons 42 0)
           (cons 91 0)
           (list 10 13.3762 -0.5702072)
           (cons 40 0)
           (cons 41 0)
           (cons 42 0)
           (cons 91 0)
           (list 10 13.532664 -0.51768)
           (cons 40 0)
           (cons 41 0)
           (cons 42 0)
           (cons 91 0)
           (list 10 14.337336 -0.51768)
           (cons 40 0)
           (cons 41 0)
           (cons 42 0)
           (cons 91 0)
           (list 10 14.4938 -0.5702072)
           (cons 40 0)
           (cons 41 0)
           (cons 42 0)
           (cons 91 0)
           (list 10 14.4938 -0.7445528)
           (cons 40 0)
           (cons 41 0)
           (cons 42 0)
           (cons 91 0)
           (list 10 14.337336 -0.79708)
           (cons 40 0)
           (cons 41 0)
           (cons 42 0)
           (cons 91 0)
           (list 10 13.532664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.3762 -1.2474728)
           (cons 40 0)
           (cons 41 0)
           (cons 42 0)
           (cons 91 0)
           (list 10 13.3762 -1.0731272)
           (cons 40 0)
           (cons 41 0)
           (cons 42 0)
           (cons 91 0)
           (list 10 13.532664 -1.0206)
           (cons 40 0)
           (cons 41 0)
           (cons 42 0)
           (cons 91 0)
           (list 10 14.337336 -1.0206)
           (cons 40 0)
           (cons 41 0)
           (cons 42 0)
           (cons 91 0)
           (list 10 14.4938 -1.0731272)
           (cons 40 0)
           (cons 41 0)
           (cons 42 0)
           (cons 91 0)
           (list 10 14.4938 -1.2474728)
           (cons 40 0)
           (cons 41 0)
           (cons 42 0)
           (cons 91 0)
           (list 10 14.337336 -1.3)
           (cons 40 0)
           (cons 41 0)
           (cons 42 0)
           (cons 91 0)
           (list 10 13.532664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.3762 0.5702072)
           (cons 40 0)
           (cons 41 0)
           (cons 42 0)
           (cons 91 0)
           (list 10 13.3762 0.7445528)
           (cons 40 0)
           (cons 41 0)
           (cons 42 0)
           (cons 91 0)
           (list 10 13.532664 0.79708)
           (cons 40 0)
           (cons 41 0)
           (cons 42 0)
           (cons 91 0)
           (list 10 14.337336 0.79708)
           (cons 40 0)
           (cons 41 0)
           (cons 42 0)
           (cons 91 0)
           (list 10 14.4938 0.7445528)
           (cons 40 0)
           (cons 41 0)
           (cons 42 0)
           (cons 91 0)
           (list 10 14.4938 0.5702072)
           (cons 40 0)
           (cons 41 0)
           (cons 42 0)
           (cons 91 0)
           (list 10 14.337336 0.51768)
           (cons 40 0)
           (cons 41 0)
           (cons 42 0)
           (cons 91 0)
           (list 10 13.532664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 13.3762 1.0731272)
           (cons 40 0)
           (cons 41 0)
           (cons 42 0)
           (cons 91 0)
           (list 10 13.3762 1.2474728)
           (cons 40 0)
           (cons 41 0)
           (cons 42 0)
           (cons 91 0)
           (list 10 13.532664 1.3)
           (cons 40 0)
           (cons 41 0)
           (cons 42 0)
           (cons 91 0)
           (list 10 14.337336 1.3)
           (cons 40 0)
           (cons 41 0)
           (cons 42 0)
           (cons 91 0)
           (list 10 14.4938 1.2474728)
           (cons 40 0)
           (cons 41 0)
           (cons 42 0)
           (cons 91 0)
           (list 10 14.4938 1.0731272)
           (cons 40 0)
           (cons 41 0)
           (cons 42 0)
           (cons 91 0)
           (list 10 14.337336 1.0206)
           (cons 40 0)
           (cons 41 0)
           (cons 42 0)
           (cons 91 0)
           (list 10 13.532664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 1.3 0 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 15 1.3 0)
           (cons 50 0)
          )
         )
         (entmake
          (list
           (cons 0 "POINT")
           (cons 100 "AcDbEntity")
           (cons 67 0)
           (cons 8 "0")
           (cons 100 "AcDbPoint")
           (list 10 15 -1.3 0)
           (cons 50 0)
          )
         )
         (entmake
          (list
           (cons 0 "POINT")
           (cons 100 "AcDbEntity")
           (cons 67 0)
           (cons 8 "0")
           (cons 100 "AcDbPoint")
           (list 10 13.3 1.3 0)
           (cons 50 0)
          )
         )
         (entmake
          (list
           (cons 0 "POINT")
           (cons 100 "AcDbEntity")
           (cons 67 0)
           (cons 8 "0")
           (cons 100 "AcDbPoint")
           (list 10 13.3 -1.3 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 15 -1.3)
           (cons 40 0)
           (cons 41 0)
           (cons 42 0)
           (cons 91 0)
           (list 10 15 1.3)
           (cons 40 0)
           (cons 41 0)
           (cons 42 0)
           (cons 91 0)
           (list 10 0 1.3)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.6 0.56666667 0)
           (cons 40 0.2)
           (cons 1 "1.30")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 0.23333333 0)
           (cons 40 0.2)
           (cons 1 "1.30")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.1 0)
           (cons 40 0.2)
           (cons 1 "13.30")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.43333333 0)
           (cons 40 0.2)
           (cons 1 "0.00")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "TAC-1999-WB-19-TRUCK"))
        (progn
         (entmake)
         (entmake
          (list
           (cons 0 "BLOCK")
           (cons 2 "TAC-1999-WB-19-TRUCK")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.635 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.635 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 7 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 7.26263966 -0.26263966 0)
           (list 11 7.26263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.8062 -0.7445528)
           (cons 40 0)
           (cons 41 0)
           (cons 42 0)
           (cons 91 0)
           (list 10 5.8062 -0.5702072)
           (cons 40 0)
           (cons 41 0)
           (cons 42 0)
           (cons 91 0)
           (list 10 5.962664 -0.51768)
           (cons 40 0)
           (cons 41 0)
           (cons 42 0)
           (cons 91 0)
           (list 10 6.767336 -0.51768)
           (cons 40 0)
           (cons 41 0)
           (cons 42 0)
           (cons 91 0)
           (list 10 6.9238 -0.5702072)
           (cons 40 0)
           (cons 41 0)
           (cons 42 0)
           (cons 91 0)
           (list 10 6.9238 -0.7445528)
           (cons 40 0)
           (cons 41 0)
           (cons 42 0)
           (cons 91 0)
           (list 10 6.767336 -0.79708)
           (cons 40 0)
           (cons 41 0)
           (cons 42 0)
           (cons 91 0)
           (list 10 5.962664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.8062 -1.2474728)
           (cons 40 0)
           (cons 41 0)
           (cons 42 0)
           (cons 91 0)
           (list 10 5.8062 -1.0731272)
           (cons 40 0)
           (cons 41 0)
           (cons 42 0)
           (cons 91 0)
           (list 10 5.962664 -1.0206)
           (cons 40 0)
           (cons 41 0)
           (cons 42 0)
           (cons 91 0)
           (list 10 6.767336 -1.0206)
           (cons 40 0)
           (cons 41 0)
           (cons 42 0)
           (cons 91 0)
           (list 10 6.9238 -1.0731272)
           (cons 40 0)
           (cons 41 0)
           (cons 42 0)
           (cons 91 0)
           (list 10 6.9238 -1.2474728)
           (cons 40 0)
           (cons 41 0)
           (cons 42 0)
           (cons 91 0)
           (list 10 6.767336 -1.3)
           (cons 40 0)
           (cons 41 0)
           (cons 42 0)
           (cons 91 0)
           (list 10 5.962664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.8062 0.5702072)
           (cons 40 0)
           (cons 41 0)
           (cons 42 0)
           (cons 91 0)
           (list 10 5.8062 0.7445528)
           (cons 40 0)
           (cons 41 0)
           (cons 42 0)
           (cons 91 0)
           (list 10 5.962664 0.79708)
           (cons 40 0)
           (cons 41 0)
           (cons 42 0)
           (cons 91 0)
           (list 10 6.767336 0.79708)
           (cons 40 0)
           (cons 41 0)
           (cons 42 0)
           (cons 91 0)
           (list 10 6.9238 0.7445528)
           (cons 40 0)
           (cons 41 0)
           (cons 42 0)
           (cons 91 0)
           (list 10 6.9238 0.5702072)
           (cons 40 0)
           (cons 41 0)
           (cons 42 0)
           (cons 91 0)
           (list 10 6.767336 0.51768)
           (cons 40 0)
           (cons 41 0)
           (cons 42 0)
           (cons 91 0)
           (list 10 5.962664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.8062 1.0731272)
           (cons 40 0)
           (cons 41 0)
           (cons 42 0)
           (cons 91 0)
           (list 10 5.8062 1.2474728)
           (cons 40 0)
           (cons 41 0)
           (cons 42 0)
           (cons 91 0)
           (list 10 5.962664 1.3)
           (cons 40 0)
           (cons 41 0)
           (cons 42 0)
           (cons 91 0)
           (list 10 6.767336 1.3)
           (cons 40 0)
           (cons 41 0)
           (cons 42 0)
           (cons 91 0)
           (list 10 6.9238 1.2474728)
           (cons 40 0)
           (cons 41 0)
           (cons 42 0)
           (cons 91 0)
           (list 10 6.9238 1.0731272)
           (cons 40 0)
           (cons 41 0)
           (cons 42 0)
           (cons 91 0)
           (list 10 6.767336 1.0206)
           (cons 40 0)
           (cons 41 0)
           (cons 42 0)
           (cons 91 0)
           (list 10 5.962664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.0762 -0.7445528)
           (cons 40 0)
           (cons 41 0)
           (cons 42 0)
           (cons 91 0)
           (list 10 7.0762 -0.5702072)
           (cons 40 0)
           (cons 41 0)
           (cons 42 0)
           (cons 91 0)
           (list 10 7.232664 -0.51768)
           (cons 40 0)
           (cons 41 0)
           (cons 42 0)
           (cons 91 0)
           (list 10 8.037336 -0.51768)
           (cons 40 0)
           (cons 41 0)
           (cons 42 0)
           (cons 91 0)
           (list 10 8.1938 -0.5702072)
           (cons 40 0)
           (cons 41 0)
           (cons 42 0)
           (cons 91 0)
           (list 10 8.1938 -0.7445528)
           (cons 40 0)
           (cons 41 0)
           (cons 42 0)
           (cons 91 0)
           (list 10 8.037336 -0.79708)
           (cons 40 0)
           (cons 41 0)
           (cons 42 0)
           (cons 91 0)
           (list 10 7.232664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.0762 -1.2474728)
           (cons 40 0)
           (cons 41 0)
           (cons 42 0)
           (cons 91 0)
           (list 10 7.0762 -1.0731272)
           (cons 40 0)
           (cons 41 0)
           (cons 42 0)
           (cons 91 0)
           (list 10 7.232664 -1.0206)
           (cons 40 0)
           (cons 41 0)
           (cons 42 0)
           (cons 91 0)
           (list 10 8.037336 -1.0206)
           (cons 40 0)
           (cons 41 0)
           (cons 42 0)
           (cons 91 0)
           (list 10 8.1938 -1.0731272)
           (cons 40 0)
           (cons 41 0)
           (cons 42 0)
           (cons 91 0)
           (list 10 8.1938 -1.2474728)
           (cons 40 0)
           (cons 41 0)
           (cons 42 0)
           (cons 91 0)
           (list 10 8.037336 -1.3)
           (cons 40 0)
           (cons 41 0)
           (cons 42 0)
           (cons 91 0)
           (list 10 7.232664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.0762 0.5702072)
           (cons 40 0)
           (cons 41 0)
           (cons 42 0)
           (cons 91 0)
           (list 10 7.0762 0.7445528)
           (cons 40 0)
           (cons 41 0)
           (cons 42 0)
           (cons 91 0)
           (list 10 7.232664 0.79708)
           (cons 40 0)
           (cons 41 0)
           (cons 42 0)
           (cons 91 0)
           (list 10 8.037336 0.79708)
           (cons 40 0)
           (cons 41 0)
           (cons 42 0)
           (cons 91 0)
           (list 10 8.1938 0.7445528)
           (cons 40 0)
           (cons 41 0)
           (cons 42 0)
           (cons 91 0)
           (list 10 8.1938 0.5702072)
           (cons 40 0)
           (cons 41 0)
           (cons 42 0)
           (cons 91 0)
           (list 10 8.037336 0.51768)
           (cons 40 0)
           (cons 41 0)
           (cons 42 0)
           (cons 91 0)
           (list 10 7.232664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.0762 1.0731272)
           (cons 40 0)
           (cons 41 0)
           (cons 42 0)
           (cons 91 0)
           (list 10 7.0762 1.2474728)
           (cons 40 0)
           (cons 41 0)
           (cons 42 0)
           (cons 91 0)
           (list 10 7.232664 1.3)
           (cons 40 0)
           (cons 41 0)
           (cons 42 0)
           (cons 91 0)
           (list 10 8.037336 1.3)
           (cons 40 0)
           (cons 41 0)
           (cons 42 0)
           (cons 91 0)
           (list 10 8.1938 1.2474728)
           (cons 40 0)
           (cons 41 0)
           (cons 42 0)
           (cons 91 0)
           (list 10 8.1938 1.0731272)
           (cons 40 0)
           (cons 41 0)
           (cons 42 0)
           (cons 91 0)
           (list 10 8.037336 1.0206)
           (cons 40 0)
           (cons 41 0)
           (cons 42 0)
           (cons 91 0)
           (list 10 7.232664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 7 0 0)
           (cons 50 0)
          )
         )
         (entmake
          (list
           (cons 0 "POINT")
           (cons 100 "AcDbEntity")
           (cons 67 0)
           (cons 8 "0")
           (cons 100 "AcDbPoint")
           (list 10 0.8 -1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0.8 1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 7 1.3 0)
           (cons 50 0)
          )
         )
         (entmake
          (list
           (cons 0 "POINT")
           (cons 100 "AcDbEntity")
           (cons 67 0)
           (cons 8 "0")
           (cons 100 "AcDbPoint")
           (list 10 7 -1.3 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 7.635 -1.3)
           (cons 40 0)
           (cons 41 0)
           (cons 42 0)
           (cons 91 0)
           (list 10 7.635 1.3)
           (cons 40 0)
           (cons 41 0)
           (cons 42 0)
           (cons 91 0)
           (list 10 0 1.3)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0.8 0 0)
           (cons 50 0)
          )
         )
         (entmake
          (list
           (cons 0 "ATTDEF")
           (cons 100 "AcDbEntity")
           (cons 67 0)
           (cons 8 "0")
           (cons 100 "AcDbText")
           (list 10 0.1 0.56666667 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 0.23333333 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.1 0)
           (cons 40 0.2)
           (cons 1 "7.00")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.43333333 0)
           (cons 40 0.2)
           (cons 1 "7.00")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.76666667 0)
           (cons 40 0.2)
           (cons 1 "29.0")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelRightM1")
           (list 10 0.8 1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM1")
           (list 10 0.8 -1.0206 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "TAC-1999-P"))
        (progn
         (entmake)
         (entmake
          (list
           (cons 0 "BLOCK")
           (cons 2 "TAC-1999-P")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.6 -1 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 5.6 1 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.9571 -0.9677674)
           (cons 40 0)
           (cons 41 0)
           (cons 42 0)
           (cons 91 0)
           (list 10 3.9571 -0.8607826)
           (cons 40 0)
           (cons 41 0)
           (cons 42 0)
           (cons 91 0)
           (list 10 4.053112 -0.82855)
           (cons 40 0)
           (cons 41 0)
           (cons 42 0)
           (cons 91 0)
           (list 10 4.546888 -0.82855)
           (cons 40 0)
           (cons 41 0)
           (cons 42 0)
           (cons 91 0)
           (list 10 4.6429 -0.8607826)
           (cons 40 0)
           (cons 41 0)
           (cons 42 0)
           (cons 91 0)
           (list 10 4.6429 -0.9677674)
           (cons 40 0)
           (cons 41 0)
           (cons 42 0)
           (cons 91 0)
           (list 10 4.546888 -1)
           (cons 40 0)
           (cons 41 0)
           (cons 42 0)
           (cons 91 0)
           (list 10 4.053112 -1)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.9571 0.8607826)
           (cons 40 0)
           (cons 41 0)
           (cons 42 0)
           (cons 91 0)
           (list 10 3.9571 0.9677674)
           (cons 40 0)
           (cons 41 0)
           (cons 42 0)
           (cons 91 0)
           (list 10 4.053112 1)
           (cons 40 0)
           (cons 41 0)
           (cons 42 0)
           (cons 91 0)
           (list 10 4.546888 1)
           (cons 40 0)
           (cons 41 0)
           (cons 42 0)
           (cons 91 0)
           (list 10 4.6429 0.9677674)
           (cons 40 0)
           (cons 41 0)
           (cons 42 0)
           (cons 91 0)
           (list 10 4.6429 0.8607826)
           (cons 40 0)
           (cons 41 0)
           (cons 42 0)
           (cons 91 0)
           (list 10 4.546888 0.82855)
           (cons 40 0)
           (cons 41 0)
           (cons 42 0)
           (cons 91 0)
           (list 10 4.053112 0.82855)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 1 0)
           (cons 50 0)
          )
         )
         (entmake
          (list
           (cons 0 "POINT")
           (cons 100 "AcDbEntity")
           (cons 67 0)
           (cons 8 "0")
           (cons 100 "AcDbPoint")
           (list 10 1.1 1 0)
           (cons 50 0)
          )
         )
         (entmake
          (list
           (cons 0 "POINT")
           (cons 100 "AcDbEntity")
           (cons 67 0)
           (cons 8 "0")
           (cons 100 "AcDbPoint")
           (list 10 4.3 1 0)
           (cons 50 0)
          )
         )
         (entmake
          (list
           (cons 0 "POINT")
           (cons 100 "AcDbEntity")
           (cons 67 0)
           (cons 8 "0")
           (cons 100 "AcDbPoint")
           (list 10 5.6 1 0)
           (cons 50 0)
          )
         )
         (entmake
          (list
           (cons 0 "POINT")
           (cons 100 "AcDbEntity")
           (cons 67 0)
           (cons 8 "0")
           (cons 100 "AcDbPoint")
           (list 10 5.6 -1 0)
           (cons 50 0)
          )
         )
         (entmake
          (list
           (cons 0 "POINT")
           (cons 100 "AcDbEntity")
           (cons 67 0)
           (cons 8 "0")
           (cons 100 "AcDbPoint")
           (list 10 4.3 -1 0)
           (cons 50 0)
          )
         )
         (entmake
          (list
           (cons 0 "POINT")
           (cons 100 "AcDbEntity")
           (cons 67 0)
           (cons 8 "0")
           (cons 100 "AcDbPoint")
           (list 10 1.1 -1 0)
           (cons 50 0)
          )
         )
         (entmake
          (list
           (cons 0 "POINT")
           (cons 100 "AcDbEntity")
           (cons 67 0)
           (cons 8 "0")
           (cons 100 "AcDbPoint")
           (list 10 0 -1 0)
           (cons 50 0)
          )
         )
         (entmake
          (list
           (cons 0 "POINT")
           (cons 100 "AcDbEntity")
           (cons 67 0)
           (cons 8 "0")
           (cons 100 "AcDbPoint")
           (list 10 1.1 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1)
           (cons 40 0)
           (cons 41 0)
           (cons 42 0)
           (cons 91 0)
           (list 10 5.6 -1)
           (cons 40 0)
           (cons 41 0)
           (cons 42 0)
           (cons 91 0)
           (list 10 5.6 1)
           (cons 40 0)
           (cons 41 0)
           (cons 42 0)
           (cons 91 0)
           (list 10 0 1)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.4 0.56666667 0)
           (cons 40 0.2)
           (cons 1 "1.10")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.4 0.23333333 0)
           (cons 40 0.2)
           (cons 1 "1.10")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.4 -0.1 0)
           (cons 40 0.2)
           (cons 1 "4.30")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.4 -0.43333333 0)
           (cons 40 0.2)
           (cons 1 "0.00")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.4 -0.76666667 0)
           (cons 40 0.2)
           (cons 1 "36.2")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelLeftM3")
           (list 10 1.1 -0.82855 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM3")
           (list 10 1.1 0.82855 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "TAC-1999-MSU"))
        (progn
         (entmake)
         (entmake
          (list
           (cons 0 "BLOCK")
           (cons 2 "TAC-1999-MSU")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 10 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 10 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.792 -0.795048)
           (cons 40 0)
           (cons 41 0)
           (cons 42 0)
           (cons 91 0)
           (list 10 6.792 -0.636552)
           (cons 40 0)
           (cons 41 0)
           (cons 42 0)
           (cons 91 0)
           (list 10 6.93424 -0.5888)
           (cons 40 0)
           (cons 41 0)
           (cons 42 0)
           (cons 91 0)
           (list 10 7.66576 -0.5888)
           (cons 40 0)
           (cons 41 0)
           (cons 42 0)
           (cons 91 0)
           (list 10 7.808 -0.636552)
           (cons 40 0)
           (cons 41 0)
           (cons 42 0)
           (cons 91 0)
           (list 10 7.808 -0.795048)
           (cons 40 0)
           (cons 41 0)
           (cons 42 0)
           (cons 91 0)
           (list 10 7.66576 -0.8428)
           (cons 40 0)
           (cons 41 0)
           (cons 42 0)
           (cons 91 0)
           (list 10 6.93424 -0.8428)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.792 -1.252248)
           (cons 40 0)
           (cons 41 0)
           (cons 42 0)
           (cons 91 0)
           (list 10 6.792 -1.093752)
           (cons 40 0)
           (cons 41 0)
           (cons 42 0)
           (cons 91 0)
           (list 10 6.93424 -1.046)
           (cons 40 0)
           (cons 41 0)
           (cons 42 0)
           (cons 91 0)
           (list 10 7.66576 -1.046)
           (cons 40 0)
           (cons 41 0)
           (cons 42 0)
           (cons 91 0)
           (list 10 7.808 -1.093752)
           (cons 40 0)
           (cons 41 0)
           (cons 42 0)
           (cons 91 0)
           (list 10 7.808 -1.252248)
           (cons 40 0)
           (cons 41 0)
           (cons 42 0)
           (cons 91 0)
           (list 10 7.66576 -1.3)
           (cons 40 0)
           (cons 41 0)
           (cons 42 0)
           (cons 91 0)
           (list 10 6.93424 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.792 0.636552)
           (cons 40 0)
           (cons 41 0)
           (cons 42 0)
           (cons 91 0)
           (list 10 6.792 0.795048)
           (cons 40 0)
           (cons 41 0)
           (cons 42 0)
           (cons 91 0)
           (list 10 6.93424 0.8428)
           (cons 40 0)
           (cons 41 0)
           (cons 42 0)
           (cons 91 0)
           (list 10 7.66576 0.8428)
           (cons 40 0)
           (cons 41 0)
           (cons 42 0)
           (cons 91 0)
           (list 10 7.808 0.795048)
           (cons 40 0)
           (cons 41 0)
           (cons 42 0)
           (cons 91 0)
           (list 10 7.808 0.636552)
           (cons 40 0)
           (cons 41 0)
           (cons 42 0)
           (cons 91 0)
           (list 10 7.66576 0.5888)
           (cons 40 0)
           (cons 41 0)
           (cons 42 0)
           (cons 91 0)
           (list 10 6.93424 0.5888)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.792 1.093752)
           (cons 40 0)
           (cons 41 0)
           (cons 42 0)
           (cons 91 0)
           (list 10 6.792 1.252248)
           (cons 40 0)
           (cons 41 0)
           (cons 42 0)
           (cons 91 0)
           (list 10 6.93424 1.3)
           (cons 40 0)
           (cons 41 0)
           (cons 42 0)
           (cons 91 0)
           (list 10 7.66576 1.3)
           (cons 40 0)
           (cons 41 0)
           (cons 42 0)
           (cons 91 0)
           (list 10 7.808 1.252248)
           (cons 40 0)
           (cons 41 0)
           (cons 42 0)
           (cons 91 0)
           (list 10 7.808 1.093752)
           (cons 40 0)
           (cons 41 0)
           (cons 42 0)
           (cons 91 0)
           (list 10 7.66576 1.046)
           (cons 40 0)
           (cons 41 0)
           (cons 42 0)
           (cons 91 0)
           (list 10 6.93424 1.046)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0.8 -1.3 0)
           (cons 50 0)
          )
         )
         (entmake
          (list
           (cons 0 "POINT")
           (cons 100 "AcDbEntity")
           (cons 67 0)
           (cons 8 "0")
           (cons 100 "AcDbPoint")
           (list 10 7.3 -1.3 0)
           (cons 50 0)
          )
         )
         (entmake
          (list
           (cons 0 "POINT")
           (cons 100 "AcDbEntity")
           (cons 67 0)
           (cons 8 "0")
           (cons 100 "AcDbPoint")
           (list 10 10 -1.3 0)
           (cons 50 0)
          )
         )
         (entmake
          (list
           (cons 0 "POINT")
           (cons 100 "AcDbEntity")
           (cons 67 0)
           (cons 8 "0")
           (cons 100 "AcDbPoint")
           (list 10 10 1.3 0)
           (cons 50 0)
          )
         )
         (entmake
          (list
           (cons 0 "POINT")
           (cons 100 "AcDbEntity")
           (cons 67 0)
           (cons 8 "0")
           (cons 100 "AcDbPoint")
           (list 10 7.3 1.3 0)
           (cons 50 0)
          )
         )
         (entmake
          (list
           (cons 0 "POINT")
           (cons 100 "AcDbEntity")
           (cons 67 0)
           (cons 8 "0")
           (cons 100 "AcDbPoint")
           (list 10 0.8 1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0.8 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 10 -1.3)
           (cons 40 0)
           (cons 41 0)
           (cons 42 0)
           (cons 91 0)
           (list 10 10 1.3)
           (cons 40 0)
           (cons 41 0)
           (cons 42 0)
           (cons 91 0)
           (list 10 0 1.3)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.1 0.56666667 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 0.23333333 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.1 0)
           (cons 40 0.2)
           (cons 1 "7.30")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.43333333 0)
           (cons 40 0.2)
           (cons 1 "0.00")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.76666667 0)
           (cons 40 0.2)
           (cons 1 "40.1")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelRightM2")
           (list 10 0.8 1.046 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM2")
           (list 10 0.8 -1.046 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "TAC-1999-LSU"))
        (progn
         (entmake)
         (entmake
          (list
           (cons 0 "BLOCK")
           (cons 2 "TAC-1999-LSU")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.4 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.4 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.692 -1.252248)
           (cons 40 0)
           (cons 41 0)
           (cons 42 0)
           (cons 91 0)
           (list 10 3.692 -1.093752)
           (cons 40 0)
           (cons 41 0)
           (cons 42 0)
           (cons 91 0)
           (list 10 3.83424 -1.046)
           (cons 40 0)
           (cons 41 0)
           (cons 42 0)
           (cons 91 0)
           (list 10 4.56576 -1.046)
           (cons 40 0)
           (cons 41 0)
           (cons 42 0)
           (cons 91 0)
           (list 10 4.708 -1.093752)
           (cons 40 0)
           (cons 41 0)
           (cons 42 0)
           (cons 91 0)
           (list 10 4.708 -1.252248)
           (cons 40 0)
           (cons 41 0)
           (cons 42 0)
           (cons 91 0)
           (list 10 4.56576 -1.3)
           (cons 40 0)
           (cons 41 0)
           (cons 42 0)
           (cons 91 0)
           (list 10 3.83424 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 3.692 1.093752)
           (cons 40 0)
           (cons 41 0)
           (cons 42 0)
           (cons 91 0)
           (list 10 3.692 1.252248)
           (cons 40 0)
           (cons 41 0)
           (cons 42 0)
           (cons 91 0)
           (list 10 3.83424 1.3)
           (cons 40 0)
           (cons 41 0)
           (cons 42 0)
           (cons 91 0)
           (list 10 4.56576 1.3)
           (cons 40 0)
           (cons 41 0)
           (cons 42 0)
           (cons 91 0)
           (list 10 4.708 1.252248)
           (cons 40 0)
           (cons 41 0)
           (cons 42 0)
           (cons 91 0)
           (list 10 4.708 1.093752)
           (cons 40 0)
           (cons 41 0)
           (cons 42 0)
           (cons 91 0)
           (list 10 4.56576 1.046)
           (cons 40 0)
           (cons 41 0)
           (cons 42 0)
           (cons 91 0)
           (list 10 3.83424 1.046)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0.8 -1.3 0)
           (cons 50 0)
          )
         )
         (entmake
          (list
           (cons 0 "POINT")
           (cons 100 "AcDbEntity")
           (cons 67 0)
           (cons 8 "0")
           (cons 100 "AcDbPoint")
           (list 10 4.2 -1.3 0)
           (cons 50 0)
          )
         )
         (entmake
          (list
           (cons 0 "POINT")
           (cons 100 "AcDbEntity")
           (cons 67 0)
           (cons 8 "0")
           (cons 100 "AcDbPoint")
           (list 10 6.4 -1.3 0)
           (cons 50 0)
          )
         )
         (entmake
          (list
           (cons 0 "POINT")
           (cons 100 "AcDbEntity")
           (cons 67 0)
           (cons 8 "0")
           (cons 100 "AcDbPoint")
           (list 10 6.4 1.3 0)
           (cons 50 0)
          )
         )
         (entmake
          (list
           (cons 0 "POINT")
           (cons 100 "AcDbEntity")
           (cons 67 0)
           (cons 8 "0")
           (cons 100 "AcDbPoint")
           (list 10 4.2 1.3 0)
           (cons 50 0)
          )
         )
         (entmake
          (list
           (cons 0 "POINT")
           (cons 100 "AcDbEntity")
           (cons 67 0)
           (cons 8 "0")
           (cons 100 "AcDbPoint")
           (list 10 0.8 1.3 0)
           (cons 50 0)
          )
         )
         (entmake
          (list
           (cons 0 "POINT")
           (cons 100 "AcDbEntity")
           (cons 67 0)
           (cons 8 "0")
           (cons 100 "AcDbPoint")
           (list 10 0.8 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 6.4 -1.3)
           (cons 40 0)
           (cons 41 0)
           (cons 42 0)
           (cons 91 0)
           (list 10 6.4 1.3)
           (cons 40 0)
           (cons 41 0)
           (cons 42 0)
           (cons 91 0)
           (list 10 0 1.3)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.1 0.56666667 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 0.23333333 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.1 0)
           (cons 40 0.2)
           (cons 1 "4.20")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.43333333 0)
           (cons 40 0.2)
           (cons 1 "0.00")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.76666667 0)
           (cons 40 0.2)
           (cons 1 "40.8")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelLeftM2")
           (list 10 0.8 -1.046 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM2")
           (list 10 0.8 1.046 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "TAC-1999-I-BUS"))
        (progn
         (entmake)
         (entmake
          (list
           (cons 0 "BLOCK")
           (cons 2 "TAC-1999-I-BUS")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 14 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 14 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.492 -1.152248)
           (cons 40 0)
           (cons 41 0)
           (cons 42 0)
           (cons 91 0)
           (list 10 9.492 -0.993752)
           (cons 40 0)
           (cons 41 0)
           (cons 42 0)
           (cons 91 0)
           (list 10 9.63424 -0.946)
           (cons 40 0)
           (cons 41 0)
           (cons 42 0)
           (cons 91 0)
           (list 10 10.36576 -0.946)
           (cons 40 0)
           (cons 41 0)
           (cons 42 0)
           (cons 91 0)
           (list 10 10.508 -0.993752)
           (cons 40 0)
           (cons 41 0)
           (cons 42 0)
           (cons 91 0)
           (list 10 10.508 -1.152248)
           (cons 40 0)
           (cons 41 0)
           (cons 42 0)
           (cons 91 0)
           (list 10 10.36576 -1.2)
           (cons 40 0)
           (cons 41 0)
           (cons 42 0)
           (cons 91 0)
           (list 10 9.63424 -1.2)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.492 0.993752)
           (cons 40 0)
           (cons 41 0)
           (cons 42 0)
           (cons 91 0)
           (list 10 9.492 1.152248)
           (cons 40 0)
           (cons 41 0)
           (cons 42 0)
           (cons 91 0)
           (list 10 9.63424 1.2)
           (cons 40 0)
           (cons 41 0)
           (cons 42 0)
           (cons 91 0)
           (list 10 10.36576 1.2)
           (cons 40 0)
           (cons 41 0)
           (cons 42 0)
           (cons 91 0)
           (list 10 10.508 1.152248)
           (cons 40 0)
           (cons 41 0)
           (cons 42 0)
           (cons 91 0)
           (list 10 10.508 0.993752)
           (cons 40 0)
           (cons 41 0)
           (cons 42 0)
           (cons 91 0)
           (list 10 10.36576 0.946)
           (cons 40 0)
           (cons 41 0)
           (cons 42 0)
           (cons 91 0)
           (list 10 9.63424 0.946)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -1.2 0)
           (cons 50 0)
          )
         )
         (entmake
          (list
           (cons 0 "POINT")
           (cons 100 "AcDbEntity")
           (cons 67 0)
           (cons 8 "0")
           (cons 100 "AcDbPoint")
           (list 10 0 1.2 0)
           (cons 50 0)
          )
         )
         (entmake
          (list
           (cons 0 "POINT")
           (cons 100 "AcDbEntity")
           (cons 67 0)
           (cons 8 "0")
           (cons 100 "AcDbPoint")
           (list 10 14 1.2 0)
           (cons 50 0)
          )
         )
         (entmake
          (list
           (cons 0 "POINT")
           (cons 100 "AcDbEntity")
           (cons 67 0)
           (cons 8 "0")
           (cons 100 "AcDbPoint")
           (list 10 14 -1.2 0)
           (cons 50 0)
          )
         )
         (entmake
          (list
           (cons 0 "POINT")
           (cons 100 "AcDbEntity")
           (cons 67 0)
           (cons 8 "0")
           (cons 100 "AcDbPoint")
           (list 10 1.8 -1.2 0)
           (cons 50 0)
          )
         )
         (entmake
          (list
           (cons 0 "POINT")
           (cons 100 "AcDbEntity")
           (cons 67 0)
           (cons 8 "0")
           (cons 100 "AcDbPoint")
           (list 10 1.8 1.2 0)
           (cons 50 0)
          )
         )
         (entmake
          (list
           (cons 0 "POINT")
           (cons 100 "AcDbEntity")
           (cons 67 0)
           (cons 8 "0")
           (cons 100 "AcDbPoint")
           (list 10 10 1.2 0)
           (cons 50 0)
          )
         )
         (entmake
          (list
           (cons 0 "POINT")
           (cons 100 "AcDbEntity")
           (cons 67 0)
           (cons 8 "0")
           (cons 100 "AcDbPoint")
           (list 10 10 -1.2 0)
           (cons 50 0)
          )
         )
         (entmake
          (list
           (cons 0 "POINT")
           (cons 100 "AcDbEntity")
           (cons 67 0)
           (cons 8 "0")
           (cons 100 "AcDbPoint")
           (list 10 1.8 0 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.2)
           (cons 40 0)
           (cons 41 0)
           (cons 42 0)
           (cons 91 0)
           (list 10 14 -1.2)
           (cons 40 0)
           (cons 41 0)
           (cons 42 0)
           (cons 91 0)
           (list 10 14 1.2)
           (cons 40 0)
           (cons 41 0)
           (cons 42 0)
           (cons 91 0)
           (list 10 0 1.2)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 1.1 0.56666667 0)
           (cons 40 0.2)
           (cons 1 "1.80")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.1 0.23333333 0)
           (cons 40 0.2)
           (cons 1 "1.80")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.1 -0.1 0)
           (cons 40 0.2)
           (cons 1 "10.00")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.1 -0.43333333 0)
           (cons 40 0.2)
           (cons 1 "0.00")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.1 -0.76666667 0)
           (cons 40 0.2)
           (cons 1 "39.1")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelRightM2")
           (list 10 1.8 0.946 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM2")
           (list 10 1.8 -0.946 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "TAC-1999-HSU"))
        (progn
         (entmake)
         (entmake
          (list
           (cons 0 "BLOCK")
           (cons 2 "TAC-1999-HSU")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 11.5 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 11.5 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.057 -0.795048)
           (cons 40 0)
           (cons 41 0)
           (cons 42 0)
           (cons 91 0)
           (list 10 8.057 -0.636552)
           (cons 40 0)
           (cons 41 0)
           (cons 42 0)
           (cons 91 0)
           (list 10 8.19924 -0.5888)
           (cons 40 0)
           (cons 41 0)
           (cons 42 0)
           (cons 91 0)
           (list 10 8.93076 -0.5888)
           (cons 40 0)
           (cons 41 0)
           (cons 42 0)
           (cons 91 0)
           (list 10 9.073 -0.636552)
           (cons 40 0)
           (cons 41 0)
           (cons 42 0)
           (cons 91 0)
           (list 10 9.073 -0.795048)
           (cons 40 0)
           (cons 41 0)
           (cons 42 0)
           (cons 91 0)
           (list 10 8.93076 -0.8428)
           (cons 40 0)
           (cons 41 0)
           (cons 42 0)
           (cons 91 0)
           (list 10 8.19924 -0.8428)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.057 -1.252248)
           (cons 40 0)
           (cons 41 0)
           (cons 42 0)
           (cons 91 0)
           (list 10 8.057 -1.093752)
           (cons 40 0)
           (cons 41 0)
           (cons 42 0)
           (cons 91 0)
           (list 10 8.19924 -1.046)
           (cons 40 0)
           (cons 41 0)
           (cons 42 0)
           (cons 91 0)
           (list 10 8.93076 -1.046)
           (cons 40 0)
           (cons 41 0)
           (cons 42 0)
           (cons 91 0)
           (list 10 9.073 -1.093752)
           (cons 40 0)
           (cons 41 0)
           (cons 42 0)
           (cons 91 0)
           (list 10 9.073 -1.252248)
           (cons 40 0)
           (cons 41 0)
           (cons 42 0)
           (cons 91 0)
           (list 10 8.93076 -1.3)
           (cons 40 0)
           (cons 41 0)
           (cons 42 0)
           (cons 91 0)
           (list 10 8.19924 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.057 0.636552)
           (cons 40 0)
           (cons 41 0)
           (cons 42 0)
           (cons 91 0)
           (list 10 8.057 0.795048)
           (cons 40 0)
           (cons 41 0)
           (cons 42 0)
           (cons 91 0)
           (list 10 8.19924 0.8428)
           (cons 40 0)
           (cons 41 0)
           (cons 42 0)
           (cons 91 0)
           (list 10 8.93076 0.8428)
           (cons 40 0)
           (cons 41 0)
           (cons 42 0)
           (cons 91 0)
           (list 10 9.073 0.795048)
           (cons 40 0)
           (cons 41 0)
           (cons 42 0)
           (cons 91 0)
           (list 10 9.073 0.636552)
           (cons 40 0)
           (cons 41 0)
           (cons 42 0)
           (cons 91 0)
           (list 10 8.93076 0.5888)
           (cons 40 0)
           (cons 41 0)
           (cons 42 0)
           (cons 91 0)
           (list 10 8.19924 0.5888)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.057 1.093752)
           (cons 40 0)
           (cons 41 0)
           (cons 42 0)
           (cons 91 0)
           (list 10 8.057 1.252248)
           (cons 40 0)
           (cons 41 0)
           (cons 42 0)
           (cons 91 0)
           (list 10 8.19924 1.3)
           (cons 40 0)
           (cons 41 0)
           (cons 42 0)
           (cons 91 0)
           (list 10 8.93076 1.3)
           (cons 40 0)
           (cons 41 0)
           (cons 42 0)
           (cons 91 0)
           (list 10 9.073 1.252248)
           (cons 40 0)
           (cons 41 0)
           (cons 42 0)
           (cons 91 0)
           (list 10 9.073 1.093752)
           (cons 40 0)
           (cons 41 0)
           (cons 42 0)
           (cons 91 0)
           (list 10 8.93076 1.046)
           (cons 40 0)
           (cons 41 0)
           (cons 42 0)
           (cons 91 0)
           (list 10 8.19924 1.046)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.327 -0.795048)
           (cons 40 0)
           (cons 41 0)
           (cons 42 0)
           (cons 91 0)
           (list 10 9.327 -0.636552)
           (cons 40 0)
           (cons 41 0)
           (cons 42 0)
           (cons 91 0)
           (list 10 9.46924 -0.5888)
           (cons 40 0)
           (cons 41 0)
           (cons 42 0)
           (cons 91 0)
           (list 10 10.20076 -0.5888)
           (cons 40 0)
           (cons 41 0)
           (cons 42 0)
           (cons 91 0)
           (list 10 10.343 -0.636552)
           (cons 40 0)
           (cons 41 0)
           (cons 42 0)
           (cons 91 0)
           (list 10 10.343 -0.795048)
           (cons 40 0)
           (cons 41 0)
           (cons 42 0)
           (cons 91 0)
           (list 10 10.20076 -0.8428)
           (cons 40 0)
           (cons 41 0)
           (cons 42 0)
           (cons 91 0)
           (list 10 9.46924 -0.8428)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.327 -1.252248)
           (cons 40 0)
           (cons 41 0)
           (cons 42 0)
           (cons 91 0)
           (list 10 9.327 -1.093752)
           (cons 40 0)
           (cons 41 0)
           (cons 42 0)
           (cons 91 0)
           (list 10 9.46924 -1.046)
           (cons 40 0)
           (cons 41 0)
           (cons 42 0)
           (cons 91 0)
           (list 10 10.20076 -1.046)
           (cons 40 0)
           (cons 41 0)
           (cons 42 0)
           (cons 91 0)
           (list 10 10.343 -1.093752)
           (cons 40 0)
           (cons 41 0)
           (cons 42 0)
           (cons 91 0)
           (list 10 10.343 -1.252248)
           (cons 40 0)
           (cons 41 0)
           (cons 42 0)
           (cons 91 0)
           (list 10 10.20076 -1.3)
           (cons 40 0)
           (cons 41 0)
           (cons 42 0)
           (cons 91 0)
           (list 10 9.46924 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.327 0.636552)
           (cons 40 0)
           (cons 41 0)
           (cons 42 0)
           (cons 91 0)
           (list 10 9.327 0.795048)
           (cons 40 0)
           (cons 41 0)
           (cons 42 0)
           (cons 91 0)
           (list 10 9.46924 0.8428)
           (cons 40 0)
           (cons 41 0)
           (cons 42 0)
           (cons 91 0)
           (list 10 10.20076 0.8428)
           (cons 40 0)
           (cons 41 0)
           (cons 42 0)
           (cons 91 0)
           (list 10 10.343 0.795048)
           (cons 40 0)
           (cons 41 0)
           (cons 42 0)
           (cons 91 0)
           (list 10 10.343 0.636552)
           (cons 40 0)
           (cons 41 0)
           (cons 42 0)
           (cons 91 0)
           (list 10 10.20076 0.5888)
           (cons 40 0)
           (cons 41 0)
           (cons 42 0)
           (cons 91 0)
           (list 10 9.46924 0.5888)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.327 1.093752)
           (cons 40 0)
           (cons 41 0)
           (cons 42 0)
           (cons 91 0)
           (list 10 9.327 1.252248)
           (cons 40 0)
           (cons 41 0)
           (cons 42 0)
           (cons 91 0)
           (list 10 9.46924 1.3)
           (cons 40 0)
           (cons 41 0)
           (cons 42 0)
           (cons 91 0)
           (list 10 10.20076 1.3)
           (cons 40 0)
           (cons 41 0)
           (cons 42 0)
           (cons 91 0)
           (list 10 10.343 1.252248)
           (cons 40 0)
           (cons 41 0)
           (cons 42 0)
           (cons 91 0)
           (list 10 10.343 1.093752)
           (cons 40 0)
           (cons 41 0)
           (cons 42 0)
           (cons 91 0)
           (list 10 10.20076 1.046)
           (cons 40 0)
           (cons 41 0)
           (cons 42 0)
           (cons 91 0)
           (list 10 9.46924 1.046)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 11.5 1.3 0)
           (cons 50 0)
          )
         )
         (entmake
          (list
           (cons 0 "POINT")
           (cons 100 "AcDbEntity")
           (cons 67 0)
           (cons 8 "0")
           (cons 100 "AcDbPoint")
           (list 10 11.5 -1.3 0)
           (cons 50 0)
          )
         )
         (entmake
          (list
           (cons 0 "POINT")
           (cons 100 "AcDbEntity")
           (cons 67 0)
           (cons 8 "0")
           (cons 100 "AcDbPoint")
           (list 10 0.8 -1.3 0)
           (cons 50 0)
          )
         )
         (entmake
          (list
           (cons 0 "POINT")
           (cons 100 "AcDbEntity")
           (cons 67 0)
           (cons 8 "0")
           (cons 100 "AcDbPoint")
           (list 10 0.8 1.3 0)
           (cons 50 0)
          )
         )
         (entmake
          (list
           (cons 0 "POINT")
           (cons 100 "AcDbEntity")
           (cons 67 0)
           (cons 8 "0")
           (cons 100 "AcDbPoint")
           (list 10 0.8 0 0)
           (cons 50 0)
          )
         )
         (entmake
          (list
           (cons 0 "POINT")
           (cons 100 "AcDbEntity")
           (cons 67 0)
           (cons 8 "0")
           (cons 100 "AcDbPoint")
           (list 10 9.2 1.3 0)
           (cons 50 0)
          )
         )
         (entmake
          (list
           (cons 0 "POINT")
           (cons 100 "AcDbEntity")
           (cons 67 0)
           (cons 8 "0")
           (cons 100 "AcDbPoint")
           (list 10 9.2 -1.3 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 11.5 -1.3)
           (cons 40 0)
           (cons 41 0)
           (cons 42 0)
           (cons 91 0)
           (list 10 11.5 1.3)
           (cons 40 0)
           (cons 41 0)
           (cons 42 0)
           (cons 91 0)
           (list 10 0 1.3)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.1 0.56666667 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 0.23333333 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.1 0)
           (cons 40 0.2)
           (cons 1 "9.20")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.43333333 0)
           (cons 40 0.2)
           (cons 1 "0.00")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.76666667 0)
           (cons 40 0.2)
           (cons 1 "39.7")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelLeftM2")
           (list 10 0.8 -1.046 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM2")
           (list 10 0.8 1.046 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "TAC-1999-BTD-TRAILER2"))
        (progn
         (entmake)
         (entmake
          (list
           (cons 0 "BLOCK")
           (cons 2 "TAC-1999-BTD-TRAILER2")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.6 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.6 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 1.3 0 0)
           (cons 40 0.104)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1062 -0.7445528)
           (cons 40 0)
           (cons 41 0)
           (cons 42 0)
           (cons 91 0)
           (list 10 7.1062 -0.5702072)
           (cons 40 0)
           (cons 41 0)
           (cons 42 0)
           (cons 91 0)
           (list 10 7.262664 -0.51768)
           (cons 40 0)
           (cons 41 0)
           (cons 42 0)
           (cons 91 0)
           (list 10 8.067336 -0.51768)
           (cons 40 0)
           (cons 41 0)
           (cons 42 0)
           (cons 91 0)
           (list 10 8.2238 -0.5702072)
           (cons 40 0)
           (cons 41 0)
           (cons 42 0)
           (cons 91 0)
           (list 10 8.2238 -0.7445528)
           (cons 40 0)
           (cons 41 0)
           (cons 42 0)
           (cons 91 0)
           (list 10 8.067336 -0.79708)
           (cons 40 0)
           (cons 41 0)
           (cons 42 0)
           (cons 91 0)
           (list 10 7.262664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1062 -1.2474728)
           (cons 40 0)
           (cons 41 0)
           (cons 42 0)
           (cons 91 0)
           (list 10 7.1062 -1.0731272)
           (cons 40 0)
           (cons 41 0)
           (cons 42 0)
           (cons 91 0)
           (list 10 7.262664 -1.0206)
           (cons 40 0)
           (cons 41 0)
           (cons 42 0)
           (cons 91 0)
           (list 10 8.067336 -1.0206)
           (cons 40 0)
           (cons 41 0)
           (cons 42 0)
           (cons 91 0)
           (list 10 8.2238 -1.0731272)
           (cons 40 0)
           (cons 41 0)
           (cons 42 0)
           (cons 91 0)
           (list 10 8.2238 -1.2474728)
           (cons 40 0)
           (cons 41 0)
           (cons 42 0)
           (cons 91 0)
           (list 10 8.067336 -1.3)
           (cons 40 0)
           (cons 41 0)
           (cons 42 0)
           (cons 91 0)
           (list 10 7.262664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1062 0.5702072)
           (cons 40 0)
           (cons 41 0)
           (cons 42 0)
           (cons 91 0)
           (list 10 7.1062 0.7445528)
           (cons 40 0)
           (cons 41 0)
           (cons 42 0)
           (cons 91 0)
           (list 10 7.262664 0.79708)
           (cons 40 0)
           (cons 41 0)
           (cons 42 0)
           (cons 91 0)
           (list 10 8.067336 0.79708)
           (cons 40 0)
           (cons 41 0)
           (cons 42 0)
           (cons 91 0)
           (list 10 8.2238 0.7445528)
           (cons 40 0)
           (cons 41 0)
           (cons 42 0)
           (cons 91 0)
           (list 10 8.2238 0.5702072)
           (cons 40 0)
           (cons 41 0)
           (cons 42 0)
           (cons 91 0)
           (list 10 8.067336 0.51768)
           (cons 40 0)
           (cons 41 0)
           (cons 42 0)
           (cons 91 0)
           (list 10 7.262664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.1062 1.0731272)
           (cons 40 0)
           (cons 41 0)
           (cons 42 0)
           (cons 91 0)
           (list 10 7.1062 1.2474728)
           (cons 40 0)
           (cons 41 0)
           (cons 42 0)
           (cons 91 0)
           (list 10 7.262664 1.3)
           (cons 40 0)
           (cons 41 0)
           (cons 42 0)
           (cons 91 0)
           (list 10 8.067336 1.3)
           (cons 40 0)
           (cons 41 0)
           (cons 42 0)
           (cons 91 0)
           (list 10 8.2238 1.2474728)
           (cons 40 0)
           (cons 41 0)
           (cons 42 0)
           (cons 91 0)
           (list 10 8.2238 1.0731272)
           (cons 40 0)
           (cons 41 0)
           (cons 42 0)
           (cons 91 0)
           (list 10 8.067336 1.0206)
           (cons 40 0)
           (cons 41 0)
           (cons 42 0)
           (cons 91 0)
           (list 10 7.262664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.3762 -0.7445528)
           (cons 40 0)
           (cons 41 0)
           (cons 42 0)
           (cons 91 0)
           (list 10 8.3762 -0.5702072)
           (cons 40 0)
           (cons 41 0)
           (cons 42 0)
           (cons 91 0)
           (list 10 8.532664 -0.51768)
           (cons 40 0)
           (cons 41 0)
           (cons 42 0)
           (cons 91 0)
           (list 10 9.337336 -0.51768)
           (cons 40 0)
           (cons 41 0)
           (cons 42 0)
           (cons 91 0)
           (list 10 9.4938 -0.5702072)
           (cons 40 0)
           (cons 41 0)
           (cons 42 0)
           (cons 91 0)
           (list 10 9.4938 -0.7445528)
           (cons 40 0)
           (cons 41 0)
           (cons 42 0)
           (cons 91 0)
           (list 10 9.337336 -0.79708)
           (cons 40 0)
           (cons 41 0)
           (cons 42 0)
           (cons 91 0)
           (list 10 8.532664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.3762 -1.2474728)
           (cons 40 0)
           (cons 41 0)
           (cons 42 0)
           (cons 91 0)
           (list 10 8.3762 -1.0731272)
           (cons 40 0)
           (cons 41 0)
           (cons 42 0)
           (cons 91 0)
           (list 10 8.532664 -1.0206)
           (cons 40 0)
           (cons 41 0)
           (cons 42 0)
           (cons 91 0)
           (list 10 9.337336 -1.0206)
           (cons 40 0)
           (cons 41 0)
           (cons 42 0)
           (cons 91 0)
           (list 10 9.4938 -1.0731272)
           (cons 40 0)
           (cons 41 0)
           (cons 42 0)
           (cons 91 0)
           (list 10 9.4938 -1.2474728)
           (cons 40 0)
           (cons 41 0)
           (cons 42 0)
           (cons 91 0)
           (list 10 9.337336 -1.3)
           (cons 40 0)
           (cons 41 0)
           (cons 42 0)
           (cons 91 0)
           (list 10 8.532664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.3762 0.5702072)
           (cons 40 0)
           (cons 41 0)
           (cons 42 0)
           (cons 91 0)
           (list 10 8.3762 0.7445528)
           (cons 40 0)
           (cons 41 0)
           (cons 42 0)
           (cons 91 0)
           (list 10 8.532664 0.79708)
           (cons 40 0)
           (cons 41 0)
           (cons 42 0)
           (cons 91 0)
           (list 10 9.337336 0.79708)
           (cons 40 0)
           (cons 41 0)
           (cons 42 0)
           (cons 91 0)
           (list 10 9.4938 0.7445528)
           (cons 40 0)
           (cons 41 0)
           (cons 42 0)
           (cons 91 0)
           (list 10 9.4938 0.5702072)
           (cons 40 0)
           (cons 41 0)
           (cons 42 0)
           (cons 91 0)
           (list 10 9.337336 0.51768)
           (cons 40 0)
           (cons 41 0)
           (cons 42 0)
           (cons 91 0)
           (list 10 8.532664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.3762 1.0731272)
           (cons 40 0)
           (cons 41 0)
           (cons 42 0)
           (cons 91 0)
           (list 10 8.3762 1.2474728)
           (cons 40 0)
           (cons 41 0)
           (cons 42 0)
           (cons 91 0)
           (list 10 8.532664 1.3)
           (cons 40 0)
           (cons 41 0)
           (cons 42 0)
           (cons 91 0)
           (list 10 9.337336 1.3)
           (cons 40 0)
           (cons 41 0)
           (cons 42 0)
           (cons 91 0)
           (list 10 9.4938 1.2474728)
           (cons 40 0)
           (cons 41 0)
           (cons 42 0)
           (cons 91 0)
           (list 10 9.4938 1.0731272)
           (cons 40 0)
           (cons 41 0)
           (cons 42 0)
           (cons 91 0)
           (list 10 9.337336 1.0206)
           (cons 40 0)
           (cons 41 0)
           (cons 42 0)
           (cons 91 0)
           (list 10 8.532664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 1.3 0 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 8.3 1.3 0)
           (cons 50 0)
          )
         )
         (entmake
          (list
           (cons 0 "POINT")
           (cons 100 "AcDbEntity")
           (cons 67 0)
           (cons 8 "0")
           (cons 100 "AcDbPoint")
           (list 10 8.3 -1.3 0)
           (cons 50 0)
          )
         )
         (entmake
          (list
           (cons 0 "POINT")
           (cons 100 "AcDbEntity")
           (cons 67 0)
           (cons 8 "0")
           (cons 100 "AcDbPoint")
           (list 10 9.6 1.3 0)
           (cons 50 0)
          )
         )
         (entmake
          (list
           (cons 0 "POINT")
           (cons 100 "AcDbEntity")
           (cons 67 0)
           (cons 8 "0")
           (cons 100 "AcDbPoint")
           (list 10 9.6 -1.3 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 9.6 -1.3)
           (cons 40 0)
           (cons 41 0)
           (cons 42 0)
           (cons 91 0)
           (list 10 9.6 1.3)
           (cons 40 0)
           (cons 41 0)
           (cons 42 0)
           (cons 91 0)
           (list 10 0 1.3)
           (cons 40 0)
           (cons 41 0)
           (cons 42 0)
           (cons 91 0)
          )
         )
         (entmake
          (list
           (cons 0 "ATTDEF")
           (cons 100 "AcDbEntity")
           (cons 67 0)
           (cons 8 "0")
           (cons 100 "AcDbText")
           (list 10 0.6 0.56666667 0)
           (cons 40 0.2)
           (cons 1 "1.30")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 0.23333333 0)
           (cons 40 0.2)
           (cons 1 "1.30")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.1 0)
           (cons 40 0.2)
           (cons 1 "8.30")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.43333333 0)
           (cons 40 0.2)
           (cons 1 "0.00")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "TAC-1999-BTD-TRAILER1"))
        (progn
         (entmake)
         (entmake
          (list
           (cons 0 "BLOCK")
           (cons 2 "TAC-1999-BTD-TRAILER1")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.5 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.5 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 11.57 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 11.57 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.5 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 8.5 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 1.3 0 0)
           (cons 40 0.104)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 11.1 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 11.36263966 -0.26263966 0)
           (list 11 11.36263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.4712 -0.7445528)
           (cons 40 0)
           (cons 41 0)
           (cons 42 0)
           (cons 91 0)
           (list 10 8.4712 -0.5702072)
           (cons 40 0)
           (cons 41 0)
           (cons 42 0)
           (cons 91 0)
           (list 10 8.627664 -0.51768)
           (cons 40 0)
           (cons 41 0)
           (cons 42 0)
           (cons 91 0)
           (list 10 9.432336 -0.51768)
           (cons 40 0)
           (cons 41 0)
           (cons 42 0)
           (cons 91 0)
           (list 10 9.5888 -0.5702072)
           (cons 40 0)
           (cons 41 0)
           (cons 42 0)
           (cons 91 0)
           (list 10 9.5888 -0.7445528)
           (cons 40 0)
           (cons 41 0)
           (cons 42 0)
           (cons 91 0)
           (list 10 9.432336 -0.79708)
           (cons 40 0)
           (cons 41 0)
           (cons 42 0)
           (cons 91 0)
           (list 10 8.627664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.4712 -1.2474728)
           (cons 40 0)
           (cons 41 0)
           (cons 42 0)
           (cons 91 0)
           (list 10 8.4712 -1.0731272)
           (cons 40 0)
           (cons 41 0)
           (cons 42 0)
           (cons 91 0)
           (list 10 8.627664 -1.0206)
           (cons 40 0)
           (cons 41 0)
           (cons 42 0)
           (cons 91 0)
           (list 10 9.432336 -1.0206)
           (cons 40 0)
           (cons 41 0)
           (cons 42 0)
           (cons 91 0)
           (list 10 9.5888 -1.0731272)
           (cons 40 0)
           (cons 41 0)
           (cons 42 0)
           (cons 91 0)
           (list 10 9.5888 -1.2474728)
           (cons 40 0)
           (cons 41 0)
           (cons 42 0)
           (cons 91 0)
           (list 10 9.432336 -1.3)
           (cons 40 0)
           (cons 41 0)
           (cons 42 0)
           (cons 91 0)
           (list 10 8.627664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.4712 0.5702072)
           (cons 40 0)
           (cons 41 0)
           (cons 42 0)
           (cons 91 0)
           (list 10 8.4712 0.7445528)
           (cons 40 0)
           (cons 41 0)
           (cons 42 0)
           (cons 91 0)
           (list 10 8.627664 0.79708)
           (cons 40 0)
           (cons 41 0)
           (cons 42 0)
           (cons 91 0)
           (list 10 9.432336 0.79708)
           (cons 40 0)
           (cons 41 0)
           (cons 42 0)
           (cons 91 0)
           (list 10 9.5888 0.7445528)
           (cons 40 0)
           (cons 41 0)
           (cons 42 0)
           (cons 91 0)
           (list 10 9.5888 0.5702072)
           (cons 40 0)
           (cons 41 0)
           (cons 42 0)
           (cons 91 0)
           (list 10 9.432336 0.51768)
           (cons 40 0)
           (cons 41 0)
           (cons 42 0)
           (cons 91 0)
           (list 10 8.627664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.4712 1.0731272)
           (cons 40 0)
           (cons 41 0)
           (cons 42 0)
           (cons 91 0)
           (list 10 8.4712 1.2474728)
           (cons 40 0)
           (cons 41 0)
           (cons 42 0)
           (cons 91 0)
           (list 10 8.627664 1.3)
           (cons 40 0)
           (cons 41 0)
           (cons 42 0)
           (cons 91 0)
           (list 10 9.432336 1.3)
           (cons 40 0)
           (cons 41 0)
           (cons 42 0)
           (cons 91 0)
           (list 10 9.5888 1.2474728)
           (cons 40 0)
           (cons 41 0)
           (cons 42 0)
           (cons 91 0)
           (list 10 9.5888 1.0731272)
           (cons 40 0)
           (cons 41 0)
           (cons 42 0)
           (cons 91 0)
           (list 10 9.432336 1.0206)
           (cons 40 0)
           (cons 41 0)
           (cons 42 0)
           (cons 91 0)
           (list 10 8.627664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.7412 -0.7445528)
           (cons 40 0)
           (cons 41 0)
           (cons 42 0)
           (cons 91 0)
           (list 10 9.7412 -0.5702072)
           (cons 40 0)
           (cons 41 0)
           (cons 42 0)
           (cons 91 0)
           (list 10 9.897664 -0.51768)
           (cons 40 0)
           (cons 41 0)
           (cons 42 0)
           (cons 91 0)
           (list 10 10.702336 -0.51768)
           (cons 40 0)
           (cons 41 0)
           (cons 42 0)
           (cons 91 0)
           (list 10 10.8588 -0.5702072)
           (cons 40 0)
           (cons 41 0)
           (cons 42 0)
           (cons 91 0)
           (list 10 10.8588 -0.7445528)
           (cons 40 0)
           (cons 41 0)
           (cons 42 0)
           (cons 91 0)
           (list 10 10.702336 -0.79708)
           (cons 40 0)
           (cons 41 0)
           (cons 42 0)
           (cons 91 0)
           (list 10 9.897664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.7412 -1.2474728)
           (cons 40 0)
           (cons 41 0)
           (cons 42 0)
           (cons 91 0)
           (list 10 9.7412 -1.0731272)
           (cons 40 0)
           (cons 41 0)
           (cons 42 0)
           (cons 91 0)
           (list 10 9.897664 -1.0206)
           (cons 40 0)
           (cons 41 0)
           (cons 42 0)
           (cons 91 0)
           (list 10 10.702336 -1.0206)
           (cons 40 0)
           (cons 41 0)
           (cons 42 0)
           (cons 91 0)
           (list 10 10.8588 -1.0731272)
           (cons 40 0)
           (cons 41 0)
           (cons 42 0)
           (cons 91 0)
           (list 10 10.8588 -1.2474728)
           (cons 40 0)
           (cons 41 0)
           (cons 42 0)
           (cons 91 0)
           (list 10 10.702336 -1.3)
           (cons 40 0)
           (cons 41 0)
           (cons 42 0)
           (cons 91 0)
           (list 10 9.897664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.7412 0.5702072)
           (cons 40 0)
           (cons 41 0)
           (cons 42 0)
           (cons 91 0)
           (list 10 9.7412 0.7445528)
           (cons 40 0)
           (cons 41 0)
           (cons 42 0)
           (cons 91 0)
           (list 10 9.897664 0.79708)
           (cons 40 0)
           (cons 41 0)
           (cons 42 0)
           (cons 91 0)
           (list 10 10.702336 0.79708)
           (cons 40 0)
           (cons 41 0)
           (cons 42 0)
           (cons 91 0)
           (list 10 10.8588 0.7445528)
           (cons 40 0)
           (cons 41 0)
           (cons 42 0)
           (cons 91 0)
           (list 10 10.8588 0.5702072)
           (cons 40 0)
           (cons 41 0)
           (cons 42 0)
           (cons 91 0)
           (list 10 10.702336 0.51768)
           (cons 40 0)
           (cons 41 0)
           (cons 42 0)
           (cons 91 0)
           (list 10 9.897664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 9.7412 1.0731272)
           (cons 40 0)
           (cons 41 0)
           (cons 42 0)
           (cons 91 0)
           (list 10 9.7412 1.2474728)
           (cons 40 0)
           (cons 41 0)
           (cons 42 0)
           (cons 91 0)
           (list 10 9.897664 1.3)
           (cons 40 0)
           (cons 41 0)
           (cons 42 0)
           (cons 91 0)
           (list 10 10.702336 1.3)
           (cons 40 0)
           (cons 41 0)
           (cons 42 0)
           (cons 91 0)
           (list 10 10.8588 1.2474728)
           (cons 40 0)
           (cons 41 0)
           (cons 42 0)
           (cons 91 0)
           (list 10 10.8588 1.0731272)
           (cons 40 0)
           (cons 41 0)
           (cons 42 0)
           (cons 91 0)
           (list 10 10.702336 1.0206)
           (cons 40 0)
           (cons 41 0)
           (cons 42 0)
           (cons 91 0)
           (list 10 9.897664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.0112 -0.7445528)
           (cons 40 0)
           (cons 41 0)
           (cons 42 0)
           (cons 91 0)
           (list 10 11.0112 -0.5702072)
           (cons 40 0)
           (cons 41 0)
           (cons 42 0)
           (cons 91 0)
           (list 10 11.167664 -0.51768)
           (cons 40 0)
           (cons 41 0)
           (cons 42 0)
           (cons 91 0)
           (list 10 11.972336 -0.51768)
           (cons 40 0)
           (cons 41 0)
           (cons 42 0)
           (cons 91 0)
           (list 10 12.1288 -0.5702072)
           (cons 40 0)
           (cons 41 0)
           (cons 42 0)
           (cons 91 0)
           (list 10 12.1288 -0.7445528)
           (cons 40 0)
           (cons 41 0)
           (cons 42 0)
           (cons 91 0)
           (list 10 11.972336 -0.79708)
           (cons 40 0)
           (cons 41 0)
           (cons 42 0)
           (cons 91 0)
           (list 10 11.167664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.0112 -1.2474728)
           (cons 40 0)
           (cons 41 0)
           (cons 42 0)
           (cons 91 0)
           (list 10 11.0112 -1.0731272)
           (cons 40 0)
           (cons 41 0)
           (cons 42 0)
           (cons 91 0)
           (list 10 11.167664 -1.0206)
           (cons 40 0)
           (cons 41 0)
           (cons 42 0)
           (cons 91 0)
           (list 10 11.972336 -1.0206)
           (cons 40 0)
           (cons 41 0)
           (cons 42 0)
           (cons 91 0)
           (list 10 12.1288 -1.0731272)
           (cons 40 0)
           (cons 41 0)
           (cons 42 0)
           (cons 91 0)
           (list 10 12.1288 -1.2474728)
           (cons 40 0)
           (cons 41 0)
           (cons 42 0)
           (cons 91 0)
           (list 10 11.972336 -1.3)
           (cons 40 0)
           (cons 41 0)
           (cons 42 0)
           (cons 91 0)
           (list 10 11.167664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.0112 0.5702072)
           (cons 40 0)
           (cons 41 0)
           (cons 42 0)
           (cons 91 0)
           (list 10 11.0112 0.7445528)
           (cons 40 0)
           (cons 41 0)
           (cons 42 0)
           (cons 91 0)
           (list 10 11.167664 0.79708)
           (cons 40 0)
           (cons 41 0)
           (cons 42 0)
           (cons 91 0)
           (list 10 11.972336 0.79708)
           (cons 40 0)
           (cons 41 0)
           (cons 42 0)
           (cons 91 0)
           (list 10 12.1288 0.7445528)
           (cons 40 0)
           (cons 41 0)
           (cons 42 0)
           (cons 91 0)
           (list 10 12.1288 0.5702072)
           (cons 40 0)
           (cons 41 0)
           (cons 42 0)
           (cons 91 0)
           (list 10 11.972336 0.51768)
           (cons 40 0)
           (cons 41 0)
           (cons 42 0)
           (cons 91 0)
           (list 10 11.167664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 11.0112 1.0731272)
           (cons 40 0)
           (cons 41 0)
           (cons 42 0)
           (cons 91 0)
           (list 10 11.0112 1.2474728)
           (cons 40 0)
           (cons 41 0)
           (cons 42 0)
           (cons 91 0)
           (list 10 11.167664 1.3)
           (cons 40 0)
           (cons 41 0)
           (cons 42 0)
           (cons 91 0)
           (list 10 11.972336 1.3)
           (cons 40 0)
           (cons 41 0)
           (cons 42 0)
           (cons 91 0)
           (list 10 12.1288 1.2474728)
           (cons 40 0)
           (cons 41 0)
           (cons 42 0)
           (cons 91 0)
           (list 10 12.1288 1.0731272)
           (cons 40 0)
           (cons 41 0)
           (cons 42 0)
           (cons 91 0)
           (list 10 11.972336 1.0206)
           (cons 40 0)
           (cons 41 0)
           (cons 42 0)
           (cons 91 0)
           (list 10 11.167664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 1.3 0 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 10.3 1.3 0)
           (cons 50 0)
          )
         )
         (entmake
          (list
           (cons 0 "POINT")
           (cons 100 "AcDbEntity")
           (cons 67 0)
           (cons 8 "0")
           (cons 100 "AcDbPoint")
           (list 10 10.3 -1.3 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 11.57 -1.3)
           (cons 40 0)
           (cons 41 0)
           (cons 42 0)
           (cons 91 0)
           (list 10 11.57 1.3)
           (cons 40 0)
           (cons 41 0)
           (cons 42 0)
           (cons 91 0)
           (list 10 0 1.3)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 11.1 0 0)
           (cons 50 0)
          )
         )
         (entmake
          (list
           (cons 0 "ATTDEF")
           (cons 100 "AcDbEntity")
           (cons 67 0)
           (cons 8 "0")
           (cons 100 "AcDbText")
           (list 10 0.6 0.56666667 0)
           (cons 40 0.2)
           (cons 1 "1.30")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 0.23333333 0)
           (cons 40 0.2)
           (cons 1 "1.30")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.1 0)
           (cons 40 0.2)
           (cons 1 "10.30")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.43333333 0)
           (cons 40 0.2)
           (cons 1 "11.10")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.6 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "TAC-1999-BTD-TRUCK"))
        (progn
         (entmake)
         (entmake
          (list
           (cons 0 "BLOCK")
           (cons 2 "TAC-1999-BTD-TRUCK")
           (cons 70 2)
           (cons 4 "")
           (list 10 0 0 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.535 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.535 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 6.9 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 7.16263966 -0.26263966 0)
           (list 11 7.16263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.7062 -0.7445528)
           (cons 40 0)
           (cons 41 0)
           (cons 42 0)
           (cons 91 0)
           (list 10 5.7062 -0.5702072)
           (cons 40 0)
           (cons 41 0)
           (cons 42 0)
           (cons 91 0)
           (list 10 5.862664 -0.51768)
           (cons 40 0)
           (cons 41 0)
           (cons 42 0)
           (cons 91 0)
           (list 10 6.667336 -0.51768)
           (cons 40 0)
           (cons 41 0)
           (cons 42 0)
           (cons 91 0)
           (list 10 6.8238 -0.5702072)
           (cons 40 0)
           (cons 41 0)
           (cons 42 0)
           (cons 91 0)
           (list 10 6.8238 -0.7445528)
           (cons 40 0)
           (cons 41 0)
           (cons 42 0)
           (cons 91 0)
           (list 10 6.667336 -0.79708)
           (cons 40 0)
           (cons 41 0)
           (cons 42 0)
           (cons 91 0)
           (list 10 5.862664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.7062 -1.2474728)
           (cons 40 0)
           (cons 41 0)
           (cons 42 0)
           (cons 91 0)
           (list 10 5.7062 -1.0731272)
           (cons 40 0)
           (cons 41 0)
           (cons 42 0)
           (cons 91 0)
           (list 10 5.862664 -1.0206)
           (cons 40 0)
           (cons 41 0)
           (cons 42 0)
           (cons 91 0)
           (list 10 6.667336 -1.0206)
           (cons 40 0)
           (cons 41 0)
           (cons 42 0)
           (cons 91 0)
           (list 10 6.8238 -1.0731272)
           (cons 40 0)
           (cons 41 0)
           (cons 42 0)
           (cons 91 0)
           (list 10 6.8238 -1.2474728)
           (cons 40 0)
           (cons 41 0)
           (cons 42 0)
           (cons 91 0)
           (list 10 6.667336 -1.3)
           (cons 40 0)
           (cons 41 0)
           (cons 42 0)
           (cons 91 0)
           (list 10 5.862664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.7062 0.5702072)
           (cons 40 0)
           (cons 41 0)
           (cons 42 0)
           (cons 91 0)
           (list 10 5.7062 0.7445528)
           (cons 40 0)
           (cons 41 0)
           (cons 42 0)
           (cons 91 0)
           (list 10 5.862664 0.79708)
           (cons 40 0)
           (cons 41 0)
           (cons 42 0)
           (cons 91 0)
           (list 10 6.667336 0.79708)
           (cons 40 0)
           (cons 41 0)
           (cons 42 0)
           (cons 91 0)
           (list 10 6.8238 0.7445528)
           (cons 40 0)
           (cons 41 0)
           (cons 42 0)
           (cons 91 0)
           (list 10 6.8238 0.5702072)
           (cons 40 0)
           (cons 41 0)
           (cons 42 0)
           (cons 91 0)
           (list 10 6.667336 0.51768)
           (cons 40 0)
           (cons 41 0)
           (cons 42 0)
           (cons 91 0)
           (list 10 5.862664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.7062 1.0731272)
           (cons 40 0)
           (cons 41 0)
           (cons 42 0)
           (cons 91 0)
           (list 10 5.7062 1.2474728)
           (cons 40 0)
           (cons 41 0)
           (cons 42 0)
           (cons 91 0)
           (list 10 5.862664 1.3)
           (cons 40 0)
           (cons 41 0)
           (cons 42 0)
           (cons 91 0)
           (list 10 6.667336 1.3)
           (cons 40 0)
           (cons 41 0)
           (cons 42 0)
           (cons 91 0)
           (list 10 6.8238 1.2474728)
           (cons 40 0)
           (cons 41 0)
           (cons 42 0)
           (cons 91 0)
           (list 10 6.8238 1.0731272)
           (cons 40 0)
           (cons 41 0)
           (cons 42 0)
           (cons 91 0)
           (list 10 6.667336 1.0206)
           (cons 40 0)
           (cons 41 0)
           (cons 42 0)
           (cons 91 0)
           (list 10 5.862664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.9762 -0.7445528)
           (cons 40 0)
           (cons 41 0)
           (cons 42 0)
           (cons 91 0)
           (list 10 6.9762 -0.5702072)
           (cons 40 0)
           (cons 41 0)
           (cons 42 0)
           (cons 91 0)
           (list 10 7.132664 -0.51768)
           (cons 40 0)
           (cons 41 0)
           (cons 42 0)
           (cons 91 0)
           (list 10 7.937336 -0.51768)
           (cons 40 0)
           (cons 41 0)
           (cons 42 0)
           (cons 91 0)
           (list 10 8.0938 -0.5702072)
           (cons 40 0)
           (cons 41 0)
           (cons 42 0)
           (cons 91 0)
           (list 10 8.0938 -0.7445528)
           (cons 40 0)
           (cons 41 0)
           (cons 42 0)
           (cons 91 0)
           (list 10 7.937336 -0.79708)
           (cons 40 0)
           (cons 41 0)
           (cons 42 0)
           (cons 91 0)
           (list 10 7.132664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.9762 -1.2474728)
           (cons 40 0)
           (cons 41 0)
           (cons 42 0)
           (cons 91 0)
           (list 10 6.9762 -1.0731272)
           (cons 40 0)
           (cons 41 0)
           (cons 42 0)
           (cons 91 0)
           (list 10 7.132664 -1.0206)
           (cons 40 0)
           (cons 41 0)
           (cons 42 0)
           (cons 91 0)
           (list 10 7.937336 -1.0206)
           (cons 40 0)
           (cons 41 0)
           (cons 42 0)
           (cons 91 0)
           (list 10 8.0938 -1.0731272)
           (cons 40 0)
           (cons 41 0)
           (cons 42 0)
           (cons 91 0)
           (list 10 8.0938 -1.2474728)
           (cons 40 0)
           (cons 41 0)
           (cons 42 0)
           (cons 91 0)
           (list 10 7.937336 -1.3)
           (cons 40 0)
           (cons 41 0)
           (cons 42 0)
           (cons 91 0)
           (list 10 7.132664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.9762 0.5702072)
           (cons 40 0)
           (cons 41 0)
           (cons 42 0)
           (cons 91 0)
           (list 10 6.9762 0.7445528)
           (cons 40 0)
           (cons 41 0)
           (cons 42 0)
           (cons 91 0)
           (list 10 7.132664 0.79708)
           (cons 40 0)
           (cons 41 0)
           (cons 42 0)
           (cons 91 0)
           (list 10 7.937336 0.79708)
           (cons 40 0)
           (cons 41 0)
           (cons 42 0)
           (cons 91 0)
           (list 10 8.0938 0.7445528)
           (cons 40 0)
           (cons 41 0)
           (cons 42 0)
           (cons 91 0)
           (list 10 8.0938 0.5702072)
           (cons 40 0)
           (cons 41 0)
           (cons 42 0)
           (cons 91 0)
           (list 10 7.937336 0.51768)
           (cons 40 0)
           (cons 41 0)
           (cons 42 0)
           (cons 91 0)
           (list 10 7.132664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.9762 1.0731272)
           (cons 40 0)
           (cons 41 0)
           (cons 42 0)
           (cons 91 0)
           (list 10 6.9762 1.2474728)
           (cons 40 0)
           (cons 41 0)
           (cons 42 0)
           (cons 91 0)
           (list 10 7.132664 1.3)
           (cons 40 0)
           (cons 41 0)
           (cons 42 0)
           (cons 91 0)
           (list 10 7.937336 1.3)
           (cons 40 0)
           (cons 41 0)
           (cons 42 0)
           (cons 91 0)
           (list 10 8.0938 1.2474728)
           (cons 40 0)
           (cons 41 0)
           (cons 42 0)
           (cons 91 0)
           (list 10 8.0938 1.0731272)
           (cons 40 0)
           (cons 41 0)
           (cons 42 0)
           (cons 91 0)
           (list 10 7.937336 1.0206)
           (cons 40 0)
           (cons 41 0)
           (cons 42 0)
           (cons 91 0)
           (list 10 7.132664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0.8 0 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0.8 1.3 0)
           (cons 50 0)
          )
         )
         (entmake
          (list
           (cons 0 "POINT")
           (cons 100 "AcDbEntity")
           (cons 67 0)
           (cons 8 "0")
           (cons 100 "AcDbPoint")
           (list 10 0.8 -1.3 0)
           (cons 50 0)
          )
         )
         (entmake
          (list
           (cons 0 "POINT")
           (cons 100 "AcDbEntity")
           (cons 67 0)
           (cons 8 "0")
           (cons 100 "AcDbPoint")
           (list 10 6.9 -1.3 0)
           (cons 50 0)
          )
         )
         (entmake
          (list
           (cons 0 "POINT")
           (cons 100 "AcDbEntity")
           (cons 67 0)
           (cons 8 "0")
           (cons 100 "AcDbPoint")
           (list 10 6.9 1.3 0)
           (cons 50 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 7.535 -1.3)
           (cons 40 0)
           (cons 41 0)
           (cons 42 0)
           (cons 91 0)
           (list 10 7.535 1.3)
           (cons 40 0)
           (cons 41 0)
           (cons 42 0)
           (cons 91 0)
           (list 10 0 1.3)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 6.9 0 0)
           (cons 50 0)
          )
         )
         (entmake
          (list
           (cons 0 "ATTDEF")
           (cons 100 "AcDbEntity")
           (cons 67 0)
           (cons 8 "0")
           (cons 100 "AcDbText")
           (list 10 0.1 0.56666667 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 0.23333333 0)
           (cons 40 0.2)
           (cons 1 "0.80")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.1 0)
           (cons 40 0.2)
           (cons 1 "6.90")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.43333333 0)
           (cons 40 0.2)
           (cons 1 "6.90")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.76666667 0)
           (cons 40 0.2)
           (cons 1 "29.50")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelLeftM1")
           (list 10 0.8 -1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM1")
           (list 10 0.8 1.0206 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "TAC-1999-B-12"))
        (progn
         (entmake)
         (entmake
          (list
           (cons 0 "BLOCK")
           (cons 2 "TAC-1999-B-12")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.2)
           (cons 40 0)
           (cons 41 0)
           (cons 42 0)
           (cons 91 0)
           (list 10 12.2 -1.2)
           (cons 40 0)
           (cons 41 0)
           (cons 42 0)
           (cons 91 0)
           (list 10 12.2 1.2)
           (cons 40 0)
           (cons 41 0)
           (cons 42 0)
           (cons 91 0)
           (list 10 0 1.2)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 12.2 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 12.2 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.892 -1.152248)
           (cons 40 0)
           (cons 41 0)
           (cons 42 0)
           (cons 91 0)
           (list 10 8.892 -0.993752)
           (cons 40 0)
           (cons 41 0)
           (cons 42 0)
           (cons 91 0)
           (list 10 9.03424 -0.946)
           (cons 40 0)
           (cons 41 0)
           (cons 42 0)
           (cons 91 0)
           (list 10 9.76576 -0.946)
           (cons 40 0)
           (cons 41 0)
           (cons 42 0)
           (cons 91 0)
           (list 10 9.908 -0.993752)
           (cons 40 0)
           (cons 41 0)
           (cons 42 0)
           (cons 91 0)
           (list 10 9.908 -1.152248)
           (cons 40 0)
           (cons 41 0)
           (cons 42 0)
           (cons 91 0)
           (list 10 9.76576 -1.2)
           (cons 40 0)
           (cons 41 0)
           (cons 42 0)
           (cons 91 0)
           (list 10 9.03424 -1.2)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.892 0.993752)
           (cons 40 0)
           (cons 41 0)
           (cons 42 0)
           (cons 91 0)
           (list 10 8.892 1.152248)
           (cons 40 0)
           (cons 41 0)
           (cons 42 0)
           (cons 91 0)
           (list 10 9.03424 1.2)
           (cons 40 0)
           (cons 41 0)
           (cons 42 0)
           (cons 91 0)
           (list 10 9.76576 1.2)
           (cons 40 0)
           (cons 41 0)
           (cons 42 0)
           (cons 91 0)
           (list 10 9.908 1.152248)
           (cons 40 0)
           (cons 41 0)
           (cons 42 0)
           (cons 91 0)
           (list 10 9.908 0.993752)
           (cons 40 0)
           (cons 41 0)
           (cons 42 0)
           (cons 91 0)
           (list 10 9.76576 0.946)
           (cons 40 0)
           (cons 41 0)
           (cons 42 0)
           (cons 91 0)
           (list 10 9.03424 0.946)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -1.2 0)
           (cons 50 0)
          )
         )
         (entmake
          (list
           (cons 0 "POINT")
           (cons 100 "AcDbEntity")
           (cons 67 0)
           (cons 8 "0")
           (cons 100 "AcDbPoint")
           (list 10 0 1.2 0)
           (cons 50 0)
          )
         )
         (entmake
          (list
           (cons 0 "POINT")
           (cons 100 "AcDbEntity")
           (cons 67 0)
           (cons 8 "0")
           (cons 100 "AcDbPoint")
           (list 10 12.2 1.2 0)
           (cons 50 0)
          )
         )
         (entmake
          (list
           (cons 0 "POINT")
           (cons 100 "AcDbEntity")
           (cons 67 0)
           (cons 8 "0")
           (cons 100 "AcDbPoint")
           (list 10 12.2 -1.2 0)
           (cons 50 0)
          )
         )
         (entmake
          (list
           (cons 0 "POINT")
           (cons 100 "AcDbEntity")
           (cons 67 0)
           (cons 8 "0")
           (cons 100 "AcDbPoint")
           (list 10 2.2 0 0)
           (cons 50 0)
          )
         )
         (entmake
          (list
           (cons 0 "POINT")
           (cons 100 "AcDbEntity")
           (cons 67 0)
           (cons 8 "0")
           (cons 100 "AcDbPoint")
           (list 10 2.2 1.2 0)
           (cons 50 0)
          )
         )
         (entmake
          (list
           (cons 0 "POINT")
           (cons 100 "AcDbEntity")
           (cons 67 0)
           (cons 8 "0")
           (cons 100 "AcDbPoint")
           (list 10 9.4 1.2 0)
           (cons 50 0)
          )
         )
         (entmake
          (list
           (cons 0 "POINT")
           (cons 100 "AcDbEntity")
           (cons 67 0)
           (cons 8 "0")
           (cons 100 "AcDbPoint")
           (list 10 9.4 -1.2 0)
           (cons 50 0)
          )
         )
         (entmake
          (list
           (cons 0 "POINT")
           (cons 100 "AcDbEntity")
           (cons 67 0)
           (cons 8 "0")
           (cons 100 "AcDbPoint")
           (list 10 2.2 -1.2 0)
           (cons 50 0)
          )
         )
         (entmake
          (list
           (cons 0 "ATTDEF")
           (cons 100 "AcDbEntity")
           (cons 67 0)
           (cons 8 "0")
           (cons 100 "AcDbText")
           (list 10 1.5 0.56666667 0)
           (cons 40 0.2)
           (cons 1 "2.200")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.5 0.23333333 0)
           (cons 40 0.2)
           (cons 1 "2.200")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.5 -0.1 0)
           (cons 40 0.2)
           (cons 1 "9.400")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.5 -0.43333333 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 1.5 -0.76666667 0)
           (cons 40 0.2)
           (cons 1 "37.1")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelLeftM2")
           (list 10 2.2 -0.946 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelRightM2")
           (list 10 2.2 0.946 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "TAC-1999-ATD-TRAILER2"))
        (progn
         (entmake)
         (entmake
          (list
           (cons 0 "BLOCK")
           (cons 2 "TAC-1999-ATD-TRAILER2")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 9.4 -1.3)
           (cons 40 0)
           (cons 41 0)
           (cons 42 0)
           (cons 91 0)
           (list 10 9.4 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.4 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.4 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 1 0 0)
           (cons 40 0.17333333)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.7062 -0.7445528)
           (cons 40 0)
           (cons 41 0)
           (cons 42 0)
           (cons 91 0)
           (list 10 6.7062 -0.5702072)
           (cons 40 0)
           (cons 41 0)
           (cons 42 0)
           (cons 91 0)
           (list 10 6.862664 -0.51768)
           (cons 40 0)
           (cons 41 0)
           (cons 42 0)
           (cons 91 0)
           (list 10 7.667336 -0.51768)
           (cons 40 0)
           (cons 41 0)
           (cons 42 0)
           (cons 91 0)
           (list 10 7.8238 -0.5702072)
           (cons 40 0)
           (cons 41 0)
           (cons 42 0)
           (cons 91 0)
           (list 10 7.8238 -0.7445528)
           (cons 40 0)
           (cons 41 0)
           (cons 42 0)
           (cons 91 0)
           (list 10 7.667336 -0.79708)
           (cons 40 0)
           (cons 41 0)
           (cons 42 0)
           (cons 91 0)
           (list 10 6.862664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.7062 -1.2474728)
           (cons 40 0)
           (cons 41 0)
           (cons 42 0)
           (cons 91 0)
           (list 10 6.7062 -1.0731272)
           (cons 40 0)
           (cons 41 0)
           (cons 42 0)
           (cons 91 0)
           (list 10 6.862664 -1.0206)
           (cons 40 0)
           (cons 41 0)
           (cons 42 0)
           (cons 91 0)
           (list 10 7.667336 -1.0206)
           (cons 40 0)
           (cons 41 0)
           (cons 42 0)
           (cons 91 0)
           (list 10 7.8238 -1.0731272)
           (cons 40 0)
           (cons 41 0)
           (cons 42 0)
           (cons 91 0)
           (list 10 7.8238 -1.2474728)
           (cons 40 0)
           (cons 41 0)
           (cons 42 0)
           (cons 91 0)
           (list 10 7.667336 -1.3)
           (cons 40 0)
           (cons 41 0)
           (cons 42 0)
           (cons 91 0)
           (list 10 6.862664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.7062 0.5702072)
           (cons 40 0)
           (cons 41 0)
           (cons 42 0)
           (cons 91 0)
           (list 10 6.7062 0.7445528)
           (cons 40 0)
           (cons 41 0)
           (cons 42 0)
           (cons 91 0)
           (list 10 6.862664 0.79708)
           (cons 40 0)
           (cons 41 0)
           (cons 42 0)
           (cons 91 0)
           (list 10 7.667336 0.79708)
           (cons 40 0)
           (cons 41 0)
           (cons 42 0)
           (cons 91 0)
           (list 10 7.8238 0.7445528)
           (cons 40 0)
           (cons 41 0)
           (cons 42 0)
           (cons 91 0)
           (list 10 7.8238 0.5702072)
           (cons 40 0)
           (cons 41 0)
           (cons 42 0)
           (cons 91 0)
           (list 10 7.667336 0.51768)
           (cons 40 0)
           (cons 41 0)
           (cons 42 0)
           (cons 91 0)
           (list 10 6.862664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.7062 1.0731272)
           (cons 40 0)
           (cons 41 0)
           (cons 42 0)
           (cons 91 0)
           (list 10 6.7062 1.2474728)
           (cons 40 0)
           (cons 41 0)
           (cons 42 0)
           (cons 91 0)
           (list 10 6.862664 1.3)
           (cons 40 0)
           (cons 41 0)
           (cons 42 0)
           (cons 91 0)
           (list 10 7.667336 1.3)
           (cons 40 0)
           (cons 41 0)
           (cons 42 0)
           (cons 91 0)
           (list 10 7.8238 1.2474728)
           (cons 40 0)
           (cons 41 0)
           (cons 42 0)
           (cons 91 0)
           (list 10 7.8238 1.0731272)
           (cons 40 0)
           (cons 41 0)
           (cons 42 0)
           (cons 91 0)
           (list 10 7.667336 1.0206)
           (cons 40 0)
           (cons 41 0)
           (cons 42 0)
           (cons 91 0)
           (list 10 6.862664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.9762 -0.7445528)
           (cons 40 0)
           (cons 41 0)
           (cons 42 0)
           (cons 91 0)
           (list 10 7.9762 -0.5702072)
           (cons 40 0)
           (cons 41 0)
           (cons 42 0)
           (cons 91 0)
           (list 10 8.132664 -0.51768)
           (cons 40 0)
           (cons 41 0)
           (cons 42 0)
           (cons 91 0)
           (list 10 8.937336 -0.51768)
           (cons 40 0)
           (cons 41 0)
           (cons 42 0)
           (cons 91 0)
           (list 10 9.0938 -0.5702072)
           (cons 40 0)
           (cons 41 0)
           (cons 42 0)
           (cons 91 0)
           (list 10 9.0938 -0.7445528)
           (cons 40 0)
           (cons 41 0)
           (cons 42 0)
           (cons 91 0)
           (list 10 8.937336 -0.79708)
           (cons 40 0)
           (cons 41 0)
           (cons 42 0)
           (cons 91 0)
           (list 10 8.132664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.9762 -1.2474728)
           (cons 40 0)
           (cons 41 0)
           (cons 42 0)
           (cons 91 0)
           (list 10 7.9762 -1.0731272)
           (cons 40 0)
           (cons 41 0)
           (cons 42 0)
           (cons 91 0)
           (list 10 8.132664 -1.0206)
           (cons 40 0)
           (cons 41 0)
           (cons 42 0)
           (cons 91 0)
           (list 10 8.937336 -1.0206)
           (cons 40 0)
           (cons 41 0)
           (cons 42 0)
           (cons 91 0)
           (list 10 9.0938 -1.0731272)
           (cons 40 0)
           (cons 41 0)
           (cons 42 0)
           (cons 91 0)
           (list 10 9.0938 -1.2474728)
           (cons 40 0)
           (cons 41 0)
           (cons 42 0)
           (cons 91 0)
           (list 10 8.937336 -1.3)
           (cons 40 0)
           (cons 41 0)
           (cons 42 0)
           (cons 91 0)
           (list 10 8.132664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.9762 0.5702072)
           (cons 40 0)
           (cons 41 0)
           (cons 42 0)
           (cons 91 0)
           (list 10 7.9762 0.7445528)
           (cons 40 0)
           (cons 41 0)
           (cons 42 0)
           (cons 91 0)
           (list 10 8.132664 0.79708)
           (cons 40 0)
           (cons 41 0)
           (cons 42 0)
           (cons 91 0)
           (list 10 8.937336 0.79708)
           (cons 40 0)
           (cons 41 0)
           (cons 42 0)
           (cons 91 0)
           (list 10 9.0938 0.7445528)
           (cons 40 0)
           (cons 41 0)
           (cons 42 0)
           (cons 91 0)
           (list 10 9.0938 0.5702072)
           (cons 40 0)
           (cons 41 0)
           (cons 42 0)
           (cons 91 0)
           (list 10 8.937336 0.51768)
           (cons 40 0)
           (cons 41 0)
           (cons 42 0)
           (cons 91 0)
           (list 10 8.132664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.9762 1.0731272)
           (cons 40 0)
           (cons 41 0)
           (cons 42 0)
           (cons 91 0)
           (list 10 7.9762 1.2474728)
           (cons 40 0)
           (cons 41 0)
           (cons 42 0)
           (cons 91 0)
           (list 10 8.132664 1.3)
           (cons 40 0)
           (cons 41 0)
           (cons 42 0)
           (cons 91 0)
           (list 10 8.937336 1.3)
           (cons 40 0)
           (cons 41 0)
           (cons 42 0)
           (cons 91 0)
           (list 10 9.0938 1.2474728)
           (cons 40 0)
           (cons 41 0)
           (cons 42 0)
           (cons 91 0)
           (list 10 9.0938 1.0731272)
           (cons 40 0)
           (cons 41 0)
           (cons 42 0)
           (cons 91 0)
           (list 10 8.937336 1.0206)
           (cons 40 0)
           (cons 41 0)
           (cons 42 0)
           (cons 91 0)
           (list 10 8.132664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 9.4 -1.3 0)
           (cons 50 0)
          )
         )
         (entmake
          (list
           (cons 0 "POINT")
           (cons 100 "AcDbEntity")
           (cons 67 0)
           (cons 8 "0")
           (cons 100 "AcDbPoint")
           (list 10 9.4 1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 1 0 0)
           (cons 50 0)
          )
         )
         (entmake
          (list
           (cons 0 "POINT")
           (cons 100 "AcDbEntity")
           (cons 67 0)
           (cons 8 "0")
           (cons 100 "AcDbPoint")
           (list 10 7.9 0 0)
           (cons 50 0)
          )
         )
         (entmake
          (list
           (cons 0 "POINT")
           (cons 100 "AcDbEntity")
           (cons 67 0)
           (cons 8 "0")
           (cons 100 "AcDbPoint")
           (list 10 7.9 1.3 0)
           (cons 50 0)
          )
         )
         (entmake
          (list
           (cons 0 "POINT")
           (cons 100 "AcDbEntity")
           (cons 67 0)
           (cons 8 "0")
           (cons 100 "AcDbPoint")
           (list 10 7.9 -1.3 0)
           (cons 50 0)
          )
         )
         (entmake
          (list
           (cons 0 "ATTDEF")
           (cons 100 "AcDbEntity")
           (cons 67 0)
           (cons 8 "0")
           (cons 100 "AcDbText")
           (list 10 0.3 0.56666667 0)
           (cons 40 0.2)
           (cons 1 "1.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 0.23333333 0)
           (cons 40 0.2)
           (cons 1 "1.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.1 0)
           (cons 40 0.2)
           (cons 1 "7.900")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.43333333 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "TAC-1999-ATD-PUP"))
        (progn
         (entmake)
         (entmake
          (list
           (cons 0 "BLOCK")
           (cons 2 "TAC-1999-ATD-PUP")
           (cons 70 2)
           (cons 4 "")
           (list 10 0 0 0)
          )
         )
         (entmake
          (list
           (cons 0 "POLYLINE")
           (cons 100 "AcDbEntity")
           (cons 67 0)
           (cons 8 "Defpoints")
           (cons 100 "AcDb2dPolyline")
           (cons 66 1)
           (list 10 0 0 0)
           (cons 70 129)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "Defpoints")
           (cons 100 "AcDbVertex")
           (cons 100 "AcDb2dVertex")
           (list 10 0 0 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 2.1 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 2.1 1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "Defpoints")
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 2.1 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.17333333)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 -0.7445528)
           (cons 40 0)
           (cons 41 0)
           (cons 42 0)
           (cons 91 0)
           (list 10 1.5412 -0.5702072)
           (cons 40 0)
           (cons 41 0)
           (cons 42 0)
           (cons 91 0)
           (list 10 1.697664 -0.51768)
           (cons 40 0)
           (cons 41 0)
           (cons 42 0)
           (cons 91 0)
           (list 10 2.502336 -0.51768)
           (cons 40 0)
           (cons 41 0)
           (cons 42 0)
           (cons 91 0)
           (list 10 2.6588 -0.5702072)
           (cons 40 0)
           (cons 41 0)
           (cons 42 0)
           (cons 91 0)
           (list 10 2.6588 -0.7445528)
           (cons 40 0)
           (cons 41 0)
           (cons 42 0)
           (cons 91 0)
           (list 10 2.502336 -0.79708)
           (cons 40 0)
           (cons 41 0)
           (cons 42 0)
           (cons 91 0)
           (list 10 1.697664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 -1.2474728)
           (cons 40 0)
           (cons 41 0)
           (cons 42 0)
           (cons 91 0)
           (list 10 1.5412 -1.0731272)
           (cons 40 0)
           (cons 41 0)
           (cons 42 0)
           (cons 91 0)
           (list 10 1.697664 -1.0206)
           (cons 40 0)
           (cons 41 0)
           (cons 42 0)
           (cons 91 0)
           (list 10 2.502336 -1.0206)
           (cons 40 0)
           (cons 41 0)
           (cons 42 0)
           (cons 91 0)
           (list 10 2.6588 -1.0731272)
           (cons 40 0)
           (cons 41 0)
           (cons 42 0)
           (cons 91 0)
           (list 10 2.6588 -1.2474728)
           (cons 40 0)
           (cons 41 0)
           (cons 42 0)
           (cons 91 0)
           (list 10 2.502336 -1.3)
           (cons 40 0)
           (cons 41 0)
           (cons 42 0)
           (cons 91 0)
           (list 10 1.697664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 0.5702072)
           (cons 40 0)
           (cons 41 0)
           (cons 42 0)
           (cons 91 0)
           (list 10 1.5412 0.7445528)
           (cons 40 0)
           (cons 41 0)
           (cons 42 0)
           (cons 91 0)
           (list 10 1.697664 0.79708)
           (cons 40 0)
           (cons 41 0)
           (cons 42 0)
           (cons 91 0)
           (list 10 2.502336 0.79708)
           (cons 40 0)
           (cons 41 0)
           (cons 42 0)
           (cons 91 0)
           (list 10 2.6588 0.7445528)
           (cons 40 0)
           (cons 41 0)
           (cons 42 0)
           (cons 91 0)
           (list 10 2.6588 0.5702072)
           (cons 40 0)
           (cons 41 0)
           (cons 42 0)
           (cons 91 0)
           (list 10 2.502336 0.51768)
           (cons 40 0)
           (cons 41 0)
           (cons 42 0)
           (cons 91 0)
           (list 10 1.697664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 1.5412 1.0731272)
           (cons 40 0)
           (cons 41 0)
           (cons 42 0)
           (cons 91 0)
           (list 10 1.5412 1.2474728)
           (cons 40 0)
           (cons 41 0)
           (cons 42 0)
           (cons 91 0)
           (list 10 1.697664 1.3)
           (cons 40 0)
           (cons 41 0)
           (cons 42 0)
           (cons 91 0)
           (list 10 2.502336 1.3)
           (cons 40 0)
           (cons 41 0)
           (cons 42 0)
           (cons 91 0)
           (list 10 2.6588 1.2474728)
           (cons 40 0)
           (cons 41 0)
           (cons 42 0)
           (cons 91 0)
           (list 10 2.6588 1.0731272)
           (cons 40 0)
           (cons 41 0)
           (cons 42 0)
           (cons 91 0)
           (list 10 2.502336 1.0206)
           (cons 40 0)
           (cons 41 0)
           (cons 42 0)
           (cons 91 0)
           (list 10 1.697664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "POINT")
           (cons 100 "AcDbEntity")
           (cons 67 0)
           (cons 8 "0")
           (cons 100 "AcDbPoint")
           (list 10 2.1 0 0)
           (cons 50 0)
          )
         )
         (entmake
          (list
           (cons 0 "POINT")
           (cons 100 "AcDbEntity")
           (cons 67 0)
           (cons 8 "0")
           (cons 100 "AcDbPoint")
           (list 10 2.1 1.3 0)
           (cons 50 0)
          )
         )
         (entmake
          (list
           (cons 0 "POINT")
           (cons 100 "AcDbEntity")
           (cons 67 0)
           (cons 8 "0")
           (cons 100 "AcDbPoint")
           (list 10 2.1 -1.3 0)
           (cons 50 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "2.100")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "2.100")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake (list (cons 0 "ENDBLK")))
        )
       )
       ((= (strcase BLKNAME) (strcase "TAC-1999-ATD-TRAILER1"))
        (progn
         (entmake)
         (entmake
          (list
           (cons 0 "BLOCK")
           (cons 2 "TAC-1999-ATD-TRAILER1")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 9.1 -1.3)
           (cons 40 0)
           (cons 41 0)
           (cons 42 0)
           (cons 91 0)
           (list 10 9.1 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.1 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.1 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 1 0 0)
           (cons 40 0.104)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.7062 -0.7445528)
           (cons 40 0)
           (cons 41 0)
           (cons 42 0)
           (cons 91 0)
           (list 10 6.7062 -0.5702072)
           (cons 40 0)
           (cons 41 0)
           (cons 42 0)
           (cons 91 0)
           (list 10 6.862664 -0.51768)
           (cons 40 0)
           (cons 41 0)
           (cons 42 0)
           (cons 91 0)
           (list 10 7.667336 -0.51768)
           (cons 40 0)
           (cons 41 0)
           (cons 42 0)
           (cons 91 0)
           (list 10 7.8238 -0.5702072)
           (cons 40 0)
           (cons 41 0)
           (cons 42 0)
           (cons 91 0)
           (list 10 7.8238 -0.7445528)
           (cons 40 0)
           (cons 41 0)
           (cons 42 0)
           (cons 91 0)
           (list 10 7.667336 -0.79708)
           (cons 40 0)
           (cons 41 0)
           (cons 42 0)
           (cons 91 0)
           (list 10 6.862664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.7062 -1.2474728)
           (cons 40 0)
           (cons 41 0)
           (cons 42 0)
           (cons 91 0)
           (list 10 6.7062 -1.0731272)
           (cons 40 0)
           (cons 41 0)
           (cons 42 0)
           (cons 91 0)
           (list 10 6.862664 -1.0206)
           (cons 40 0)
           (cons 41 0)
           (cons 42 0)
           (cons 91 0)
           (list 10 7.667336 -1.0206)
           (cons 40 0)
           (cons 41 0)
           (cons 42 0)
           (cons 91 0)
           (list 10 7.8238 -1.0731272)
           (cons 40 0)
           (cons 41 0)
           (cons 42 0)
           (cons 91 0)
           (list 10 7.8238 -1.2474728)
           (cons 40 0)
           (cons 41 0)
           (cons 42 0)
           (cons 91 0)
           (list 10 7.667336 -1.3)
           (cons 40 0)
           (cons 41 0)
           (cons 42 0)
           (cons 91 0)
           (list 10 6.862664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.7062 0.5702072)
           (cons 40 0)
           (cons 41 0)
           (cons 42 0)
           (cons 91 0)
           (list 10 6.7062 0.7445528)
           (cons 40 0)
           (cons 41 0)
           (cons 42 0)
           (cons 91 0)
           (list 10 6.862664 0.79708)
           (cons 40 0)
           (cons 41 0)
           (cons 42 0)
           (cons 91 0)
           (list 10 7.667336 0.79708)
           (cons 40 0)
           (cons 41 0)
           (cons 42 0)
           (cons 91 0)
           (list 10 7.8238 0.7445528)
           (cons 40 0)
           (cons 41 0)
           (cons 42 0)
           (cons 91 0)
           (list 10 7.8238 0.5702072)
           (cons 40 0)
           (cons 41 0)
           (cons 42 0)
           (cons 91 0)
           (list 10 7.667336 0.51768)
           (cons 40 0)
           (cons 41 0)
           (cons 42 0)
           (cons 91 0)
           (list 10 6.862664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 6.7062 1.0731272)
           (cons 40 0)
           (cons 41 0)
           (cons 42 0)
           (cons 91 0)
           (list 10 6.7062 1.2474728)
           (cons 40 0)
           (cons 41 0)
           (cons 42 0)
           (cons 91 0)
           (list 10 6.862664 1.3)
           (cons 40 0)
           (cons 41 0)
           (cons 42 0)
           (cons 91 0)
           (list 10 7.667336 1.3)
           (cons 40 0)
           (cons 41 0)
           (cons 42 0)
           (cons 91 0)
           (list 10 7.8238 1.2474728)
           (cons 40 0)
           (cons 41 0)
           (cons 42 0)
           (cons 91 0)
           (list 10 7.8238 1.0731272)
           (cons 40 0)
           (cons 41 0)
           (cons 42 0)
           (cons 91 0)
           (list 10 7.667336 1.0206)
           (cons 40 0)
           (cons 41 0)
           (cons 42 0)
           (cons 91 0)
           (list 10 6.862664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.9762 -0.7445528)
           (cons 40 0)
           (cons 41 0)
           (cons 42 0)
           (cons 91 0)
           (list 10 7.9762 -0.5702072)
           (cons 40 0)
           (cons 41 0)
           (cons 42 0)
           (cons 91 0)
           (list 10 8.132664 -0.51768)
           (cons 40 0)
           (cons 41 0)
           (cons 42 0)
           (cons 91 0)
           (list 10 8.937336 -0.51768)
           (cons 40 0)
           (cons 41 0)
           (cons 42 0)
           (cons 91 0)
           (list 10 9.0938 -0.5702072)
           (cons 40 0)
           (cons 41 0)
           (cons 42 0)
           (cons 91 0)
           (list 10 9.0938 -0.7445528)
           (cons 40 0)
           (cons 41 0)
           (cons 42 0)
           (cons 91 0)
           (list 10 8.937336 -0.79708)
           (cons 40 0)
           (cons 41 0)
           (cons 42 0)
           (cons 91 0)
           (list 10 8.132664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.9762 -1.2474728)
           (cons 40 0)
           (cons 41 0)
           (cons 42 0)
           (cons 91 0)
           (list 10 7.9762 -1.0731272)
           (cons 40 0)
           (cons 41 0)
           (cons 42 0)
           (cons 91 0)
           (list 10 8.132664 -1.0206)
           (cons 40 0)
           (cons 41 0)
           (cons 42 0)
           (cons 91 0)
           (list 10 8.937336 -1.0206)
           (cons 40 0)
           (cons 41 0)
           (cons 42 0)
           (cons 91 0)
           (list 10 9.0938 -1.0731272)
           (cons 40 0)
           (cons 41 0)
           (cons 42 0)
           (cons 91 0)
           (list 10 9.0938 -1.2474728)
           (cons 40 0)
           (cons 41 0)
           (cons 42 0)
           (cons 91 0)
           (list 10 8.937336 -1.3)
           (cons 40 0)
           (cons 41 0)
           (cons 42 0)
           (cons 91 0)
           (list 10 8.132664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.9762 0.5702072)
           (cons 40 0)
           (cons 41 0)
           (cons 42 0)
           (cons 91 0)
           (list 10 7.9762 0.7445528)
           (cons 40 0)
           (cons 41 0)
           (cons 42 0)
           (cons 91 0)
           (list 10 8.132664 0.79708)
           (cons 40 0)
           (cons 41 0)
           (cons 42 0)
           (cons 91 0)
           (list 10 8.937336 0.79708)
           (cons 40 0)
           (cons 41 0)
           (cons 42 0)
           (cons 91 0)
           (list 10 9.0938 0.7445528)
           (cons 40 0)
           (cons 41 0)
           (cons 42 0)
           (cons 91 0)
           (list 10 9.0938 0.5702072)
           (cons 40 0)
           (cons 41 0)
           (cons 42 0)
           (cons 91 0)
           (list 10 8.937336 0.51768)
           (cons 40 0)
           (cons 41 0)
           (cons 42 0)
           (cons 91 0)
           (list 10 8.132664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 7.9762 1.0731272)
           (cons 40 0)
           (cons 41 0)
           (cons 42 0)
           (cons 91 0)
           (list 10 7.9762 1.2474728)
           (cons 40 0)
           (cons 41 0)
           (cons 42 0)
           (cons 91 0)
           (list 10 8.132664 1.3)
           (cons 40 0)
           (cons 41 0)
           (cons 42 0)
           (cons 91 0)
           (list 10 8.937336 1.3)
           (cons 40 0)
           (cons 41 0)
           (cons 42 0)
           (cons 91 0)
           (list 10 9.0938 1.2474728)
           (cons 40 0)
           (cons 41 0)
           (cons 42 0)
           (cons 91 0)
           (list 10 9.0938 1.0731272)
           (cons 40 0)
           (cons 41 0)
           (cons 42 0)
           (cons 91 0)
           (list 10 8.937336 1.0206)
           (cons 40 0)
           (cons 41 0)
           (cons 42 0)
           (cons 91 0)
           (list 10 8.132664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 1 0 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 9.1 1.3 0)
           (cons 50 0)
          )
         )
         (entmake
          (list
           (cons 0 "POINT")
           (cons 100 "AcDbEntity")
           (cons 67 0)
           (cons 8 "0")
           (cons 100 "AcDbPoint")
           (list 10 9.1 -1.3 0)
           (cons 50 0)
          )
         )
         (entmake
          (list
           (cons 0 "POINT")
           (cons 100 "AcDbEntity")
           (cons 67 0)
           (cons 8 "0")
           (cons 100 "AcDbPoint")
           (list 10 7.9 -1.3 0)
           (cons 50 0)
          )
         )
         (entmake
          (list
           (cons 0 "POINT")
           (cons 100 "AcDbEntity")
           (cons 67 0)
           (cons 8 "0")
           (cons 100 "AcDbPoint")
           (list 10 7.9 1.3 0)
           (cons 50 0)
          )
         )
         (entmake
          (list
           (cons 0 "ATTDEF")
           (cons 100 "AcDbEntity")
           (cons 67 0)
           (cons 8 "0")
           (cons 100 "AcDbText")
           (list 10 0.3 0.56666667 0)
           (cons 40 0.2)
           (cons 1 "1.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 0.23333333 0)
           (cons 40 0.2)
           (cons 1 "1.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.1 0)
           (cons 40 0.2)
           (cons 1 "7.900")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.43333333 0)
           (cons 40 0.2)
           (cons 1 "9.100")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.3 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "POINT")
           (cons 100 "AcDbEntity")
           (cons 67 0)
           (cons 8 "0")
           (cons 100 "AcDbPoint")
           (list 10 9.1 0 0)
           (cons 50 0)
          )
         )
         (entmake (list (cons 0 "ENDBLK")))
        )
       )
       ((= (strcase BLKNAME) (strcase "TAC-1999-ATD-TRUCK"))
        (progn
         (entmake)
         (entmake
          (list
           (cons 0 "BLOCK")
           (cons 2 "TAC-1999-ATD-TRUCK")
           (cons 70 2)
           (cons 4 "")
           (list 10 0 0 0)
          )
         )
         (entmake
          (list
           (cons 0 "LWPOLYLINE")
           (cons 100 "AcDbEntity")
           (cons 67 0)
           (cons 8 "Defpoints")
           (cons 100 "AcDbPolyline")
           (cons 90 4)
           (cons 70 1)
           (cons 43 0)
           (cons 38 0)
           (cons 39 0)
           (list 10 0 -1.3)
           (cons 40 0)
           (cons 41 0)
           (cons 42 0)
           (cons 91 0)
           (list 10 6.535 -1.3)
           (cons 40 0)
           (cons 41 0)
           (cons 42 0)
           (cons 91 0)
           (list 10 6.535 1.3)
           (cons 40 0)
           (cons 41 0)
           (cons 42 0)
           (cons 91 0)
           (list 10 0 1.3)
           (cons 40 0)
           (cons 41 0)
           (cons 42 0)
           (cons 91 0)
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.535 -0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 6.535 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 0.51768 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 3 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.3 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "ARC")
           (cons 100 "AcDbEntity")
           (cons 67 0)
           (cons 8 "0")
           (cons 62 7)
           (cons 6 "Continuous")
           (cons 48 1.524)
           (cons 100 "AcDbCircle")
           (list 10 5.9 0 0)
           (cons 40 0.37142857)
           (cons 100 "AcDbArc")
           (cons 50 0.78539816)
           (cons 51 5.49778714)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 6.16263966 -0.26263966 0)
           (list 11 6.16263966 0.26263966 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.7062 -0.7445528)
           (cons 40 0)
           (cons 41 0)
           (cons 42 0)
           (cons 91 0)
           (list 10 4.7062 -0.5702072)
           (cons 40 0)
           (cons 41 0)
           (cons 42 0)
           (cons 91 0)
           (list 10 4.862664 -0.51768)
           (cons 40 0)
           (cons 41 0)
           (cons 42 0)
           (cons 91 0)
           (list 10 5.667336 -0.51768)
           (cons 40 0)
           (cons 41 0)
           (cons 42 0)
           (cons 91 0)
           (list 10 5.8238 -0.5702072)
           (cons 40 0)
           (cons 41 0)
           (cons 42 0)
           (cons 91 0)
           (list 10 5.8238 -0.7445528)
           (cons 40 0)
           (cons 41 0)
           (cons 42 0)
           (cons 91 0)
           (list 10 5.667336 -0.79708)
           (cons 40 0)
           (cons 41 0)
           (cons 42 0)
           (cons 91 0)
           (list 10 4.862664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.7062 -1.2474728)
           (cons 40 0)
           (cons 41 0)
           (cons 42 0)
           (cons 91 0)
           (list 10 4.7062 -1.0731272)
           (cons 40 0)
           (cons 41 0)
           (cons 42 0)
           (cons 91 0)
           (list 10 4.862664 -1.0206)
           (cons 40 0)
           (cons 41 0)
           (cons 42 0)
           (cons 91 0)
           (list 10 5.667336 -1.0206)
           (cons 40 0)
           (cons 41 0)
           (cons 42 0)
           (cons 91 0)
           (list 10 5.8238 -1.0731272)
           (cons 40 0)
           (cons 41 0)
           (cons 42 0)
           (cons 91 0)
           (list 10 5.8238 -1.2474728)
           (cons 40 0)
           (cons 41 0)
           (cons 42 0)
           (cons 91 0)
           (list 10 5.667336 -1.3)
           (cons 40 0)
           (cons 41 0)
           (cons 42 0)
           (cons 91 0)
           (list 10 4.862664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.7062 0.5702072)
           (cons 40 0)
           (cons 41 0)
           (cons 42 0)
           (cons 91 0)
           (list 10 4.7062 0.7445528)
           (cons 40 0)
           (cons 41 0)
           (cons 42 0)
           (cons 91 0)
           (list 10 4.862664 0.79708)
           (cons 40 0)
           (cons 41 0)
           (cons 42 0)
           (cons 91 0)
           (list 10 5.667336 0.79708)
           (cons 40 0)
           (cons 41 0)
           (cons 42 0)
           (cons 91 0)
           (list 10 5.8238 0.7445528)
           (cons 40 0)
           (cons 41 0)
           (cons 42 0)
           (cons 91 0)
           (list 10 5.8238 0.5702072)
           (cons 40 0)
           (cons 41 0)
           (cons 42 0)
           (cons 91 0)
           (list 10 5.667336 0.51768)
           (cons 40 0)
           (cons 41 0)
           (cons 42 0)
           (cons 91 0)
           (list 10 4.862664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.7062 1.0731272)
           (cons 40 0)
           (cons 41 0)
           (cons 42 0)
           (cons 91 0)
           (list 10 4.7062 1.2474728)
           (cons 40 0)
           (cons 41 0)
           (cons 42 0)
           (cons 91 0)
           (list 10 4.862664 1.3)
           (cons 40 0)
           (cons 41 0)
           (cons 42 0)
           (cons 91 0)
           (list 10 5.667336 1.3)
           (cons 40 0)
           (cons 41 0)
           (cons 42 0)
           (cons 91 0)
           (list 10 5.8238 1.2474728)
           (cons 40 0)
           (cons 41 0)
           (cons 42 0)
           (cons 91 0)
           (list 10 5.8238 1.0731272)
           (cons 40 0)
           (cons 41 0)
           (cons 42 0)
           (cons 91 0)
           (list 10 5.667336 1.0206)
           (cons 40 0)
           (cons 41 0)
           (cons 42 0)
           (cons 91 0)
           (list 10 4.862664 1.0206)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9762 -0.7445528)
           (cons 40 0)
           (cons 41 0)
           (cons 42 0)
           (cons 91 0)
           (list 10 5.9762 -0.5702072)
           (cons 40 0)
           (cons 41 0)
           (cons 42 0)
           (cons 91 0)
           (list 10 6.132664 -0.51768)
           (cons 40 0)
           (cons 41 0)
           (cons 42 0)
           (cons 91 0)
           (list 10 6.937336 -0.51768)
           (cons 40 0)
           (cons 41 0)
           (cons 42 0)
           (cons 91 0)
           (list 10 7.0938 -0.5702072)
           (cons 40 0)
           (cons 41 0)
           (cons 42 0)
           (cons 91 0)
           (list 10 7.0938 -0.7445528)
           (cons 40 0)
           (cons 41 0)
           (cons 42 0)
           (cons 91 0)
           (list 10 6.937336 -0.79708)
           (cons 40 0)
           (cons 41 0)
           (cons 42 0)
           (cons 91 0)
           (list 10 6.132664 -0.79708)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9762 -1.2474728)
           (cons 40 0)
           (cons 41 0)
           (cons 42 0)
           (cons 91 0)
           (list 10 5.9762 -1.0731272)
           (cons 40 0)
           (cons 41 0)
           (cons 42 0)
           (cons 91 0)
           (list 10 6.132664 -1.0206)
           (cons 40 0)
           (cons 41 0)
           (cons 42 0)
           (cons 91 0)
           (list 10 6.937336 -1.0206)
           (cons 40 0)
           (cons 41 0)
           (cons 42 0)
           (cons 91 0)
           (list 10 7.0938 -1.0731272)
           (cons 40 0)
           (cons 41 0)
           (cons 42 0)
           (cons 91 0)
           (list 10 7.0938 -1.2474728)
           (cons 40 0)
           (cons 41 0)
           (cons 42 0)
           (cons 91 0)
           (list 10 6.937336 -1.3)
           (cons 40 0)
           (cons 41 0)
           (cons 42 0)
           (cons 91 0)
           (list 10 6.132664 -1.3)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9762 0.5702072)
           (cons 40 0)
           (cons 41 0)
           (cons 42 0)
           (cons 91 0)
           (list 10 5.9762 0.7445528)
           (cons 40 0)
           (cons 41 0)
           (cons 42 0)
           (cons 91 0)
           (list 10 6.132664 0.79708)
           (cons 40 0)
           (cons 41 0)
           (cons 42 0)
           (cons 91 0)
           (list 10 6.937336 0.79708)
           (cons 40 0)
           (cons 41 0)
           (cons 42 0)
           (cons 91 0)
           (list 10 7.0938 0.7445528)
           (cons 40 0)
           (cons 41 0)
           (cons 42 0)
           (cons 91 0)
           (list 10 7.0938 0.5702072)
           (cons 40 0)
           (cons 41 0)
           (cons 42 0)
           (cons 91 0)
           (list 10 6.937336 0.51768)
           (cons 40 0)
           (cons 41 0)
           (cons 42 0)
           (cons 91 0)
           (list 10 6.132664 0.51768)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 5.9762 1.0731272)
           (cons 40 0)
           (cons 41 0)
           (cons 42 0)
           (cons 91 0)
           (list 10 5.9762 1.2474728)
           (cons 40 0)
           (cons 41 0)
           (cons 42 0)
           (cons 91 0)
           (list 10 6.132664 1.3)
           (cons 40 0)
           (cons 41 0)
           (cons 42 0)
           (cons 91 0)
           (list 10 6.937336 1.3)
           (cons 40 0)
           (cons 41 0)
           (cons 42 0)
           (cons 91 0)
           (list 10 7.0938 1.2474728)
           (cons 40 0)
           (cons 41 0)
           (cons 42 0)
           (cons 91 0)
           (list 10 7.0938 1.0731272)
           (cons 40 0)
           (cons 41 0)
           (cons 42 0)
           (cons 91 0)
           (list 10 6.937336 1.0206)
           (cons 40 0)
           (cons 41 0)
           (cons 42 0)
           (cons 91 0)
           (list 10 6.132664 1.0206)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0.8 0 0)
           (cons 50 0)
          )
         )
         (entmake
          (list
           (cons 0 "POINT")
           (cons 100 "AcDbEntity")
           (cons 67 0)
           (cons 8 "0")
           (cons 100 "AcDbPoint")
           (list 10 0 1.3 0)
           (cons 50 0)
          )
         )
         (entmake
          (list
           (cons 0 "POINT")
           (cons 100 "AcDbEntity")
           (cons 67 0)
           (cons 8 "0")
           (cons 100 "AcDbPoint")
           (list 10 0.8 1.3 0)
           (cons 50 0)
          )
         )
         (entmake
          (list
           (cons 0 "POINT")
           (cons 100 "AcDbEntity")
           (cons 67 0)
           (cons 8 "0")
           (cons 100 "AcDbPoint")
           (list 10 0.8 -1.3 0)
           (cons 50 0)
          )
         )
         (entmake
          (list
           (cons 0 "POINT")
           (cons 100 "AcDbEntity")
           (cons 67 0)
           (cons 8 "0")
           (cons 100 "AcDbPoint")
           (list 10 0 -1.3 0)
           (cons 50 0)
          )
         )
         (entmake
          (list
           (cons 0 "POINT")
           (cons 100 "AcDbEntity")
           (cons 67 0)
           (cons 8 "0")
           (cons 100 "AcDbPoint")
           (list 10 5.9 1.3 0)
           (cons 50 0)
          )
         )
         (entmake
          (list
           (cons 0 "POINT")
           (cons 100 "AcDbEntity")
           (cons 67 0)
           (cons 8 "0")
           (cons 100 "AcDbPoint")
           (list 10 5.9 -1.3 0)
           (cons 50 0)
          )
         )
         (entmake
          (list
           (cons 0 "POINT")
           (cons 100 "AcDbEntity")
           (cons 67 0)
           (cons 8 "0")
           (cons 100 "AcDbPoint")
           (list 10 5.9 0 0)
           (cons 50 0)
          )
         )
         (entmake
          (list
           (cons 0 "ATTDEF")
           (cons 100 "AcDbEntity")
           (cons 67 0)
           (cons 8 "0")
           (cons 100 "AcDbText")
           (list 10 0.1 0.56666667 0)
           (cons 40 0.2)
           (cons 1 "0.800")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 0.23333333 0)
           (cons 40 0.2)
           (cons 1 "0.800")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.1 0)
           (cons 40 0.2)
           (cons 1 "5.900")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.43333333 0)
           (cons 40 0.2)
           (cons 1 "5.900")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 0.1 -0.76666667 0)
           (cons 40 0.2)
           (cons 1 "27.4")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "INSERT")
           (cons 100 "AcDbEntity")
           (cons 67 0)
           (cons 8 "0")
           (cons 100 "AcDbBlockReference")
           (cons 2 "WheelRightM1")
           (list 10 0.8 1.0206 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM1")
           (list 10 0.8 -1.0206 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "TAC-1999-A-BUS-REAR"))
        (progn
         (entmake)
         (entmake
          (list
           (cons 0 "BLOCK")
           (cons 2 "TAC-1999-A-BUS-REAR")
           (cons 70 2)
           (cons 4 "")
           (list 10 0 0 0)
          )
         )
         (entmake
          (list
           (cons 0 "POLYLINE")
           (cons 100 "AcDbEntity")
           (cons 67 0)
           (cons 8 "Defpoints")
           (cons 100 "AcDb2dPolyline")
           (cons 66 1)
           (list 10 0 0 0)
           (cons 70 129)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "Defpoints")
           (cons 100 "AcDbVertex")
           (cons 100 "AcDb2dVertex")
           (list 10 0 0 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 0.6 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 7.8 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 7.8 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 0.6 1.2 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "Defpoints")
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0.6 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.8 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 7.8 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0.6 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0.6 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0.6 -1.2 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 0 0 0)
           (list 11 0.6 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 0 0 0)
           (cons 40 0.16)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.292 -1.152248)
           (cons 40 0)
           (cons 41 0)
           (cons 42 0)
           (cons 91 0)
           (list 10 4.292 -0.993752)
           (cons 40 0)
           (cons 41 0)
           (cons 42 0)
           (cons 91 0)
           (list 10 4.43424 -0.946)
           (cons 40 0)
           (cons 41 0)
           (cons 42 0)
           (cons 91 0)
           (list 10 5.16576 -0.946)
           (cons 40 0)
           (cons 41 0)
           (cons 42 0)
           (cons 91 0)
           (list 10 5.308 -0.993752)
           (cons 40 0)
           (cons 41 0)
           (cons 42 0)
           (cons 91 0)
           (list 10 5.308 -1.152248)
           (cons 40 0)
           (cons 41 0)
           (cons 42 0)
           (cons 91 0)
           (list 10 5.16576 -1.2)
           (cons 40 0)
           (cons 41 0)
           (cons 42 0)
           (cons 91 0)
           (list 10 4.43424 -1.2)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 4.292 0.993752)
           (cons 40 0)
           (cons 41 0)
           (cons 42 0)
           (cons 91 0)
           (list 10 4.292 1.152248)
           (cons 40 0)
           (cons 41 0)
           (cons 42 0)
           (cons 91 0)
           (list 10 4.43424 1.2)
           (cons 40 0)
           (cons 41 0)
           (cons 42 0)
           (cons 91 0)
           (list 10 5.16576 1.2)
           (cons 40 0)
           (cons 41 0)
           (cons 42 0)
           (cons 91 0)
           (list 10 5.308 1.152248)
           (cons 40 0)
           (cons 41 0)
           (cons 42 0)
           (cons 91 0)
           (list 10 5.308 0.993752)
           (cons 40 0)
           (cons 41 0)
           (cons 42 0)
           (cons 91 0)
           (list 10 5.16576 0.946)
           (cons 40 0)
           (cons 41 0)
           (cons 42 0)
           (cons 91 0)
           (list 10 4.43424 0.946)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 0 0 0)
           (cons 50 0)
          )
         )
         (entmake
          (list
           (cons 0 "ATTDEF")
           (cons 100 "AcDbEntity")
           (cons 67 0)
           (cons 8 "0")
           (cons 100 "AcDbText")
           (list 10 -0.7 0.56666667 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 0.23333333 0)
           (cons 40 0.2)
           (cons 1 "0.000")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.1 0)
           (cons 40 0.2)
           (cons 1 "4.800")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.43333333 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 -0.7 -0.76666667 0)
           (cons 40 0.2)
           (cons 1 "")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "POINT")
           (cons 100 "AcDbEntity")
           (cons 67 0)
           (cons 8 "0")
           (cons 100 "AcDbPoint")
           (list 10 4.8 -1.2 0)
           (cons 50 0)
          )
         )
         (entmake
          (list
           (cons 0 "POINT")
           (cons 100 "AcDbEntity")
           (cons 67 0)
           (cons 8 "0")
           (cons 100 "AcDbPoint")
           (list 10 4.8 1.2 0)
           (cons 50 0)
          )
         )
         (entmake
          (list
           (cons 0 "POINT")
           (cons 100 "AcDbEntity")
           (cons 67 0)
           (cons 8 "0")
           (cons 100 "AcDbPoint")
           (list 10 7.8 1.2 0)
           (cons 50 0)
          )
         )
         (entmake
          (list
           (cons 0 "POINT")
           (cons 100 "AcDbEntity")
           (cons 67 0)
           (cons 8 "0")
           (cons 100 "AcDbPoint")
           (list 10 7.8 -1.2 0)
           (cons 50 0)
          )
         )
         (entmake (list (cons 0 "ENDBLK")))
        )
       )
       ((= (strcase BLKNAME) (strcase "TAC-1999-A-BUS-FRONT"))
        (progn
         (entmake)
         (entmake
          (list
           (cons 0 "BLOCK")
           (cons 2 "TAC-1999-A-BUS-FRONT")
           (cons 70 2)
           (cons 4 "")
           (list 10 0 0 0)
          )
         )
         (entmake
          (list
           (cons 0 "POLYLINE")
           (cons 100 "AcDbEntity")
           (cons 67 0)
           (cons 8 "Defpoints")
           (cons 100 "AcDb2dPolyline")
           (cons 66 1)
           (list 10 0 0 0)
           (cons 70 129)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "Defpoints")
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 9.9 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 10.5 0 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 9.9 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "Defpoints")
           (cons 100 "AcDbVertex")
           (cons 100 "AcDb2dVertex")
           (list 10 0 1.2 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "Defpoints")
          )
         )
         (entmake
          (list
           (cons 0 "POLYLINE")
           (cons 100 "AcDbEntity")
           (cons 67 0)
           (cons 8 "0")
           (cons 62 7)
           (cons 6 "Continuous")
           (cons 48 1.524)
           (cons 100 "AcDb2dPolyline")
           (cons 66 1)
           (list 10 0 0 0)
           (cons 70 1)
           (cons 40 0)
           (cons 41 0)
           (cons 71 0)
           (cons 72 0)
           (cons 73 0)
           (cons 74 0)
           (cons 75 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.9 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 9.9 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "VERTEX")
           (cons 100 "AcDbEntity")
           (cons 67 0)
           (cons 8 "0")
           (cons 62 7)
           (cons 6 "Continuous")
           (cons 48 1.524)
           (cons 100 "AcDbVertex")
           (cons 100 "AcDb2dVertex")
           (list 10 0 -1.2 0)
           (cons 40 0)
           (cons 41 0)
           (cons 42 0)
           (cons 91 0)
           (cons 70 0)
           (cons 50 0)
          )
         )
         (entmake
          (list
           (cons 0 "SEQEND")
           (cons 100 "AcDbEntity")
           (cons 67 0)
           (cons 8 "0")
           (cons 62 7)
           (cons 6 "Continuous")
           (cons 48 1.524)
          )
         )
         (entmake
          (list
           (cons 0 "LINE")
           (cons 100 "AcDbEntity")
           (cons 67 0)
           (cons 8 "0")
           (cons 62 7)
           (cons 6 "Continuous")
           (cons 48 1.524)
           (cons 100 "AcDbLine")
           (list 10 9.9 0 0)
           (list 11 10.5 0 0)
          )
         )
         (entmake
          (list
           (cons 0 "CIRCLE")
           (cons 100 "AcDbEntity")
           (cons 67 0)
           (cons 8 "0")
           (cons 62 7)
           (cons 6 "Continuous")
           (cons 48 1.524)
           (cons 100 "AcDbCircle")
           (list 10 10.5 0 0)
           (cons 40 0.1016)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.192 -1.152248)
           (cons 40 0)
           (cons 41 0)
           (cons 42 0)
           (cons 91 0)
           (list 10 8.192 -0.993752)
           (cons 40 0)
           (cons 41 0)
           (cons 42 0)
           (cons 91 0)
           (list 10 8.33424 -0.946)
           (cons 40 0)
           (cons 41 0)
           (cons 42 0)
           (cons 91 0)
           (list 10 9.06576 -0.946)
           (cons 40 0)
           (cons 41 0)
           (cons 42 0)
           (cons 91 0)
           (list 10 9.208 -0.993752)
           (cons 40 0)
           (cons 41 0)
           (cons 42 0)
           (cons 91 0)
           (list 10 9.208 -1.152248)
           (cons 40 0)
           (cons 41 0)
           (cons 42 0)
           (cons 91 0)
           (list 10 9.06576 -1.2)
           (cons 40 0)
           (cons 41 0)
           (cons 42 0)
           (cons 91 0)
           (list 10 8.33424 -1.2)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 8.192 0.993752)
           (cons 40 0)
           (cons 41 0)
           (cons 42 0)
           (cons 91 0)
           (list 10 8.192 1.152248)
           (cons 40 0)
           (cons 41 0)
           (cons 42 0)
           (cons 91 0)
           (list 10 8.33424 1.2)
           (cons 40 0)
           (cons 41 0)
           (cons 42 0)
           (cons 91 0)
           (list 10 9.06576 1.2)
           (cons 40 0)
           (cons 41 0)
           (cons 42 0)
           (cons 91 0)
           (list 10 9.208 1.152248)
           (cons 40 0)
           (cons 41 0)
           (cons 42 0)
           (cons 91 0)
           (list 10 9.208 0.993752)
           (cons 40 0)
           (cons 41 0)
           (cons 42 0)
           (cons 91 0)
           (list 10 9.06576 0.946)
           (cons 40 0)
           (cons 41 0)
           (cons 42 0)
           (cons 91 0)
           (list 10 8.33424 0.946)
           (cons 40 0)
           (cons 41 0)
           (cons 42 0)
           (cons 91 0)
          )
         )
         (entmake
          (list
           (cons 0 "POINT")
           (cons 100 "AcDbEntity")
           (cons 67 0)
           (cons 8 "0")
           (cons 100 "AcDbPoint")
           (list 10 3.2 0 0)
           (cons 50 0)
          )
         )
         (entmake
          (list
           (cons 0 "ATTDEF")
           (cons 100 "AcDbEntity")
           (cons 67 0)
           (cons 8 "0")
           (cons 100 "AcDbText")
           (list 10 2.5 0.56666667 0)
           (cons 40 0.2)
           (cons 1 "3.200")
           (cons 50 0)
           (cons 41 1)
           (cons 51 0)
           (cons 7 "Standard")
           (cons 71 0)
           (cons 72 0)
           (list 11 0 0 0)
           (cons 100 "AcDbAttributeDefinition")
           (cons 3 "Insert to Steering(Eye) Point (D0)")
           (cons 2 "D0")
           (cons 70 9)
           (cons 73 0)
           (cons 74 0)
          )
         )
         (entmake
          (list
           (cons 0 "ATTDEF")
           (cons 100 "AcDbEntity")
           (cons 67 0)
           (cons 8 "0")
           (cons 100 "AcDbText")
           (list 10 2.5 0.23333333 0)
           (cons 40 0.2)
           (cons 1 "3.200")
           (cons 50 0)
           (cons 41 1)
           (cons 51 0)
           (cons 7 "Standard")
           (cons 71 0)
           (cons 72 0)
           (list 11 0 0 0)
           (cons 100 "AcDbAttributeDefinition")
           (cons 3 "Insert to Front Wheel (Dg)")
           (cons 2 "DG")
           (cons 70 9)
           (cons 73 0)
           (cons 74 0)
          )
         )
         (entmake
          (list
           (cons 0 "ATTDEF")
           (cons 100 "AcDbEntity")
           (cons 67 0)
           (cons 8 "0")
           (cons 100 "AcDbText")
           (list 10 2.5 -0.1 0)
           (cons 40 0.2)
           (cons 1 "8.700")
           (cons 50 0)
           (cons 41 1)
           (cons 51 0)
           (cons 7 "Standard")
           (cons 71 0)
           (cons 72 0)
           (list 11 0 0 0)
           (cons 100 "AcDbAttributeDefinition")
           (cons 3 "Insert to Rear Wheels (D)")
           (cons 2 "D")
           (cons 70 9)
           (cons 73 0)
           (cons 74 0)
          )
         )
         (entmake
          (list
           (cons 0 "ATTDEF")
           (cons 100 "AcDbEntity")
           (cons 67 0)
           (cons 8 "0")
           (cons 100 "AcDbText")
           (list 10 2.5 -0.43333333 0)
           (cons 40 0.2)
           (cons 1 "10.500")
           (cons 50 0)
           (cons 41 1)
           (cons 51 0)
           (cons 7 "Standard")
           (cons 71 0)
           (cons 72 0)
           (list 11 0 0 0)
           (cons 100 "AcDbAttributeDefinition")
           (cons 3 "Insert to Hook (Dh)")
           (cons 2 "DH")
           (cons 70 9)
           (cons 73 0)
           (cons 74 0)
          )
         )
         (entmake
          (list
           (cons 0 "ATTDEF")
           (cons 100 "AcDbEntity")
           (cons 67 0)
           (cons 8 "0")
           (cons 100 "AcDbText")
           (list 10 2.5 -0.76666667 0)
           (cons 40 0.2)
           (cons 1 "27.3")
           (cons 50 0)
           (cons 41 1)
           (cons 51 0)
           (cons 7 "Standard")
           (cons 71 0)
           (cons 72 0)
           (list 11 0 0 0)
           (cons 100 "AcDbAttributeDefinition")
           (cons 3 "Lock Angle (L)")
           (cons 2 "L")
           (cons 70 9)
           (cons 73 0)
           (cons 74 0)
          )
         )
         (entmake
          (list
           (cons 0 "POINT")
           (cons 100 "AcDbEntity")
           (cons 67 0)
           (cons 8 "0")
           (cons 100 "AcDbPoint")
           (list 10 0 -1.2 0)
           (cons 50 0)
          )
         )
         (entmake
          (list
           (cons 0 "POINT")
           (cons 100 "AcDbEntity")
           (cons 67 0)
           (cons 8 "0")
           (cons 100 "AcDbPoint")
           (list 10 0 1.2 0)
           (cons 50 0)
          )
         )
         (entmake
          (list
           (cons 0 "POINT")
           (cons 100 "AcDbEntity")
           (cons 67 0)
           (cons 8 "0")
           (cons 100 "AcDbPoint")
           (list 10 9.9 1.2 0)
           (cons 50 0)
          )
         )
         (entmake
          (list
           (cons 0 "POINT")
           (cons 100 "AcDbEntity")
           (cons 67 0)
           (cons 8 "0")
           (cons 100 "AcDbPoint")
           (list 10 9.9 -1.2 0)
           (cons 50 0)
          )
         )
         (entmake
          (list
           (cons 0 "POINT")
           (cons 100 "AcDbEntity")
           (cons 67 0)
           (cons 8 "0")
           (cons 100 "AcDbPoint")
           (list 10 3.2 1.2 0)
           (cons 50 0)
          )
         )
         (entmake
          (list
           (cons 0 "POINT")
           (cons 100 "AcDbEntity")
           (cons 67 0)
           (cons 8 "0")
           (cons 100 "AcDbPoint")
           (list 10 3.2 -1.2 0)
           (cons 50 0)
          )
         )
         (entmake
          (list
           (cons 0 "POINT")
           (cons 100 "AcDbEntity")
           (cons 67 0)
           (cons 8 "0")
           (cons 100 "AcDbPoint")
           (list 10 8.7 -1.2 0)
           (cons 50 0)
          )
         )
         (entmake
          (list
           (cons 0 "POINT")
           (cons 100 "AcDbEntity")
           (cons 67 0)
           (cons 8 "0")
           (cons 100 "AcDbPoint")
           (list 10 8.7 1.2 0)
           (cons 50 0)
          )
         )
         (entmake
          (list
           (cons 0 "POINT")
           (cons 100 "AcDbEntity")
           (cons 67 0)
           (cons 8 "0")
           (cons 100 "AcDbPoint")
           (list 10 10.5 0 0)
           (cons 50 0)
          )
         )
         (entmake
          (list
           (cons 0 "INSERT")
           (cons 100 "AcDbEntity")
           (cons 67 0)
           (cons 8 "0")
           (cons 100 "AcDbBlockReference")
           (cons 2 "WheelRightM2")
           (list 10 3.2 0.946 0)
           (cons 41 1)
           (cons 42 1)
           (cons 43 1)
           (cons 50 0)
           (cons 70 0)
           (cons 71 0)
           (cons 44 0)
           (cons 45 0)
          )
         )
         (entmake
          (list
           (cons 0 "INSERT")
           (cons 100 "AcDbEntity")
           (cons 67 0)
           (cons 8 "0")
           (cons 100 "AcDbBlockReference")
           (cons 2 "WheelLeftM2")
           (list 10 3.2 -0.946 0)
           (cons 41 1)
           (cons 42 1)
           (cons 43 1)
           (cons 50 0)
           (cons 70 0)
           (cons 71 0)
           (cons 44 0)
           (cons 45 0)
          )
         )
         (entmake (list (cons 0 "ENDBLK")))
        )
       )
       ((= (strcase BLKNAME) (strcase "WheelLeftM2"))
        (progn
         (entmake)
         (entmake
          (list
           (cons 0 "BLOCK")
           (cons 2 "WheelLeftM2")
           (cons 70 0)
           (cons 4 "")
           (list 10 0 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -0.508 -0.206248)
           (cons 40 0)
           (cons 41 0)
           (cons 42 0)
           (cons 91 0)
           (list 10 -0.508 -0.047752)
           (cons 40 0)
           (cons 41 0)
           (cons 42 0)
           (cons 91 0)
           (list 10 -0.36576 0)
           (cons 40 0)
           (cons 41 0)
           (cons 42 0)
           (cons 91 0)
           (list 10 0.36576 0)
           (cons 40 0)
           (cons 41 0)
           (cons 42 0)
           (cons 91 0)
           (list 10 0.508 -0.047752)
           (cons 40 0)
           (cons 41 0)
           (cons 42 0)
           (cons 91 0)
           (list 10 0.508 -0.206248)
           (cons 40 0)
           (cons 41 0)
           (cons 42 0)
           (cons 91 0)
           (list 10 0.36576 -0.254)
           (cons 40 0)
           (cons 41 0)
           (cons 42 0)
           (cons 91 0)
           (list 10 -0.36576 -0.254)
           (cons 40 0)
           (cons 41 0)
           (cons 42 0)
           (cons 91 0)
          )
         )
         (entmake (list (cons 0 "ENDBLK")))
        )
       )
       ((= (strcase BLKNAME) (strcase "WheelRightM2"))
        (progn
         (entmake)
         (entmake
          (list
           (cons 0 "BLOCK")
           (cons 2 "WheelRightM2")
           (cons 70 0)
           (cons 4 "")
           (list 10 0 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -0.508 0.047752)
           (cons 40 0)
           (cons 41 0)
           (cons 42 0)
           (cons 91 0)
           (list 10 -0.508 0.206248)
           (cons 40 0)
           (cons 41 0)
           (cons 42 0)
           (cons 91 0)
           (list 10 -0.36576 0.254)
           (cons 40 0)
           (cons 41 0)
           (cons 42 0)
           (cons 91 0)
           (list 10 0.36576 0.254)
           (cons 40 0)
           (cons 41 0)
           (cons 42 0)
           (cons 91 0)
           (list 10 0.508 0.206248)
           (cons 40 0)
           (cons 41 0)
           (cons 42 0)
           (cons 91 0)
           (list 10 0.508 0.047752)
           (cons 40 0)
           (cons 41 0)
           (cons 42 0)
           (cons 91 0)
           (list 10 0.36576 0)
           (cons 40 0)
           (cons 41 0)
           (cons 42 0)
           (cons 91 0)
           (list 10 -0.36576 0)
           (cons 40 0)
           (cons 41 0)
           (cons 42 0)
           (cons 91 0)
          )
         )
         (entmake (list (cons 0 "ENDBLK")))
        )
       )
       ((= (strcase BLKNAME) (strcase "WheelLeftM1"))
        (progn
         (entmake)
         (entmake
          (list
           (cons 0 "BLOCK")
           (cons 2 "WheelLeftM1")
           (cons 70 0)
           (cons 4 "")
           (list 10 0 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -0.5588 -0.2268728)
           (cons 40 0)
           (cons 41 0)
           (cons 42 0)
           (cons 91 0)
           (list 10 -0.5588 -0.0525272)
           (cons 40 0)
           (cons 41 0)
           (cons 42 0)
           (cons 91 0)
           (list 10 -0.402336 0)
           (cons 40 0)
           (cons 41 0)
           (cons 42 0)
           (cons 91 0)
           (list 10 0.402336 0)
           (cons 40 0)
           (cons 41 0)
           (cons 42 0)
           (cons 91 0)
           (list 10 0.5588 -0.0525272)
           (cons 40 0)
           (cons 41 0)
           (cons 42 0)
           (cons 91 0)
           (list 10 0.5588 -0.2268728)
           (cons 40 0)
           (cons 41 0)
           (cons 42 0)
           (cons 91 0)
           (list 10 0.402336 -0.2794)
           (cons 40 0)
           (cons 41 0)
           (cons 42 0)
           (cons 91 0)
           (list 10 -0.402336 -0.2794)
           (cons 40 0)
           (cons 41 0)
           (cons 42 0)
           (cons 91 0)
          )
         )
         (entmake (list (cons 0 "ENDBLK")))
        )
       )
       ((= (strcase BLKNAME) (strcase "WheelRightM1"))
        (progn
         (entmake)
         (entmake
          (list
           (cons 0 "BLOCK")
           (cons 2 "WheelRightM1")
           (cons 70 0)
           (cons 4 "")
           (list 10 0 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -0.5588 0.0525272)
           (cons 40 0)
           (cons 41 0)
           (cons 42 0)
           (cons 91 0)
           (list 10 -0.5588 0.2268728)
           (cons 40 0)
           (cons 41 0)
           (cons 42 0)
           (cons 91 0)
           (list 10 -0.402336 0.2794)
           (cons 40 0)
           (cons 41 0)
           (cons 42 0)
           (cons 91 0)
           (list 10 0.402336 0.2794)
           (cons 40 0)
           (cons 41 0)
           (cons 42 0)
           (cons 91 0)
           (list 10 0.5588 0.2268728)
           (cons 40 0)
           (cons 41 0)
           (cons 42 0)
           (cons 91 0)
           (list 10 0.5588 0.0525272)
           (cons 40 0)
           (cons 41 0)
           (cons 42 0)
           (cons 91 0)
           (list 10 0.402336 0)
           (cons 40 0)
           (cons 41 0)
           (cons 42 0)
           (cons 91 0)
           (list 10 -0.402336 0)
           (cons 40 0)
           (cons 41 0)
           (cons 42 0)
           (cons 91 0)
          )
         )
         (entmake (list (cons 0 "ENDBLK")))
        )
       )
       ((= (strcase BLKNAME) (strcase "WheelLeftM3"))
        (progn
         (entmake)
         (entmake
          (list
           (cons 0 "BLOCK")
           (cons 2 "WheelLeftM3")
           (cons 70 0)
           (cons 4 "")
           (list 10 0 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -0.3429 -0.1392174)
           (cons 40 0)
           (cons 41 0)
           (cons 42 0)
           (cons 91 0)
           (list 10 -0.3429 -0.0322326)
           (cons 40 0)
           (cons 41 0)
           (cons 42 0)
           (cons 91 0)
           (list 10 -0.246888 0)
           (cons 40 0)
           (cons 41 0)
           (cons 42 0)
           (cons 91 0)
           (list 10 0.246888 0)
           (cons 40 0)
           (cons 41 0)
           (cons 42 0)
           (cons 91 0)
           (list 10 0.3429 -0.0322326)
           (cons 40 0)
           (cons 41 0)
           (cons 42 0)
           (cons 91 0)
           (list 10 0.3429 -0.1392174)
           (cons 40 0)
           (cons 41 0)
           (cons 42 0)
           (cons 91 0)
           (list 10 0.246888 -0.17145)
           (cons 40 0)
           (cons 41 0)
           (cons 42 0)
           (cons 91 0)
           (list 10 -0.246888 -0.17145)
           (cons 40 0)
           (cons 41 0)
           (cons 42 0)
           (cons 91 0)
          )
         )
         (entmake (list (cons 0 "ENDBLK")))
        )
       )
       ((= (strcase BLKNAME) (strcase "WheelRightM3"))
        (progn
         (entmake)
         (entmake
          (list
           (cons 0 "BLOCK")
           (cons 2 "WheelRightM3")
           (cons 70 0)
           (cons 4 "")
           (list 10 0 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -0.3429 0.0322326)
           (cons 40 0)
           (cons 41 0)
           (cons 42 0)
           (cons 91 0)
           (list 10 -0.3429 0.1392174)
           (cons 40 0)
           (cons 41 0)
           (cons 42 0)
           (cons 91 0)
           (list 10 -0.246888 0.17145)
           (cons 40 0)
           (cons 41 0)
           (cons 42 0)
           (cons 91 0)
           (list 10 0.246888 0.17145)
           (cons 40 0)
           (cons 41 0)
           (cons 42 0)
           (cons 91 0)
           (list 10 0.3429 0.1392174)
           (cons 40 0)
           (cons 41 0)
           (cons 42 0)
           (cons 91 0)
           (list 10 0.3429 0.0322326)
           (cons 40 0)
           (cons 41 0)
           (cons 42 0)
           (cons 91 0)
           (list 10 0.246888 0)
           (cons 40 0)
           (cons 41 0)
           (cons 42 0)
           (cons 91 0)
           (list 10 -0.246888 0)
           (cons 40 0)
           (cons 41 0)
           (cons 42 0)
           (cons 91 0)
          )
         )
         (entmake (list (cons 0 "ENDBLK")))
        )
       )
       ((= (strcase BLKNAME) (strcase "WheelLeft1"))
        (progn
         (entmake)
         (entmake
          (list
           (cons 0 "BLOCK")
           (cons 2 "WheelLeft1")
           (cons 70 0)
           (cons 4 "")
           (list 10 0 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -1.83333333 -0.74433333)
           (cons 40 0)
           (cons 41 0)
           (cons 42 0)
           (cons 91 0)
           (list 10 -1.83333333 -0.17233333)
           (cons 40 0)
           (cons 41 0)
           (cons 42 0)
           (cons 91 0)
           (list 10 -1.32 0)
           (cons 40 0)
           (cons 41 0)
           (cons 42 0)
           (cons 91 0)
           (list 10 1.32 0)
           (cons 40 0)
           (cons 41 0)
           (cons 42 0)
           (cons 91 0)
           (list 10 1.83333333 -0.17233333)
           (cons 40 0)
           (cons 41 0)
           (cons 42 0)
           (cons 91 0)
           (list 10 1.83333333 -0.74433333)
           (cons 40 0)
           (cons 41 0)
           (cons 42 0)
           (cons 91 0)
           (list 10 1.32 -0.91666667)
           (cons 40 0)
           (cons 41 0)
           (cons 42 0)
           (cons 91 0)
           (list 10 -1.32 -0.91666667)
           (cons 40 0)
           (cons 41 0)
           (cons 42 0)
           (cons 91 0)
          )
         )
         (entmake (list (cons 0 "ENDBLK")))
        )
       )
       ((= (strcase BLKNAME) (strcase "WheelRight1"))
        (progn
         (entmake)
         (entmake
          (list
           (cons 0 "BLOCK")
           (cons 2 "WheelRight1")
           (cons 70 0)
           (cons 4 "")
           (list 10 0 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -1.83333333 0.17233333)
           (cons 40 0)
           (cons 41 0)
           (cons 42 0)
           (cons 91 0)
           (list 10 -1.83333333 0.74433333)
           (cons 40 0)
           (cons 41 0)
           (cons 42 0)
           (cons 91 0)
           (list 10 -1.32 0.91666667)
           (cons 40 0)
           (cons 41 0)
           (cons 42 0)
           (cons 91 0)
           (list 10 1.32 0.91666667)
           (cons 40 0)
           (cons 41 0)
           (cons 42 0)
           (cons 91 0)
           (list 10 1.83333333 0.74433333)
           (cons 40 0)
           (cons 41 0)
           (cons 42 0)
           (cons 91 0)
           (list 10 1.83333333 0.17233333)
           (cons 40 0)
           (cons 41 0)
           (cons 42 0)
           (cons 91 0)
           (list 10 1.32 0)
           (cons 40 0)
           (cons 41 0)
           (cons 42 0)
           (cons 91 0)
           (list 10 -1.32 0)
           (cons 40 0)
           (cons 41 0)
           (cons 42 0)
           (cons 91 0)
          )
         )
         (entmake (list (cons 0 "ENDBLK")))
        )
       )
       ((= (strcase BLKNAME) (strcase "WheelLeft2"))
        (progn
         (entmake)
         (entmake
          (list
           (cons 0 "BLOCK")
           (cons 2 "WheelLeft2")
           (cons 70 0)
           (cons 4 "")
           (list 10 0 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -1.66666667 -0.67666667)
           (cons 40 0)
           (cons 41 0)
           (cons 42 0)
           (cons 91 0)
           (list 10 -1.66666667 -0.15666667)
           (cons 40 0)
           (cons 41 0)
           (cons 42 0)
           (cons 91 0)
           (list 10 -1.2 0)
           (cons 40 0)
           (cons 41 0)
           (cons 42 0)
           (cons 91 0)
           (list 10 1.2 0)
           (cons 40 0)
           (cons 41 0)
           (cons 42 0)
           (cons 91 0)
           (list 10 1.66666667 -0.15666667)
           (cons 40 0)
           (cons 41 0)
           (cons 42 0)
           (cons 91 0)
           (list 10 1.66666667 -0.67666667)
           (cons 40 0)
           (cons 41 0)
           (cons 42 0)
           (cons 91 0)
           (list 10 1.2 -0.83333333)
           (cons 40 0)
           (cons 41 0)
           (cons 42 0)
           (cons 91 0)
           (list 10 -1.2 -0.83333333)
           (cons 40 0)
           (cons 41 0)
           (cons 42 0)
           (cons 91 0)
          )
         )
         (entmake (list (cons 0 "ENDBLK")))
        )
       )
       ((= (strcase BLKNAME) (strcase "WheelRight2"))
        (progn
         (entmake)
         (entmake
          (list
           (cons 0 "BLOCK")
           (cons 2 "WheelRight2")
           (cons 70 0)
           (cons 4 "")
           (list 10 0 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -1.66666667 0.15666667)
           (cons 40 0)
           (cons 41 0)
           (cons 42 0)
           (cons 91 0)
           (list 10 -1.66666667 0.67666667)
           (cons 40 0)
           (cons 41 0)
           (cons 42 0)
           (cons 91 0)
           (list 10 -1.2 0.83333333)
           (cons 40 0)
           (cons 41 0)
           (cons 42 0)
           (cons 91 0)
           (list 10 1.2 0.83333333)
           (cons 40 0)
           (cons 41 0)
           (cons 42 0)
           (cons 91 0)
           (list 10 1.66666667 0.67666667)
           (cons 40 0)
           (cons 41 0)
           (cons 42 0)
           (cons 91 0)
           (list 10 1.66666667 0.15666667)
           (cons 40 0)
           (cons 41 0)
           (cons 42 0)
           (cons 91 0)
           (list 10 1.2 0)
           (cons 40 0)
           (cons 41 0)
           (cons 42 0)
           (cons 91 0)
           (list 10 -1.2 0)
           (cons 40 0)
           (cons 41 0)
           (cons 42 0)
           (cons 91 0)
          )
         )
         (entmake (list (cons 0 "ENDBLK")))
        )
       )
       ((= (strcase BLKNAME) (strcase "WheelLeft4"))
        (progn
         (entmake)
         (entmake
          (list
           (cons 0 "BLOCK")
           (cons 2 "WheelLeft4")
           (cons 70 0)
           (cons 4 "")
           (list 10 0 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -1.04166667 -0.42291667)
           (cons 40 0)
           (cons 41 0)
           (cons 42 0)
           (cons 91 0)
           (list 10 -1.04166667 -0.09791667)
           (cons 40 0)
           (cons 41 0)
           (cons 42 0)
           (cons 91 0)
           (list 10 -0.75 0)
           (cons 40 0)
           (cons 41 0)
           (cons 42 0)
           (cons 91 0)
           (list 10 0.75 0)
           (cons 40 0)
           (cons 41 0)
           (cons 42 0)
           (cons 91 0)
           (list 10 1.04166667 -0.09791667)
           (cons 40 0)
           (cons 41 0)
           (cons 42 0)
           (cons 91 0)
           (list 10 1.04166667 -0.42291667)
           (cons 40 0)
           (cons 41 0)
           (cons 42 0)
           (cons 91 0)
           (list 10 0.75 -0.52083333)
           (cons 40 0)
           (cons 41 0)
           (cons 42 0)
           (cons 91 0)
           (list 10 -0.75 -0.52083333)
           (cons 40 0)
           (cons 41 0)
           (cons 42 0)
           (cons 91 0)
          )
         )
         (entmake (list (cons 0 "ENDBLK")))
        )
       )
       ((= (strcase BLKNAME) (strcase "WheelRight4"))
        (progn
         (entmake)
         (entmake
          (list
           (cons 0 "BLOCK")
           (cons 2 "WheelRight4")
           (cons 70 0)
           (cons 4 "")
           (list 10 0 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -1.04166667 0.09791667)
           (cons 40 0)
           (cons 41 0)
           (cons 42 0)
           (cons 91 0)
           (list 10 -1.04166667 0.42291667)
           (cons 40 0)
           (cons 41 0)
           (cons 42 0)
           (cons 91 0)
           (list 10 -0.75 0.52083333)
           (cons 40 0)
           (cons 41 0)
           (cons 42 0)
           (cons 91 0)
           (list 10 0.75 0.52083333)
           (cons 40 0)
           (cons 41 0)
           (cons 42 0)
           (cons 91 0)
           (list 10 1.04166667 0.42291667)
           (cons 40 0)
           (cons 41 0)
           (cons 42 0)
           (cons 91 0)
           (list 10 1.04166667 0.09791667)
           (cons 40 0)
           (cons 41 0)
           (cons 42 0)
           (cons 91 0)
           (list 10 0.75 0)
           (cons 40 0)
           (cons 41 0)
           (cons 42 0)
           (cons 91 0)
           (list 10 -0.75 0)
           (cons 40 0)
           (cons 41 0)
           (cons 42 0)
           (cons 91 0)
          )
         )
         (entmake (list (cons 0 "ENDBLK")))
        )
       )
       ((= (strcase BLKNAME) (strcase "Wheel5"))
        (progn
         (entmake)
         (entmake
          (list
           (cons 0 "BLOCK")
           (cons 2 "Wheel5")
           (cons 70 0)
           (cons 4 "")
           (list 10 0 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -0.4572 -2.48804176)
           (cons 40 0)
           (cons 41 0)
           (cons 42 0)
           (cons 91 0)
           (list 10 -0.4572 -2.15203024)
           (cons 40 0)
           (cons 41 0)
           (cons 42 0)
           (cons 91 0)
           (list 10 -0.329184 -2.050796)
           (cons 40 0)
           (cons 41 0)
           (cons 42 0)
           (cons 91 0)
           (list 10 0.329184 -2.050796)
           (cons 40 0)
           (cons 41 0)
           (cons 42 0)
           (cons 91 0)
           (list 10 0.4572 -2.15203024)
           (cons 40 0)
           (cons 41 0)
           (cons 42 0)
           (cons 91 0)
           (list 10 0.4572 -2.48804176)
           (cons 40 0)
           (cons 41 0)
           (cons 42 0)
           (cons 91 0)
           (list 10 0.329184 -2.589276)
           (cons 40 0)
           (cons 41 0)
           (cons 42 0)
           (cons 91 0)
           (list 10 -0.329184 -2.589276)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -0.4572 -1.52030176)
           (cons 40 0)
           (cons 41 0)
           (cons 42 0)
           (cons 91 0)
           (list 10 -0.4572 -1.18429024)
           (cons 40 0)
           (cons 41 0)
           (cons 42 0)
           (cons 91 0)
           (list 10 -0.329184 -1.083056)
           (cons 40 0)
           (cons 41 0)
           (cons 42 0)
           (cons 91 0)
           (list 10 0.329184 -1.083056)
           (cons 40 0)
           (cons 41 0)
           (cons 42 0)
           (cons 91 0)
           (list 10 0.4572 -1.18429024)
           (cons 40 0)
           (cons 41 0)
           (cons 42 0)
           (cons 91 0)
           (list 10 0.4572 -1.52030176)
           (cons 40 0)
           (cons 41 0)
           (cons 42 0)
           (cons 91 0)
           (list 10 0.329184 -1.621536)
           (cons 40 0)
           (cons 41 0)
           (cons 42 0)
           (cons 91 0)
           (list 10 -0.329184 -1.621536)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -0.4572 -0.55256176)
           (cons 40 0)
           (cons 41 0)
           (cons 42 0)
           (cons 91 0)
           (list 10 -0.4572 -0.21655024)
           (cons 40 0)
           (cons 41 0)
           (cons 42 0)
           (cons 91 0)
           (list 10 -0.329184 -0.115316)
           (cons 40 0)
           (cons 41 0)
           (cons 42 0)
           (cons 91 0)
           (list 10 0.329184 -0.115316)
           (cons 40 0)
           (cons 41 0)
           (cons 42 0)
           (cons 91 0)
           (list 10 0.4572 -0.21655024)
           (cons 40 0)
           (cons 41 0)
           (cons 42 0)
           (cons 91 0)
           (list 10 0.4572 -0.55256176)
           (cons 40 0)
           (cons 41 0)
           (cons 42 0)
           (cons 91 0)
           (list 10 0.329184 -0.653796)
           (cons 40 0)
           (cons 41 0)
           (cons 42 0)
           (cons 91 0)
           (list 10 -0.329184 -0.653796)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -0.4572 0.21655024)
           (cons 40 0)
           (cons 41 0)
           (cons 42 0)
           (cons 91 0)
           (list 10 -0.4572 0.55256176)
           (cons 40 0)
           (cons 41 0)
           (cons 42 0)
           (cons 91 0)
           (list 10 -0.329184 0.653796)
           (cons 40 0)
           (cons 41 0)
           (cons 42 0)
           (cons 91 0)
           (list 10 0.329184 0.653796)
           (cons 40 0)
           (cons 41 0)
           (cons 42 0)
           (cons 91 0)
           (list 10 0.4572 0.55256176)
           (cons 40 0)
           (cons 41 0)
           (cons 42 0)
           (cons 91 0)
           (list 10 0.4572 0.21655024)
           (cons 40 0)
           (cons 41 0)
           (cons 42 0)
           (cons 91 0)
           (list 10 0.329184 0.115316)
           (cons 40 0)
           (cons 41 0)
           (cons 42 0)
           (cons 91 0)
           (list 10 -0.329184 0.115316)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -0.4572 1.18429024)
           (cons 40 0)
           (cons 41 0)
           (cons 42 0)
           (cons 91 0)
           (list 10 -0.4572 1.52030176)
           (cons 40 0)
           (cons 41 0)
           (cons 42 0)
           (cons 91 0)
           (list 10 -0.329184 1.621536)
           (cons 40 0)
           (cons 41 0)
           (cons 42 0)
           (cons 91 0)
           (list 10 0.329184 1.621536)
           (cons 40 0)
           (cons 41 0)
           (cons 42 0)
           (cons 91 0)
           (list 10 0.4572 1.52030176)
           (cons 40 0)
           (cons 41 0)
           (cons 42 0)
           (cons 91 0)
           (list 10 0.4572 1.18429024)
           (cons 40 0)
           (cons 41 0)
           (cons 42 0)
           (cons 91 0)
           (list 10 0.329184 1.083056)
           (cons 40 0)
           (cons 41 0)
           (cons 42 0)
           (cons 91 0)
           (list 10 -0.329184 1.083056)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -0.4572 2.15203024)
           (cons 40 0)
           (cons 41 0)
           (cons 42 0)
           (cons 91 0)
           (list 10 -0.4572 2.48804176)
           (cons 40 0)
           (cons 41 0)
           (cons 42 0)
           (cons 91 0)
           (list 10 -0.329184 2.589276)
           (cons 40 0)
           (cons 41 0)
           (cons 42 0)
           (cons 91 0)
           (list 10 0.329184 2.589276)
           (cons 40 0)
           (cons 41 0)
           (cons 42 0)
           (cons 91 0)
           (list 10 0.4572 2.48804176)
           (cons 40 0)
           (cons 41 0)
           (cons 42 0)
           (cons 91 0)
           (list 10 0.4572 2.15203024)
           (cons 40 0)
           (cons 41 0)
           (cons 42 0)
           (cons 91 0)
           (list 10 0.329184 2.050796)
           (cons 40 0)
           (cons 41 0)
           (cons 42 0)
           (cons 91 0)
           (list 10 -0.329184 2.050796)
           (cons 40 0)
           (cons 41 0)
           (cons 42 0)
           (cons 91 0)
          )
         )
         (entmake (list (cons 0 "ENDBLK")))
        )
       )
       ((= (strcase BLKNAME) (strcase "WheelLeftM6"))
        (progn
         (entmake)
         (entmake
          (list
           (cons 0 "BLOCK")
           (cons 2 "WheelLeftM6")
           (cons 70 0)
           (cons 4 "")
           (list 10 0 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -0.508 -0.206248)
           (cons 40 0)
           (cons 41 0)
           (cons 42 0)
           (cons 91 0)
           (list 10 -0.508 -0.047752)
           (cons 40 0)
           (cons 41 0)
           (cons 42 0)
           (cons 91 0)
           (list 10 -0.36576 0)
           (cons 40 0)
           (cons 41 0)
           (cons 42 0)
           (cons 91 0)
           (list 10 0.36576 0)
           (cons 40 0)
           (cons 41 0)
           (cons 42 0)
           (cons 91 0)
           (list 10 0.508 -0.047752)
           (cons 40 0)
           (cons 41 0)
           (cons 42 0)
           (cons 91 0)
           (list 10 0.508 -0.206248)
           (cons 40 0)
           (cons 41 0)
           (cons 42 0)
           (cons 91 0)
           (list 10 0.36576 -0.254)
           (cons 40 0)
           (cons 41 0)
           (cons 42 0)
           (cons 91 0)
           (list 10 -0.36576 -0.254)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -0.508 -0.663448)
           (cons 40 0)
           (cons 41 0)
           (cons 42 0)
           (cons 91 0)
           (list 10 -0.508 -0.504952)
           (cons 40 0)
           (cons 41 0)
           (cons 42 0)
           (cons 91 0)
           (list 10 -0.36576 -0.4572)
           (cons 40 0)
           (cons 41 0)
           (cons 42 0)
           (cons 91 0)
           (list 10 0.36576 -0.4572)
           (cons 40 0)
           (cons 41 0)
           (cons 42 0)
           (cons 91 0)
           (list 10 0.508 -0.504952)
           (cons 40 0)
           (cons 41 0)
           (cons 42 0)
           (cons 91 0)
           (list 10 0.508 -0.663448)
           (cons 40 0)
           (cons 41 0)
           (cons 42 0)
           (cons 91 0)
           (list 10 0.36576 -0.7112)
           (cons 40 0)
           (cons 41 0)
           (cons 42 0)
           (cons 91 0)
           (list 10 -0.36576 -0.7112)
           (cons 40 0)
           (cons 41 0)
           (cons 42 0)
           (cons 91 0)
          )
         )
         (entmake (list (cons 0 "ENDBLK")))
        )
       )
       ((= (strcase BLKNAME) (strcase "WheelRightM6"))
        (progn
         (entmake)
         (entmake
          (list
           (cons 0 "BLOCK")
           (cons 2 "WheelRightM6")
           (cons 70 0)
           (cons 4 "")
           (list 10 0 0 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -0.508 0.047752)
           (cons 40 0)
           (cons 41 0)
           (cons 42 0)
           (cons 91 0)
           (list 10 -0.508 0.206248)
           (cons 40 0)
           (cons 41 0)
           (cons 42 0)
           (cons 91 0)
           (list 10 -0.36576 0.254)
           (cons 40 0)
           (cons 41 0)
           (cons 42 0)
           (cons 91 0)
           (list 10 0.36576 0.254)
           (cons 40 0)
           (cons 41 0)
           (cons 42 0)
           (cons 91 0)
           (list 10 0.508 0.206248)
           (cons 40 0)
           (cons 41 0)
           (cons 42 0)
           (cons 91 0)
           (list 10 0.508 0.047752)
           (cons 40 0)
           (cons 41 0)
           (cons 42 0)
           (cons 91 0)
           (list 10 0.36576 0)
           (cons 40 0)
           (cons 41 0)
           (cons 42 0)
           (cons 91 0)
           (list 10 -0.36576 0)
           (cons 40 0)
           (cons 41 0)
           (cons 42 0)
           (cons 91 0)
          )
         )
         (entmake
          (list
           (cons 0 "LWPOLYLINE")
           (cons 100 "AcDbEntity")
           (cons 67 0)
           (cons 8 "0")
           (cons 62 7)
           (cons 6 "Continuous")
           (cons 48 1.524)
           (cons 100 "AcDbPolyline")
           (cons 90 8)
           (cons 70 129)
           (cons 43 0)
           (cons 38 0)
           (cons 39 0)
           (list 10 -0.508 0.504952)
           (cons 40 0)
           (cons 41 0)
           (cons 42 0)
           (cons 91 0)
           (list 10 -0.508 0.663448)
           (cons 40 0)
           (cons 41 0)
           (cons 42 0)
           (cons 91 0)
           (list 10 -0.36576 0.7112)
           (cons 40 0)
           (cons 41 0)
           (cons 42 0)
           (cons 91 0)
           (list 10 0.36576 0.7112)
           (cons 40 0)
           (cons 41 0)
           (cons 42 0)
           (cons 91 0)
           (list 10 0.508 0.663448)
           (cons 40 0)
           (cons 41 0)
           (cons 42 0)
           (cons 91 0)
           (list 10 0.508 0.504952)
           (cons 40 0)
           (cons 41 0)
           (cons 42 0)
           (cons 91 0)
           (list 10 0.36576 0.4572)
           (cons 40 0)
           (cons 41 0)
           (cons 42 0)
           (cons 91 0)
           (list 10 -0.36576 0.4572)
           (cons 40 0)
           (cons 41 0)
           (cons 42 0)
           (cons 91 0)
          )
         )
         (entmake (list (cons 0 "ENDBLK")))
        )
       )
       (T
        (progn
         (alert (strcat "!!! BLOCK DOES NOT EXIST - " BLKNAME " !!!"))
        )
       )
 )
)
